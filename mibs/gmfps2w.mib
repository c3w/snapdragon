--
-- Sorrento Networks Private MIB for the GigaMux FPS2W Card.
--
-- This MIB file is to be used with GigaMux GM-FPS2W version 1.1.00
-- or greater. Previous versions may not return all variables.
--
-- Revision 1.2	06thDec2002	ndhameja
-- 1. Added back TFTP related traps for backward compatibility.
--
--
-- Modification History :
--
-- Revision 1.1	  06/04/2002	mjagtap
-- 1. Deprecated 'unit', 'managemet', 'client' and 'tftp' groups.
--    Next firmware revision will NOT support these deprecated groups
--    from this MIB.
--    Instead, firmware version mentioned above support such groups 
--    from gmCommon.mib.
-- 2. Removed TFTP related traps. Now supports these traps from gmCommon.mib
--
-- Revision 1.0	28/11/2000	ndhameja
-- Initial Release.
--
-- Copyright 2002 Sorrento Networks. All Rights Reserved.
-- Reproduction of this document is authorized on condition
-- that this copyright notice is included.
-- This Sorrento Networks SNMP Management Information Base
-- Specification (Specification) embodies Sorrento Networks'
-- proprietary intellectual property.  Sorrento Networks retains
-- all title and ownership in the Specification, including any
-- revisions.
--
-- It is Sorrento Networks intent to encourage the widespread
-- use of this Specification in connection with the management of
-- Sorrento Networks products. Sorrento Networks grants vendors,
-- end-users, and other interested parties a non-exclusive license to
-- use this Specification in connection with the management of Sorrento 
-- Networks products.
--
-- This Specification is supplied "AS IS," and Sorrento Networks
-- makes no warranty, either express or implied, as to the use,
-- operation, condition, or performance of the Specification.


	GMux-FPS2WCard-MIB DEFINITIONS ::= BEGIN

	IMPORTS
		  enterprises, IpAddress
			  FROM RFC1155-SMI
		  DisplayString
			  FROM RFC1213-MIB
		  OBJECT-TYPE
			  FROM RFC-1212
		  TRAP-TYPE
			  FROM RFC-1215;

	osicomTechnologies	OBJECT IDENTIFIER ::= { enterprises 2522 }
	gigaNest		OBJECT IDENTIFIER ::= { osicomTechnologies 1 }
	gigaMuxFPS2W		OBJECT IDENTIFIER ::= { gigaNest 15 }
		status		OBJECT IDENTIFIER ::= { gigaMuxFPS2W 1 }
		configuration	OBJECT IDENTIFIER ::= { gigaMuxFPS2W 2 }
		unit		OBJECT IDENTIFIER ::= { gigaMuxFPS2W 3 }
		management	OBJECT IDENTIFIER ::= { gigaMuxFPS2W 4 }
		client		OBJECT IDENTIFIER ::= { gigaMuxFPS2W 5 }
		tftp		OBJECT IDENTIFIER ::= { gigaMuxFPS2W 6 }

--
--  Status group
--
--  This group contains objects for obtaining the status of the 
--  FPS2W channel card.
--

	fps2wTrunk1Status  OBJECT-TYPE
		SYNTAX INTEGER
		{
			normal(1),
			failed(2),
			not-applicable(3)
		}
		ACCESS read-only
		STATUS mandatory
		DESCRIPTION
			"The state of fiber 1 for a FPS2W module."
		::= { status 1 }

	fps2wTrunk2Status  OBJECT-TYPE
		SYNTAX INTEGER
		{
			normal(1),
			failed(2),
			not-applicable(3)
		}
		ACCESS read-only
		STATUS mandatory
		DESCRIPTION
			"The state of fiber 2 for a FPS2W module."
		::= { status 2 }

--
--  Configuration group
--
--  This group contains objects for managing the FPS2W version of
--	the channel card
--

	circuitId OBJECT-TYPE
		SYNTAX DisplayString	(SIZE (0..20))
		ACCESS read-write
		STATUS mandatory
		DESCRIPTION
			"This optional field can be used by a network
			 management system to provide an end-to-end
			 view of a single channel which is
			 cross-connected through multiple
			 multiplexers. Enter the same number into all
			 modules which carry the same channel of
			 traffic. Up to 20 alphanumeric characters can
			 be entered."
		::= { configuration 1 }

	sequenceNumber OBJECT-TYPE
		SYNTAX INTEGER
		ACCESS read-write
		STATUS mandatory
		DESCRIPTION
			"This optional field is used along with the
			 CircuitId field to portray and end-to-end
			 view of each channel which is cross-connected
			 through multiplexers. Enter a two digit
			 number, starting with 01 on the module
			 interfacing to the customers equipment on the
			 one end. Increment this number as the
			 connection traverses other modules
			 to the far end of the circuit."
		::= { configuration 2 }

	fps2wSwitchMode  OBJECT-TYPE
		SYNTAX INTEGER
		{
			automatic(1),
			lockout(2)
		}
		ACCESS read-write
		STATUS mandatory
		DESCRIPTION
			"The operational mode of the FPS2W switch:-

			 automatic(1) - A failure on the working line causes an 
			 automatic switch to the protection line & vice versa.
			 
			 lockout(2)   - When you perform a lockout, you prevent
			 the traffic from switching to the protection line, it 
			 returns to the working line regardless of the condition 
			 of the working line."
		::= { configuration 3 }

	fps2wSwitchPostion  OBJECT-TYPE
		SYNTAX INTEGER
		{
			fiber1(1),
			fiber2(2)
		}
		ACCESS read-only
		STATUS mandatory
		DESCRIPTION
			"The position of the FPS2W switch. Applicable
			 only for FPS2W modules."
		::= { configuration 4 }

	fps2wRevertFlag  OBJECT-TYPE
		SYNTAX INTEGER
		{
			non-revertive(1),
			revertive(2)
		}
		ACCESS read-write
		STATUS mandatory
		DESCRIPTION
			" non-revertive  - The user can perform a forced switch 
			 of working to protection or of protection to working.
			 revertive - The user can perform a forced switch 
			 of working to protection only."
		::= { configuration 5 }

	fps2wForcedSwitch  OBJECT-TYPE
		SYNTAX INTEGER
		{
			fiber1(1),
			fiber2(2),
			release(3)
		}
		ACCESS read-write
		STATUS mandatory
		DESCRIPTION
			"When you perform a forced switch of working to protection,
			traffic switches to the protection line, and vice versa.
			The switch will not occur if the line has LOS (loss of 
			signal)."
		::= { configuration 6 }

--
--
--	Unit group
--
--

	unitName OBJECT-TYPE
		SYNTAX DisplayString (SIZE (0..8))
		ACCESS read-only
		STATUS deprecated
		DESCRIPTION
			"Short name for the card."
		::= { unit 1 }

	unitDescription OBJECT-TYPE
		SYNTAX DisplayString (SIZE (0..40))
		ACCESS read-only
		STATUS deprecated
		DESCRIPTION
			"Additional description information about
			 the card, expanding upon the short name."
		::= { unit 2 }

	unitVersion OBJECT-TYPE
		SYNTAX DisplayString (SIZE (0..16))
		ACCESS read-only
		STATUS deprecated
		DESCRIPTION
			"The software version number."
		::= { unit 3 }

	unitCommand OBJECT-TYPE
		SYNTAX INTEGER
		{
			nothing(1),
			warmResetNow(2),
			resetAllCounters(3),
			saveConfigurationNow(4)
		}
		ACCESS read-write
		STATUS deprecated
		DESCRIPTION
			"Set this object to one of the following
			 values to perform one of a variety of
			 actions:
			 nothing(1)		 - Do nothing.
			 warmResetNow(2)	 - Causes a system
						   restart.
			 resetAllCounters(3)	 - Reset all
						   statistics counters.
			 saveConfigurationNow(4) - Stores active
						   configuration into
						   non-volatile flash
						   memory.
			 The default is nothing(1)."
		::= { unit 4 }

	unitConfigurationState OBJECT-TYPE
		SYNTAX INTEGER
		{
			unchanged(1),
			changed(2)
		}
		ACCESS read-only
		STATUS deprecated
		DESCRIPTION
			"Indicates the state of the active
			 configuration as compared to that saved in
			 flash memory.
			 unchanged(1) - Flash is up-to-date
			 changed(2)   - operating configuration differs
					from that saved in the flash
					memory."
		::= { unit 5 }

--
--	Management group
--
--	Internet management (SNMP/TCP/IP) configuration options.
--

	internetAddress OBJECT-TYPE
		SYNTAX IpAddress
		ACCESS read-only
		STATUS deprecated
		DESCRIPTION
			"internetAddress is the IP address that is
			 assigned to the card."
		::= { management 1 }

	subnetMask OBJECT-TYPE
		SYNTAX IpAddress
		ACCESS read-only
		STATUS deprecated
		DESCRIPTION
			"subnetMask is the IP subnet mask that is
			 assigned to the card."
		::= { management 2 }

	trapPriorityThreshold OBJECT-TYPE
		SYNTAX INTEGER 
		{
			minor(1),
			major(2),
			critical(3),
			none(4)
		}
		ACCESS read-only
		STATUS deprecated
		DESCRIPTION
			"Specifies the minimum priority of an alarm
			 condition for which a trap will be generated.
			 minor(1)    - all traps will be sent
			 major(2)    - only critical and major traps
			 critical(3) - only critical traps are sent
			 none(4)     - no traps will be sent."
		::= { management 3 }
		
	trapDelay OBJECT-TYPE
		SYNTAX INTEGER (0..255)
		ACCESS read-write
		STATUS deprecated
		DESCRIPTION
			"Specifies the delay between detection of a
			 alarm condition and the sending of a trap.
			 During this delay period, if the trap
			 condition clears, then the trap will not be
			 sent. This delay is used to avoid
			 transmission of traps for momentary
			 problems."
		::= { management 4 }

	clientAutoLearn OBJECT-TYPE
		SYNTAX INTEGER	
		{
			enabled(1),
			disabled(2)
		}
		ACCESS read-write
		STATUS deprecated
		DESCRIPTION
			"clientAutoLearn allows the card to
			 automatically learn client SNMP addresses. If
			 enabled, the card can automatically learn 16
			 Client IP addresses and store them in the
			 unitClientTable as dynamic. Addresses are
			 learned from incoming SNMP messages. If set
			 to disabled, only the addresses that are
			 manually entered in the unitClientTable are
			 available.
			 The default is enabled(1)."
		::= { management 5 }

--
--	Client Table
--
--	Contains the IP addresses of SNMP network management stations
--	that will receive SNMP traffic.  The agent will only
--	communicated with managers whose IP addresses are in the
--	table.	Entries can be either learned automatically, from
--	requests received by the card, or via configuration, by
--	terminal or SNMP. See also the clientAutoLearn object in the
--	management group.
--

	clientTable OBJECT-TYPE
		SYNTAX SEQUENCE OF ClientEntry
		ACCESS not-accessible
		STATUS deprecated
		DESCRIPTION
			"Client IP addresses of SNMP network
			 management stations that should receive SNMP
			 traffic generated by the card."
		::= { client 1 }

	clientEntry OBJECT-TYPE
		SYNTAX ClientEntry
		ACCESS not-accessible
		STATUS deprecated
		DESCRIPTION
			""
		INDEX	{ clientIndex }
		::= { clientTable 1 }

	ClientEntry ::=
		SEQUENCE 
		{
			clientIndex
				INTEGER,
			clientAddress
				IpAddress,
			clientType
				INTEGER
		}

	clientIndex OBJECT-TYPE
		SYNTAX INTEGER
		ACCESS read-only
		STATUS deprecated
		DESCRIPTION
			"Number for this entry in the client table."
		::= { clientEntry 1 }

	clientAddress OBJECT-TYPE
		SYNTAX IpAddress
		ACCESS read-write
		STATUS deprecated
		DESCRIPTION
			"IP address for an SNMP network management
			 station. Set the address to 0.0.0.0 to remove
			 the entry."
		::= { clientEntry 2 }

	clientType OBJECT-TYPE
		SYNTAX INTEGER
		{
			dynamic(1),
			static(2),
			unused(3)
		}
		ACCESS read-only
		STATUS deprecated
		DESCRIPTION
			"Status of the entry:
			 dynamic(1) - Auto-learned from an SNMP request
			 static(2)  - Configured statically
			 unused(3)  - As yet unused entry."
		::= { clientEntry 3 }

--
--
-- tftp Group
--
--

	tftpSoftwareServerIPAddress OBJECT-TYPE
	SYNTAX IpAddress
	ACCESS read-write
	STATUS deprecated
	DESCRIPTION
		"IP address of TFTP Server for Operational Code."
	::= { tftp 1 }
														
	tftpSoftwareFileName OBJECT-TYPE
		SYNTAX DisplayString (SIZE (0..32))
		ACCESS read-write
		STATUS deprecated
		DESCRIPTION
			"File name of operational code."
		::= { tftp 2}

	tftpAction OBJECT-TYPE
		SYNTAX INTEGER  
		{
			no-action(1),
			start-software-download(2)
		}
		ACCESS read-write
		STATUS deprecated
		DESCRIPTION
		    "Get or Set download state.
			no-action(1)			- no TFTP activity
			start-software-download(2) 	- srtart software download"
		::= { tftp 3 }


	tftpStatus OBJECT-TYPE
		SYNTAX INTEGER  
		{
			file-not-found(1),
			access-violation(2),
			disk-full(3),
			illegal-TFTP-operation(4),
			unknown-part-TID(5),
			file-already-exists(6),
			no-such-user(7),
			missing-software-server-address(8),
			missing-software-file-name(9),
			file-type-error(10),
			bad-db-version(11),
			no-memory(12),
			crc-Error(13),
			time-out(14),
			transfer-ok(15),
			tftp-in-progress(16),
			none(99)
		}
		ACCESS read-only
		STATUS deprecated
		DESCRIPTION
			"Status of TFTP operation."
		::= { tftp 4 }

--
--
--  Enterprise specific traps
--
--

	fiberTrunk1Normal TRAP-TYPE
		ENTERPRISE gigaMuxFPS2W
		DESCRIPTION
			"FPS2W Fiber Trunk 1 Recovered."
		::= 31

	fiberTrunk1Failed TRAP-TYPE
		ENTERPRISE gigaMuxFPS2W
		DESCRIPTION
			"FPS2W Fiber Trunk 1 Failed."
		::= 32

	fiberTrunk2Normal TRAP-TYPE
		ENTERPRISE gigaMuxFPS2W
		DESCRIPTION
			"FPS2W Fiber Trunk 2 Recovered."
		::= 33

	fiberTrunk2Failed TRAP-TYPE
		ENTERPRISE gigaMuxFPS2W
		DESCRIPTION
			"FPS2W Fiber Trunk 2 Failed."
		::= 34

	lockoutModeGen TRAP-TYPE
		ENTERPRISE gigaMuxFPS2W 
		DESCRIPTION
			"Switched to lockout mode, out of auto mode."
		::= 35
	
	lockoutModeClr TRAP-TYPE
		ENTERPRISE gigaMuxFPS2W 
		DESCRIPTION
			"Switched to automatic mode, out of lockout mode."
		::= 36

	forcedSwitchToAGen TRAP-TYPE
		ENTERPRISE gigaMuxFPS2W
		DESCRIPTION
			"Switch Forced to fiber A."
		::= 37

	forcedSwitchToAClr TRAP-TYPE
		ENTERPRISE gigaMuxFPS2W
		DESCRIPTION
			"Force Switch to fiber A released."
		::= 38
		
	forcedSwitchToBGen TRAP-TYPE
		ENTERPRISE gigaMuxFPS2W
		DESCRIPTION
			"Switch Forced to fiber B."
		::= 39

	forcedSwitchToBClr TRAP-TYPE
		ENTERPRISE gigaMuxFPS2W
		DESCRIPTION
			"Force Switch to fiber B released."
		::= 40

	tftpDownloadFailed TRAP-TYPE
		ENTERPRISE gigaMuxFPS2W
		VARIABLES { tftpStatus }
		DESCRIPTION
			"TFTP download operation failed.
			Error code is sent as first attached variable."
		::= 41

	tftpDownloadSuccessful TRAP-TYPE
		ENTERPRISE gigaMuxFPS2W
		DESCRIPTION
			"TFTP download operation was successful.
			Card will automatically reset and boot up with new image."
		::= 42

END
