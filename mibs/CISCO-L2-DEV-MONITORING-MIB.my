-- *****************************************************************
-- CISCO-L2-DEV-MONITORING-MIB.my: CISCO L2 DEVICE MONITORING MIB 
-- file
--
-- August 2001, Francis Pang 
--
-- Copyright (c) 2001, 2002 by Cisco Systems, Inc.
-- All rights reserved.
-- *****************************************************************
--
CISCO-L2-DEV-MONITORING-MIB DEFINITIONS ::= BEGIN

IMPORTS
        MODULE-IDENTITY,
        NOTIFICATION-TYPE,
        OBJECT-TYPE,
        Unsigned32
                FROM SNMPv2-SMI
        MODULE-COMPLIANCE,
        NOTIFICATION-GROUP,
        OBJECT-GROUP
                FROM SNMPv2-CONF
        MacAddress, 
        TruthValue,
        RowStatus
                FROM SNMPv2-TC
        ciscoMgmt
                FROM CISCO-SMI;





ciscoL2DevMonMIB MODULE-IDENTITY
        LAST-UPDATED    "200109270000Z"
        ORGANIZATION    "Cisco System Inc."
        CONTACT-INFO
                "       Cisco Systems
                        Customer Service

                Postal: 170 West Tasman Drive,
                        San Jose CA 95134-1706.
                        USA

                   Tel: +1 800 553-NETS

                E-mail: cs-snmp@cisco.com"
        DESCRIPTION
                "This MIB module is for monitoring of active 
                layer 2 devices by hot standby layer 2 devices 
                and the configuration of hot standby switch-over
                parameters."
        REVISION        "200109270000Z"
        DESCRIPTION
                "Initial version of this MIB module."
        ::= { ciscoMgmt 271 }



ciscoL2DevMonMIBObjects OBJECT IDENTIFIER 
        ::= { ciscoL2DevMonMIB 1 }

cl2DevMonConfig OBJECT IDENTIFIER 
        ::= { ciscoL2DevMonMIBObjects 1}


-- *****************************************************************
--  Attributes for Hot Standby Monitoring unit 
-- *****************************************************************

cl2DevMonInStandbyMode OBJECT-TYPE   
        SYNTAX TruthValue 
        MAX-ACCESS read-write
        STATUS current
        DESCRIPTION
                "If the value of this variable is TRUE, this device 
                is in monitoring or standby mode and it will poll 
                for the health of the devices on the 
                cl2DevMonActiveTable.  If the value of 
                cl2DevMonInStandbyMode is FALSE,
                it only can be set back to TRUE using command line 
                interface or SNMP request. The value can be set to 
                FALSE only by the device itself because force 
                switch over from standby mode to active mode is
                not allowed."
        DEFVAL { false }
        ::= { cl2DevMonConfig 1 }


cl2DevMonNotifEnabled OBJECT-TYPE
        SYNTAX TruthValue
        MAX-ACCESS read-write
        STATUS current
        DESCRIPTION
               "Indicates whether cl2DevMonSwitchover 
                notifications will or will not be sent by the device 
                when it changes its cl2DevMonInStandbyMode to 
                FALSE and becomes an active unit."
        DEFVAL { false }
        ::= { cl2DevMonConfig 2 }


cl2DevMonActiveTable OBJECT-TYPE
        SYNTAX SEQUENCE OF Cl2DevMonActiveEntry
        MAX-ACCESS not-accessible
        STATUS current
        DESCRIPTION 
                "The table for active devices on the network
                being monitored by the hot standby monitoring 
                unit. This table is on the hot standby 
                monitoring unit. All entries on this table will 
                only be added, deleted, modified using command
                user interface or SNMP request."
        ::= { cl2DevMonConfig 3 }


cl2DevMonActiveEntry OBJECT-TYPE
        SYNTAX Cl2DevMonActiveEntry
        MAX-ACCESS not-accessible
        STATUS current
        DESCRIPTION 
                "An entry in the cl2DevMonActiveTable table."
        INDEX { cl2DevMonActiveMacAddress }
        ::= { cl2DevMonActiveTable 1 }


Cl2DevMonActiveEntry ::= SEQUENCE { 
        cl2DevMonActiveMacAddress           MacAddress,
        cl2DevMonActivePollingFrequency     Unsigned32, 
        cl2DevMonActivePollingTimeOut       Unsigned32,
        cl2DevMonActiveRowStatus            RowStatus 
                                      }


cl2DevMonActiveMacAddress OBJECT-TYPE   
        SYNTAX MacAddress 
        MAX-ACCESS not-accessible 
        STATUS current
        DESCRIPTION
                "Mac address of the active unit to be monitored by
                this hot standby monitoring unit." 
        ::= { cl2DevMonActiveEntry 1 }

cl2DevMonActivePollingFrequency OBJECT-TYPE   
        SYNTAX Unsigned32 (1..30) 
        UNITS "seconds"
        MAX-ACCESS read-create
        STATUS current
        DESCRIPTION
                "The frequency, in seconds, the active unit 
                specified by cl2DevMonActiveMacAddress is polled 
                for its health."
        DEFVAL { 5 }
        ::= { cl2DevMonActiveEntry 2 }


cl2DevMonActivePollingTimeOut OBJECT-TYPE 
        SYNTAX Unsigned32 (1..600) 
        UNITS "seconds"
        MAX-ACCESS read-create
        STATUS current
        DESCRIPTION
                "The total time, in seconds, the standby monitoring 
                unit can tolerate the failure of polling 
                of the active unit.  After this duration, one
                more failure of the polling will trigger this hot
                standby monitoring unit to take over and become an
                active unit. It then will stop monitoring other 
                active units and set value of cl2DevMonInStandbyMode 
                to FALSE."
        DEFVAL { 5 }
        ::= { cl2DevMonActiveEntry 3 }


cl2DevMonActiveRowStatus OBJECT-TYPE 
        SYNTAX RowStatus 
        MAX-ACCESS read-create
        STATUS current
        DESCRIPTION
                "The status column used for creating, modifying, and
                deleting instances of the columnar objects in the 
                cl2DevMonActiveTable table."
        ::= { cl2DevMonActiveEntry 4 }



-- *****************************************************************
-- notifications
-- *****************************************************************

ciscoL2DevMonMIBNotifications OBJECT IDENTIFIER 
        ::= { ciscoL2DevMonMIB 0 }

cl2DevMonSwitchover NOTIFICATION-TYPE
        OBJECTS {    
                cl2DevMonActivePollingFrequency, 
                cl2DevMonActivePollingTimeOut   
                }
        STATUS current
        DESCRIPTION
                "This cl2DevMonSwitchover notification will 
                only be sent when this device changes its 
                cl2DevMonInStandbyMode to FALSE and becomes 
                an active unit. The sending of these 
                notifications can be enabled/disabled
                via the cl2DevMonNotifEnabled object."
        ::= { ciscoL2DevMonMIBNotifications 1 }



-- *****************************************************************
--   Conformance information
-- *****************************************************************

ciscoL2DevMonMIBConformance
        OBJECT IDENTIFIER ::= { ciscoL2DevMonMIB 2 }
ciscoL2DevMonMIBCompliances
        OBJECT IDENTIFIER 
                ::= { ciscoL2DevMonMIBConformance 1 }
ciscoL2DevMonMIBGroups
        OBJECT IDENTIFIER 
                ::= { ciscoL2DevMonMIBConformance 2 }


-- *****************************************************************
--   Compliance statements
-- *****************************************************************

ciscoL2DevMonCompliance MODULE-COMPLIANCE
        STATUS  current
        DESCRIPTION
                "The compliance statement for the 
                ciscoL2DevMonConfig group."
        MODULE 
                MANDATORY-GROUPS {
                        ciscoL2DevMonConfigGroup,
                        ciscoL2DevMonNotificationGroup
                }
        ::= { ciscoL2DevMonMIBCompliances 1 }

-- *****************************************************************
--   Units of conformance
-- *****************************************************************


ciscoL2DevMonConfigGroup OBJECT-GROUP
        OBJECTS {
                cl2DevMonInStandbyMode,
                cl2DevMonNotifEnabled,
                cl2DevMonActivePollingFrequency,
                cl2DevMonActivePollingTimeOut,
                cl2DevMonActiveRowStatus
        }
        STATUS    current
        DESCRIPTION
                "Management information to support operation of 
                 L2 monitoring and hot standby."
        ::= { ciscoL2DevMonMIBGroups 1 }


ciscoL2DevMonNotificationGroup NOTIFICATION-GROUP
        NOTIFICATIONS {
                cl2DevMonSwitchover 
        }
        STATUS current
        DESCRIPTION
                "The notifications for the 
                CISCO-L2-DEV-MONITORING-MIB"
        ::= { ciscoL2DevMonMIBGroups 2 }

END
