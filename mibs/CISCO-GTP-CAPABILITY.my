-- ********************************************************************
-- CISCO-GTP-CAPABILITY.my CISCO-GTP-MIB AGENT-CAPABILITIES
--
-- March 2002, Jeyachitra Alagar
--
-- Copyright (c) 2002 by cisco Systems, Inc.
-- All rights reserved.
-- ********************************************************************

CISCO-GTP-CAPABILITY DEFINITIONS ::= BEGIN

IMPORTS
        MODULE-IDENTITY
                FROM SNMPv2-SMI
        AGENT-CAPABILITIES
                FROM SNMPv2-CONF
        ciscoAgentCapability
                FROM CISCO-SMI;

ciscoGtpCapability MODULE-IDENTITY
        LAST-UPDATED    "200203211600Z"
        ORGANIZATION    "Cisco Systems, Inc."
        CONTACT-INFO
                "       Cisco Systems
                        Customer Service

                        Postal: 170 West Tasman Drive
                                San Jose, CA  95134
                                USA
                                Tel: +1 800 553-NETS

                        E-mail: cs-gprs@cisco.com"
        DESCRIPTION
                "Agent capabilities for CISCO-GTP-MIB"
        REVISION        "200203211600Z"
        DESCRIPTION
                "Initial version of this MIB module."
        ::= { ciscoAgentCapability 9979 }

cGtpCapabilityV12R02Rev08YD AGENT-CAPABILITIES
        PRODUCT-RELEASE  "Cisco IOS 12.2(8)YD"
        STATUS           current
        DESCRIPTION      "CISCO GTP MIB capabilities"
        SUPPORTS         CISCO-GTP-MIB
        INCLUDES         {
                          cGtpConfigurationsGroupRev1,
                          cGtpStatusGroupRev1,
                          cGtpStatisticsGroupRev1,
                          cGtpNotifGroup
                          }

        VARIATION        cGtpGSNService
        SYNTAX           BITS
        DESCRIPTION      "SGSN GPRS service is not supported"

        VARIATION        cGtpVersion
        ACCESS           read-only
        DESCRIPTION      "Write Access not yet supported"

        VARIATION        cGtpT3TunnelTimer
        ACCESS           not-accessible
        DESCRIPTION      "Both read and write access are not supported"

        ::= { ciscoGtpCapability 1 }

END
