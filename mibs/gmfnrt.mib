--
-- Sorrento Networks Private MIB for Fiber Node Receiver and Transmitter Cards
--
--
-- This MIB file is to be used with GM-FNR1,GM-FNR2, GM-FNT1,GM-FNT2
-- version 1.0.0 or greater.
--
-- Revision 1.0.0	08/08/2000	mjagtap
-- Initial Release.
--
-- Copyright 2000, Sorrento Networks. All Rights Reserved.
-- Reproduction of this document is authorized on condition that this
-- copyright notice is included. This Sorrento Networks' SNMP
-- Management Information Base Specification (Specification) embodies
-- Sorrento Networks' proprietary intellectual property.  Sorrento Networks
-- retains all title and ownership in the Specification, including any revisions.
--
-- It is Sorrento Networks' intent to encourage the widespread use
-- of this Specification in connection with the management of Sorrento Networks'
-- products. Sorrento Networks grants vendors,
-- end-users, and other interested parties a non-exclusive license to
-- use this Specification in connection with the management of 
-- Sorrento Networks' products.
--
-- This Specification is supplied "AS IS," and Sorrento Networks
-- makes no warranty, either express or implied, as to the use,
-- operation, condition, or performance of the Specification.


	GMUX-FNRT-MIB DEFINITIONS ::= BEGIN

	IMPORTS
		  enterprises, IpAddress
			  FROM RFC1155-SMI
		  DisplayString
			  FROM RFC1213-MIB
		  OBJECT-TYPE
			  FROM RFC-1212
		  TRAP-TYPE
			  FROM RFC-1215;

	osicomTechnologies	OBJECT IDENTIFIER ::= { enterprises 2522 }
	gigaNest			OBJECT IDENTIFIER ::= { osicomTechnologies 1 }
	gigaMuxFNRT			OBJECT IDENTIFIER ::= { gigaNest 11 }
	moduleA 			OBJECT IDENTIFIER ::= { gigaMuxFNRT 1 }
	moduleB 			OBJECT IDENTIFIER ::= { gigaMuxFNRT 2 }
	unit				OBJECT IDENTIFIER ::= { gigaMuxFNRT 3 }
	management			OBJECT IDENTIFIER ::= { gigaMuxFNRT 4 }
	client				OBJECT IDENTIFIER ::= { gigaMuxFNRT 5 }

--
--  moduleA Status group
--
--  These objects contain current settings and status for the
--  receiver module on the card.
--

	rxSigInA  OBJECT-TYPE
		SYNTAX INTEGER
		{
			normal(1),
			low(2),
			not-applicable(3)
		}
		ACCESS read-only
		STATUS mandatory
		DESCRIPTION
			"Indicates whether receiver has
			 proper output electrical signal level or not
			 presented at the equipment OUTPUT connector
			 of the module.
			 Applicable only for GM-FNR1, GM-FNR2."
		::= { moduleA 1 }

	txLaserOn OBJECT-TYPE
		SYNTAX INTEGER
		{
			normal(1),
			failed(2),
			not-applicable(3)
		}
		ACCESS read-only
		STATUS mandatory
		DESCRIPTION
			"Transmitter Laser status.
			 Applicable only for GM-FNT1, GM-FNT2."
		::= { moduleA 2 }

	txChannel OBJECT-TYPE
		SYNTAX INTEGER
		{
			  not-applicable(99)
		}
		ACCESS read-only
		STATUS mandatory
		DESCRIPTION
			"Transmitter Laser Channel.
			 Applicable only for GM-FNT1, GM-FNT2."
		::= { moduleA 3 }

	txLaserTempHigh OBJECT-TYPE
		SYNTAX INTEGER
		{
			no(1),
			yes(2),
			not-applicable(3)
		}
		ACCESS read-only
		STATUS mandatory
		DESCRIPTION
			"Transmitter Laser Temperature High or not.
			 Applicable only for GM-FNT1, GM-FNT2."
		::= { moduleA 4 }

	txLaserTempLow OBJECT-TYPE
		SYNTAX INTEGER
		{
			no(1),
			yes(2),
			not-applicable(3)
		}
		ACCESS read-only
		STATUS mandatory
		DESCRIPTION
			"Transmitter Laser Temperature Low or not.
			 Applicable only for GM-FNT1, GM-FNT2."
		::= { moduleA 5 }

--
--  moduleB Status group
--
--  These objects contain current settings and status for the
--  receiver module on the card.
--

	rxSigInB  OBJECT-TYPE
		SYNTAX INTEGER
		{
			normal(1),
			low(2),
			not-applicable(3)
		}
		ACCESS read-only
		STATUS mandatory
		DESCRIPTION
			"Indicates whether receiver has
			 proper output electrical signal level or not
			 presented at the equipment OUTPUT connector
			 of the module.
			 Applicable only for GM-FNR1, GM-FNR2."
		::= { moduleB 1 }


--
--
--      Unit group
--
--

        unitName OBJECT-TYPE
                SYNTAX DisplayString (SIZE (0..8))
                ACCESS read-only
                STATUS mandatory
                DESCRIPTION
                        "Short name for the card."
                ::= { unit 1 }

        unitDescription OBJECT-TYPE
                SYNTAX DisplayString (SIZE (0..40))
                ACCESS read-only
                STATUS mandatory
                DESCRIPTION
                        "Additional description information about
                         the card, expanding upon the short name."
                ::= { unit 2 }

        unitVersion OBJECT-TYPE
                SYNTAX DisplayString (SIZE (0..16))
                ACCESS read-only
                STATUS mandatory
                DESCRIPTION
                        "The software version number."
                ::= { unit 3 }

        unitCommand OBJECT-TYPE
                SYNTAX INTEGER
                {
	                nothing(1),
	                warmResetNow(2),
	                resetAllCounters(3),
	                saveConfigurationNow(4)
                }
                ACCESS read-write
                STATUS mandatory
                DESCRIPTION
                        "Set this object to one of the following
                         values to perform one of a variety of
                         actions:
	                         nothing(1)              - Do nothing.
	                         warmResetNow(2)         - Causes a system
	                                                   restart.
	                         resetAllCounters(3)     - Reset all
	                                                   statistics counters.
	                         saveConfigurationNow(4) - Stores active
	                                                   configuration into
	                                                   non-volatile flash
	                                                   memory.
	                         The default is nothing(1)."
                ::= { unit 4 }

        unitConfigurationState OBJECT-TYPE
                SYNTAX INTEGER
                {
                    unchanged(1),
                    changed(2)
                }
                ACCESS read-only
                STATUS mandatory
                DESCRIPTION
                        "Indicates the state of the active
                         configuration as compared to that saved in
                         flash memory.
                         unchanged(1) - Flash is up-to-date
                         changed(2)   - operating configuration differs
                                        from that saved in the flash
                                        memory."
                ::= { unit 5 }

--
--      Management group
--
--      Internet management (SNMP/TCP/IP) configuration options.
--
        internetAddress OBJECT-TYPE
                SYNTAX IpAddress
                ACCESS read-only
                STATUS mandatory
                DESCRIPTION
                        "internetAddress is the IP address that is
                         assigned to the card."
                ::= { management 1 }
				
        subnetMask OBJECT-TYPE
                SYNTAX IpAddress
                ACCESS read-only
                STATUS mandatory
                DESCRIPTION
                        "subnetMask is the IP subnet mask that is
                         assigned to the card."
                ::= { management 2 }
				
        trapPriorityThreshold OBJECT-TYPE
				SYNTAX INTEGER 
				{
					minor(1),
					major(2),
					critical(3),
					none(4)
				}
                ACCESS read-write
                STATUS mandatory
                DESCRIPTION
                        "Specifies the minimum priority of an alarm
			 condition for which a trap will be generated.
                         minor(1)    - all traps will be sent
                         major(2)    - only critical and major traps
                         critical(3) - only critical traps are sent
                         none(4)     - no traps will be sent."
                ::= { management 3 }

        trapDelay OBJECT-TYPE
                SYNTAX INTEGER (0..255)
                ACCESS read-write
                STATUS mandatory
                DESCRIPTION
                        "Specifies the delay between detection of a
                         alarm condition and the sending of a trap.
                         During this delay period, if the trap
                         condition clears, then the trap will not be
                         sent. This delay is used to avoid
                         transmission of traps for momentary
                         problems."
                ::= { management 4 }

        clientAutoLearn OBJECT-TYPE
                SYNTAX INTEGER  
				{
					enabled(1),
					disabled(2)
				}
                ACCESS read-write
                STATUS mandatory
                DESCRIPTION
                        "clientAutoLearn allows the card to
                         automatically learn client SNMP addresses. If
                         enabled, the card can automatically learn 16
                         Client IP addresses and store them in the
                         unitClientTable as dynamic. Addresses are
                         learned from incoming SNMP messages. If set
                         to disabled, only the addresses that are
                         manually entered in the unitClientTable are
                         available.
                         The default is enabled(1)."
                ::= { management 5 }

--
--      Client Table
--
--      Contains the IP addresses of SNMP network management stations
--      that will receive SNMP traffic.  The agent will only
--      communicated with managers whose IP addresses are in the
--      table.  Entries can be either learned automatically, from
--      requests received by the card, or via configuration, by
--      terminal or SNMP. See also the clientAutoLearn object in the
--      management group.
--

        clientTable OBJECT-TYPE
                SYNTAX SEQUENCE OF clientEntry
                ACCESS not-accessible
                STATUS mandatory
                DESCRIPTION
                        "Client IP addresses of SNMP network
                         management stations that should receive SNMP
                         traffic generated by the card."
                ::= { client 1 }

        clientEntry OBJECT-TYPE
                SYNTAX ClientEntry
		ACCESS not-accessible
                STATUS mandatory
                DESCRIPTION
                        ""
                INDEX   { clientIndex }
                ::= { clientTable 1 }

        ClientEntry ::=
                SEQUENCE
				{
					clientIndex
						INTEGER,
					clientAddress
						IpAddress,
					clientType
						INTEGER
				}

        clientIndex OBJECT-TYPE
                SYNTAX INTEGER
                ACCESS read-only
                STATUS mandatory
                DESCRIPTION
                        "Number for this entry in the client table."
                ::= { clientEntry 1 }

        clientAddress OBJECT-TYPE
                SYNTAX IpAddress
                ACCESS read-write
                STATUS mandatory
                DESCRIPTION
                        "IP address for an SNMP network management
                         station. Set the address to 0.0.0.0 to remove
                         the entry."
                ::= { clientEntry 2 }

        clientType OBJECT-TYPE
                SYNTAX INTEGER
				{
					dynamic(1),
					static(2),
					unused(3)
				}
                ACCESS read-only
                STATUS mandatory
                DESCRIPTION
                        "Status of the entry:
                         dynamic(1) - Auto-learned from an SNMP request
                         static(2)  - Configured statically
                         unused(3)  - As yet unusd entry."
                ::= { clientEntry 3 }

--
--  Enterprise specific traps
--
--

	rxSigInANormal TRAP-TYPE
		ENTERPRISE gigaMuxFNRT
		DESCRIPTION
			"Generated when GMFNR Receiver A Signal is Normal."
		::= 1

	rxSigInALow TRAP-TYPE
		ENTERPRISE gigaMuxFNRT
		DESCRIPTION
  			"Generated when GMFNR Receiver A Signal turns Low."
		::= 2

	txLaserOn TRAP-TYPE
		ENTERPRISE gigaMuxFNRT
		DESCRIPTION
			"Generated when GMFNT Transmitter Laser turns Normal."
		::= 3

	txLaserFailed TRAP-TYPE
		ENTERPRISE gigaMuxFNRT
		DESCRIPTION
			"Generated when GMFNT Transmitter Laser Fails."
		::= 4

	txLaserTempHighNo TRAP-TYPE
		ENTERPRISE gigaMuxFNRT
		DESCRIPTION
			"Generated when GMFNT Transmitter Laser Temp turns Normal."
		::= 5

	txLaserTempHigh TRAP-TYPE
		ENTERPRISE gigaMuxFNRT
		DESCRIPTION
			"Generated when GMFNT Transmitter Laser Temp turns High."
		::= 6

	txLaserTempLowNo TRAP-TYPE
		ENTERPRISE gigaMuxFNRT
		DESCRIPTION
			"Generated when GMFNT Transmitter Laser Temp turns Normal."
		::= 7

	txLaserTempLow TRAP-TYPE
		ENTERPRISE gigaMuxFNRT
		DESCRIPTION
			"Generated when GMFNT Transmitter Laser Temp turns Low."
		::= 8

	rxSigInBNormal TRAP-TYPE
		ENTERPRISE gigaMuxFNRT
		DESCRIPTION
			"Generated when GMFNR Receiver B Signal is Normal."
		::= 9	

	rxSigInBLow TRAP-TYPE
		ENTERPRISE gigaMuxFNRT
		DESCRIPTION
			"Generated when GMFNR Receiver B Signal turns Low."
		::= 10

END
