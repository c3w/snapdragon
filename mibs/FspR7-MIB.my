FspR7-MIB DEFINITIONS ::= BEGIN

IMPORTS
    DisplayString,TestAndIncr,TimeStamp,RowStatus,DateAndTime,TruthValue,TEXTUAL-CONVENTION
      FROM  SNMPv2-TC
    MODULE-COMPLIANCE,NOTIFICATION-GROUP,OBJECT-GROUP
      FROM  SNMPv2-CONF
    Counter32,MODULE-IDENTITY,NOTIFICATION-TYPE,OBJECT-TYPE,OBJECT-IDENTITY,TimeTicks,mib-2,snmpModules,enterprises,Unsigned32,Integer32,IpAddress
      FROM  SNMPv2-SMI
    entPhysicalIndex
      FROM  ENTITY-MIB
    SnmpAdminString
      FROM  SNMP-FRAMEWORK-MIB
    fspR7,TrapAlarmSeverity,ServiceImpairment,neEventLogTimeStamp,neEventLogIdentityTranslation,config,EnableState,OnOff,neTrapsinkAddress,Counter64String
      FROM  ADVA-MIB
    EnableStateCaps,entityIndex,entityClass,entityContainedIn,LoopConfig,EthDuplexMode,EthDuplexModeCaps,SonetTimingSource,EntityIndex,SonetVcType,SonetVcBundleAllocation,SonetVcBundleAllocationCaps,ProtectionMech,ProtectionMechCaps,ApsDirection,OtnPayloadType,OtnPayloadTypeCaps,SonetVcTypeCaps,OhTerminationLevel,OhTerminationLevelCaps,Grade,ApsHoldoffTime,ApsType,ApsRevertMode,OtnTcmLevel,SonetTimingSourceCaps,OtnTcmLevelCaps,SonetTimingSourceCaps,ApsHoldoffTimeCaps
      FROM  ADVANEW-MIB;
    

fspR7MIB MODULE-IDENTITY
    LAST-UPDATED "200609050000Z"
    ORGANIZATION " 
          ADVA AG Optical Networking
        "  
    CONTACT-INFO "
          ADVA AG Optical Networking
          Justus-von-Liebig-Str. 7
          12489 Berlin, Germany
          
          Support Europe:
          Phone:  +49 89 89 0665 848
          Fax:    +49 89 89 0665 22848
          e-mail: support@advaoptical.com
          
          Support USA:
          Phone:  +1 201 995 0080
          Fax:    +1 201 995 0081
          e-mail: support-usa@advaoptical.com
          
          Support Asia:
          Phone:  +81 3 5408 5891
          Fax:    +81 3 5408 5899
        e-mail: support-asia@advaoptical.com
        "  
    DESCRIPTION
        "
         The FSP3000R7 MIB..
        " 
    REVISION "200609050000Z"  
    DESCRIPTION
        "
         The Release 7.0.6D MIB.
        " 
    REVISION "200606140000Z"  
    DESCRIPTION
        "
         The Release 7.0.6 MIB.
        " 
    REVISION "200605040000Z"  
    DESCRIPTION
        "
         The Release 7.0.2 MIB..
        " 
    ::= { fspR7 2 }
  
fspR7Products   OBJECT IDENTIFIER ::= { fspR7 1 }

-- The fspR7MIB sub-tree is further divided into:

conditionMIB   OBJECT IDENTIFIER ::= { fspR7MIB 1 }
adminMIB   OBJECT IDENTIFIER ::= { fspR7MIB 2 }
trapMIB   OBJECT IDENTIFIER ::= { fspR7MIB 3 }
configAndStatusMIB   OBJECT IDENTIFIER ::= { fspR7MIB 4 }
deploymentProvisioningMIB   OBJECT IDENTIFIER ::= { fspR7MIB 5 }
performanceMIB   OBJECT IDENTIFIER ::= { fspR7MIB 6 }
performanceAdmin   OBJECT IDENTIFIER ::= { performanceMIB 1 }
performanceMonitoring   OBJECT IDENTIFIER ::= { performanceMIB 2 }
fspR7Conformance   OBJECT IDENTIFIER ::= { fspR7MIB 7 }
fspR7VendorTypes   OBJECT IDENTIFIER ::= { fspR7MIB 8 }
      
-- The alarm MIB sub-tree is further divided into:

conditionFilters   OBJECT IDENTIFIER ::= { conditionMIB 1 }
currentConditions   OBJECT IDENTIFIER ::= { conditionMIB 2 }
      
-- The admin MIB sub-tree is further divided into:

neAdmin   OBJECT IDENTIFIER ::= { adminMIB 1 }
  
-- The trap MIB sub-tree is further divided into:

trapMibPrefix   OBJECT IDENTIFIER ::= { trapMIB 0 }
trapVariables   OBJECT IDENTIFIER ::= { trapMIB 1 }
  
-- The configAndStatus MIB sub-tree is further divided into:

commonConfigAndStatus   OBJECT IDENTIFIER ::= { configAndStatusMIB 1 }
equipmentConfigAndStatus   OBJECT IDENTIFIER ::= { configAndStatusMIB 2 }
interfaceConfigAndStatus   OBJECT IDENTIFIER ::= { configAndStatusMIB 3 }
serviceConfigAndStatus   OBJECT IDENTIFIER ::= { configAndStatusMIB 4 }
connectionConfigAndStatus   OBJECT IDENTIFIER ::= { configAndStatusMIB 5 }
systemConfigAndStatus   OBJECT IDENTIFIER ::= { configAndStatusMIB 6 }
  
-- The deploymentProvConfigAndStatus MIB sub-tree is further divided into:

shelfDeployProv   OBJECT IDENTIFIER ::= { deploymentProvisioningMIB 1 }
moduleDeployProv   OBJECT IDENTIFIER ::= { deploymentProvisioningMIB 2 }
plugDeployProv   OBJECT IDENTIFIER ::= { deploymentProvisioningMIB 3 }
facilityDeployProv   OBJECT IDENTIFIER ::= { deploymentProvisioningMIB 4 }

FspR7AdminState ::= TEXTUAL-CONVENTION
  STATUS        current
  DESCRIPTION                                                    
         "The Adminstrative State will be displayed in the GUI with full
         name values; it will be differently displayed in TL1 syntax according
         to TL1 display rules. The transaction into the UAS state requires
         a special destroy/delete function." 
  SYNTAX        INTEGER
                {
                  undefined(0),
                  uas(1),
                  is(2),
                  ains(3),
                  mgt(4),
                  mt(5),
                  dsbld(6)
                }

FspR7AdminStateCaps ::= TEXTUAL-CONVENTION
  STATUS        current
  DESCRIPTION                                                    
         "The Adminstrative State will be displayed in the GUI with full
         name values; it will be differently displayed in TL1 syntax according
         to TL1 display rules. The transaction into the UAS state requires
         a special destroy/delete function." 
  SYNTAX        BITS
                {
                  capUndefined(0),
                  capUas(1),
                  capIs(2),
                  capAins(3),
                  capMgt(4),
                  capMt(5),
                  capDsbld(6)
                }

FspR7AlsHoldoff ::= TEXTUAL-CONVENTION
  STATUS        current
  DESCRIPTION                                                    
         "Hold-Off Period for ALS Consequent Action" 
  SYNTAX        INTEGER
                {
                  undefined(0),
                  del0ms(1),
                  del250ms(2),
                  del550ms(3)
                }

FspR7AlsHoldoffCaps ::= TEXTUAL-CONVENTION
  STATUS        current
  DESCRIPTION                                                    
         "Hold-Off Period for ALS Consequent Action" 
  SYNTAX        BITS
                {
                  capUndefined(0),
                  capDel0ms(1),
                  capDel250ms(2),
                  capDel550ms(3)
                }

FspR7AlsMode ::= TEXTUAL-CONVENTION
  STATUS        current
  DESCRIPTION                                                    
         "Determines the reaction in backward direction in response to a LOS
         on the same Interface: on a Network Interface connected to the DWDM
         this is a matter of laser safety" 
  SYNTAX        INTEGER
                {
                  undefined(0),
                  advaALS(1),
                  sonetALS(2),
                  noALS(3)
                }

FspR7AlsModeCaps ::= TEXTUAL-CONVENTION
  STATUS        current
  DESCRIPTION                                                    
         "Determines the reaction in backward direction in response to a LOS
         on the same Interface: on a Network Interface connected to the DWDM
         this is a matter of laser safety" 
  SYNTAX        BITS
                {
                  capUndefined(0),
                  capAdvaALS(1),
                  capSonetALS(2),
                  capNoALS(3)
                }

FspR7APSCommand ::= TEXTUAL-CONVENTION
  STATUS        current
  DESCRIPTION                                                    
         "Protection Switch commands: Manual, Lock or Release.
         The 'Manual Switch' switches manually from addressed facility to
         the partner but does not force the traffic onto a broken fiber and
         it does not block the subsequent automatic functioning of the switch.
         The 'Lock Switch' - ask Gerald for description.......
         The 'Release Switch' releases the current switch command.
         Relevant especially to 'Lock Switch' command. For 'Manual Switch' relevant
         only if revertivity is supported." 
  SYNTAX        INTEGER
                {
                  undefined(0),
                  release(1),
                  manualSwitch(2)
                }

FspR7APSCommandCaps ::= TEXTUAL-CONVENTION
  STATUS        current
  DESCRIPTION                                                    
         "Protection Switch commands: Manual, Lock or Release.
         The 'Manual Switch' switches manually from addressed facility to
         the partner but does not force the traffic onto a broken fiber and
         it does not block the subsequent automatic functioning of the switch.
         The 'Lock Switch' - ask Gerald for description.......
         The 'Release Switch' releases the current switch command.
         Relevant especially to 'Lock Switch' command. For 'Manual Switch' relevant
         only if revertivity is supported." 
  SYNTAX        BITS
                {
                  capUndefined(0),
                  capRelease(1),
                  capManualSwitch(2)
                }

FspR7Baund ::= TEXTUAL-CONVENTION
  STATUS        current
  DESCRIPTION                                                    
         "Baud rate of the serial interface" 
  SYNTAX        INTEGER
                {
                  undefined(0),
                  baud2400(1),
                  baud4800(2),
                  baud9600(3),
                  baud19200(4),
                  baud38400(5),
                  baud57600(6),
                  baud115200(7)
                }

FspR7BaundCaps ::= TEXTUAL-CONVENTION
  STATUS        current
  DESCRIPTION                                                    
         "Baud rate of the serial interface" 
  SYNTAX        BITS
                {
                  capUndefined(0),
                  capBaud2400(1),
                  capBaud4800(2),
                  capBaud9600(3),
                  capBaud19200(4),
                  capBaud38400(5),
                  capBaud57600(6),
                  capBaud115200(7)
                }

FspR7BERThreshold ::= TEXTUAL-CONVENTION
  STATUS        current
  DESCRIPTION                                                    
         "Bit-Error-Based Degradation Definition for SONET (standard integration period)" 
  SYNTAX        INTEGER
                {
                  undefined(0),
                  exp5(1),
                  exp6(2),
                  exp7(3),
                  exp8(4),
                  exp9(5)
                }

FspR7BERThresholdCaps ::= TEXTUAL-CONVENTION
  STATUS        current
  DESCRIPTION                                                    
         "Bit-Error-Based Degradation Definition for SONET (standard integration period)" 
  SYNTAX        BITS
                {
                  capUndefined(0),
                  capExp5(1),
                  capExp6(2),
                  capExp7(3),
                  capExp8(4),
                  capExp9(5)
                }

FspR7Bitrate ::= TEXTUAL-CONVENTION
  STATUS        current
  DESCRIPTION                                                    
         "Provisioned data rate" 
  SYNTAX        INTEGER
                {
                  undefined(0),
                  bitrate10(1),
                  bitrate100(2)
                }

FspR7BitrateCaps ::= TEXTUAL-CONVENTION
  STATUS        current
  DESCRIPTION                                                    
         "Provisioned data rate" 
  SYNTAX        BITS
                {
                  capUndefined(0),
                  capBitrate10(1),
                  capBitrate100(2)
                }

FspR7ChannelIdentifier ::= TEXTUAL-CONVENTION
  STATUS        current
  DESCRIPTION                                                    
         "Channel" 
  SYNTAX        INTEGER
                {
                  undefined(0),
                  d01(1),
                  d02(2),
                  d03(3),
                  d04(4),
                  d05(5),
                  d06(6),
                  d07(7),
                  d08(8),
                  d09(9),
                  d10(10),
                  d11(11),
                  d12(12),
                  d13(13),
                  d14(14),
                  d15(15),
                  d16(16),
                  d17(17),
                  d18(18),
                  d19(19),
                  d20(20),
                  d21(21),
                  d22(22),
                  d23(23),
                  d24(24),
                  d25(25),
                  d26(26),
                  d27(27),
                  d28(28),
                  d29(29),
                  d30(30),
                  d31(31),
                  d32(32),
                  d33(33),
                  d34(34),
                  d35(35),
                  d36(36),
                  d37(37),
                  d38(38),
                  d39(39),
                  d40(40),
                  d41(41),
                  d42(42),
                  d43(43),
                  d44(44),
                  d45(45),
                  d46(46),
                  d47(47),
                  d48(48),
                  d49(49),
                  d50(50),
                  d51(51),
                  d52(52),
                  d53(53),
                  d54(54),
                  d55(55),
                  d56(56),
                  d57(57),
                  d58(58),
                  d59(59),
                  d60(60),
                  d61(61),
                  d62(62),
                  d63(63),
                  d64(64),
                  dc1(65),
                  dc2(66),
                  dc3(67),
                  dc4(68),
                  dc5(69),
                  dc6(70),
                  dc7(71),
                  dc8(72),
                  dl1(73),
                  dl2(74),
                  dl3(75),
                  dl4(76),
                  dl5(77),
                  dl6(78),
                  dl7(79),
                  dl8(80),
                  c1470(91),
                  c1490(92),
                  c1510(93),
                  c1530(94),
                  c1550(95),
                  c1570(96),
                  c1590(97),
                  c1610(98),
                  s1310(99),
                  s1630(100),
                  g850(101),
                  g1310(102),
                  g1550(103),
                  any(104),
                  notInGrid(105),
                  s1510(106)
                }

FspR7ChannelIdentifierCaps ::= TEXTUAL-CONVENTION
  STATUS        current
  DESCRIPTION                                                    
         "Channel" 
  SYNTAX        BITS
                {
                  capUndefined(0),
                  capD01(1),
                  capD02(2),
                  capD03(3),
                  capD04(4),
                  capD05(5),
                  capD06(6),
                  capD07(7),
                  capD08(8),
                  capD09(9),
                  capD10(10),
                  capD11(11),
                  capD12(12),
                  capD13(13),
                  capD14(14),
                  capD15(15),
                  capD16(16),
                  capD17(17),
                  capD18(18),
                  capD19(19),
                  capD20(20),
                  capD21(21),
                  capD22(22),
                  capD23(23),
                  capD24(24),
                  capD25(25),
                  capD26(26),
                  capD27(27),
                  capD28(28),
                  capD29(29),
                  capD30(30),
                  capD31(31),
                  capD32(32),
                  capD33(33),
                  capD34(34),
                  capD35(35),
                  capD36(36),
                  capD37(37),
                  capD38(38),
                  capD39(39),
                  capD40(40),
                  capD41(41),
                  capD42(42),
                  capD43(43),
                  capD44(44),
                  capD45(45),
                  capD46(46),
                  capD47(47),
                  capD48(48),
                  capD49(49),
                  capD50(50),
                  capD51(51),
                  capD52(52),
                  capD53(53),
                  capD54(54),
                  capD55(55),
                  capD56(56),
                  capD57(57),
                  capD58(58),
                  capD59(59),
                  capD60(60),
                  capD61(61),
                  capD62(62),
                  capD63(63),
                  capD64(64),
                  capDc1(65),
                  capDc2(66),
                  capDc3(67),
                  capDc4(68),
                  capDc5(69),
                  capDc6(70),
                  capDc7(71),
                  capDc8(72),
                  capDl1(73),
                  capDl2(74),
                  capDl3(75),
                  capDl4(76),
                  capDl5(77),
                  capDl6(78),
                  capDl7(79),
                  capDl8(80),
                  capC1470(91),
                  capC1490(92),
                  capC1510(93),
                  capC1530(94),
                  capC1550(95),
                  capC1570(96),
                  capC1590(97),
                  capC1610(98),
                  capS1310(99),
                  capS1630(100),
                  capG850(101),
                  capG1310(102),
                  capG1550(103),
                  capAny(104),
                  capNotInGrid(105),
                  capS1510(106)
                }

FspR7ConnectorType ::= TEXTUAL-CONVENTION
  STATUS        current
  DESCRIPTION                                                    
         "Connector Type" 
  SYNTAX        INTEGER
                {
                  undefined(0),
                  lc(1),
                  rj45(2),
                  mupc(3),
                  dsub8(4),
                  usbS(5)
                }

FspR7ConnectorTypeCaps ::= TEXTUAL-CONVENTION
  STATUS        current
  DESCRIPTION                                                    
         "Connector Type" 
  SYNTAX        BITS
                {
                  capUndefined(0),
                  capLc(1),
                  capRj45(2),
                  capMupc(3),
                  capDsub8(4),
                  capUsbS(5)
                }

FspR7DatabaseType ::= TEXTUAL-CONVENTION
  STATUS        current
  DESCRIPTION                                                    
         "this shows whether the system is running on a temporary auxiliary DB or on the DB in ACT, which is the normal situation" 
  SYNTAX        INTEGER
                {
                  undefined(0),
                  auxiliary(1),
                  normal(2)
                }

FspR7Date ::= TEXTUAL-CONVENTION
  DISPLAY-HINT "2d-1d-1d"
  STATUS        current
  DESCRIPTION                                                    
         "A date specification.
         
         field octets contents range
         ----- ------ -------- -----
         1 1-2 year* 0..65536
         2 3 month 1..12
         3 4 day 1..31
         
         * Notes:
         - the value of year is in network-byte order
         
         For example, Tuesday May 26, 1992 would be
         displayed as:
         
         1992-5-26" 
  SYNTAX        OCTET STRING (SIZE(4))

FspR7DeploymentScenario ::= TEXTUAL-CONVENTION
  STATUS        current
  DESCRIPTION                                                    
         "Describes how the card is applied related to a network scenario" 
  SYNTAX        INTEGER
                {
                  undefined(0),
                  generic(1),
                  backToBack(2),
                  clientProt(3),
                  passThrough(4)
                }

FspR7DeploymentScenarioCaps ::= TEXTUAL-CONVENTION
  STATUS        current
  DESCRIPTION                                                    
         "Describes how the card is applied related to a network scenario" 
  SYNTAX        BITS
                {
                  capUndefined(0),
                  capGeneric(1),
                  capBackToBack(2),
                  capClientProt(3),
                  capPassThrough(4)
                }

FspR7EdfaOutputPowerRating ::= TEXTUAL-CONVENTION
  STATUS        current
  DESCRIPTION                                                    
         "Optical Output Power Rating - Inventory" 
  SYNTAX        INTEGER
                {
                  undefined(0),
                  pwrOut10(1),
                  pwrOut17(2),
                  pwrOut18(3),
                  pwrOut20(4),
                  pwrOut15(5)
                }

FspR7EdfaOutputPowerRatingCaps ::= TEXTUAL-CONVENTION
  STATUS        current
  DESCRIPTION                                                    
         "Optical Output Power Rating - Inventory" 
  SYNTAX        BITS
                {
                  capUndefined(0),
                  capPwrOut10(1),
                  capPwrOut17(2),
                  capPwrOut18(3),
                  capPwrOut20(4),
                  capPwrOut15(5)
                }

FspR7EntitySecondaryStates ::= TEXTUAL-CONVENTION
  STATUS        current
  DESCRIPTION                                                    
         "Variable for representing the secondary states of an entity." 
  SYNTAX        BITS
                {
                  ueq(0),
                  meaState(1),
                  sgeo(2),
                  lpbkState(3),
                  lkdo(4),
                  frcdState(5),
                  faf(6),
                  flt(7),
                  act(8),
                  stbyh(9),
                  psi(10),
                  pri(11),
                  dgn(12),
                  busy(13),
                  idleState(14)
                }

FspR7EntityType ::= TEXTUAL-CONVENTION
  STATUS        current
  DESCRIPTION                                                    
         "" 
  SYNTAX        INTEGER
                {
                  undefined(0),
                  eqpSh1hu(1),
                  eqpSh1huDc(2),
                  eqpSh3hu(3),
                  eqpSh7hu(4),
                  eqpF2kSh5hu(5),
                  eqpF2kSh6hu(6),
                  eqpUnknown(19),
                  eqpNcu(20),
                  eqpNcutif(21),
                  eqpScu(22),
                  eqpScue(23),
                  eqpR6cu(24),
                  eqpPsu1huac(25),
                  eqpPsu7huac(26),
                  eqpPsu7hudc(27),
                  eqpFcu7hu(28),
                  eqp2clsmd(29),
                  eqp2absmc(30),
                  eqp2bsmd(31),
                  eqp1Gsmud(32),
                  eqp4gsmd(33),
                  eqp8gsmd(34),
                  eqp1csmuc(35),
                  eqp1csmuewc(36),
                  eqp4csmd(37),
                  eqp4csmud(38),
                  eqp4csmc(39),
                  eqpOsfm(40),
                  eqp1pm(41),
                  eqp2pm(42),
                  eqp40csmd(43),
                  eqpDcm(44),
                  eqpEdfas(45),
                  eqpEdfasgc(46),
                  eqpEdfadgc(47),
                  eqpRaman(48),
                  eqp4tcc2g5(49),
                  eqp4tcc2g5d(50),
                  eqp4tcc10gd(51),
                  eqp4tcc10gc(52),
                  eqpWcc10gd(53),
                  eqpWcc10gc(54),
                  eqpWcc2g7(55),
                  eqpWcc2g7d(56),
                  eqp2tcm2g5(57),
                  eqp2tca2g5(58),
                  eqp8tca10gd(59),
                  eqp8tca10gc(60),
                  eqpWca10gd(61),
                  eqpWca10gc(62),
                  eqp4tca4gd(63),
                  eqp4tca4gc(64),
                  eqpwca2g5(65),
                  eqp4tca1g3d(66),
                  eqp4tca1g3c(67),
                  eqp8tce2g5d(68),
                  eqp8tce2g5c(69),
                  eqpWcelsd(70),
                  eqpWcelsc(71),
                  eqpVsm(72),
                  eqpRsmolm(73),
                  eqpRsmsf(74),
                  eqpOscm(75),
                  eqp2oscm(76),
                  eqpDrm(77),
                  eqpXfpG(78),
                  eqpsfpd(79),
                  eqpSfpc(80),
                  eqpSfpg(81),
                  eqpSfpe(82),
                  eqpSh1hudcm(83),
                  eqpCustomc(84),
                  eqpCustomd(85),
                  eqpPsu1hudc(86),
                  eqpWcc2g7c(87),
                  eqp1csmuEwD(88),
                  eqp1csmuG(89),
                  eqp3BsmC(90),
                  eqp2Tca2g5s(91),
                  eqp8Csmuc(92),
                  eqpEdfaDgcb(93),
                  eqpOscm2n(94),
                  eqp4Tcc10gtd(95),
                  eqp4Tca4g(96),
                  eqpDcg(97),
                  eqp2Tcm2g5d(98),
                  eqp2Tcm2g5c(99),
                  eqpWcm2g5d(100),
                  eqpWcm2g5c(101),
                  eqpEdfmSgc(102),
                  eqpF2kDemiV2(103),
                  eqpPsm955(104),
                  ifTypeOtu1(501),
                  ifTypeOtu2(502),
                  ifType10GbE(503),
                  ifTypeOc192(504),
                  ifTypeOc48(505),
                  ifTypeStm16(506),
                  ifTypeStm64(507),
                  ifType10GFC(508),
                  ifTypeF1062(510),
                  ifTypeF1250(511),
                  ifTypeFC(512),
                  ifTypeF125(513),
                  ifTypeF200(514),
                  ifTypeF9953(515),
                  ifTypeF10312(516),
                  ifTypeF10518(517),
                  ifTypeF2488(518),
                  ifTypeGfpF(519),
                  ifTypeGfpT(520),
                  ifTypeDccL(521),
                  ifTypeDccS(522),
                  ifTypeDccP(523),
                  ifTypeOdu1(524),
                  ifTypeGcc0(525),
                  ifTypeGcc1(526),
                  ifTypeGcc2(527),
                  ifTypeoch(528),
                  ifTypeOm(529),
                  ifTypeOt(534),
                  ifTypeE10or100bt(536),
                  ifTypeE100fx(537),
                  ifTypeCl(538),
                  ifType2GFC(539),
                  ifType2GCL(540),
                  ifType1GbE(541),
                  ifTypeEoc(542),
                  ifTypeSwitch(543),
                  ifTypePassive(544),
                  ifTypeF2500(545),
                  ifTypeSc(546),
                  ifTypeUch(547),
                  ifTypeF155(548),
                  ifTypeF622(549),
                  ifTypeF2125(550),
                  ifTypeF2666(551),
                  ifTypeF2450(552),
                  ifTypeF10709(554),
                  ifTypeF11095(555),
                  ifTypeF11318(556),
                  ifTypeLs(557),
                  ifType4Gfc(558),
                  ifTypeGcc0S(559),
                  ifType2R(560),
                  ifTypePppIp(561),
                  ifTypeLanIp(562),
                  ifTypeSerial(564),
                  ifTypeModem(565),
                  ifTypeAdapt(566),
                  ifTypeAdaptd(567),
                  ifTypeGBEFR(569),
                  ifTypeVc4(570),
                  ifTypeVc3(571),
                  ifTypeSts1(572),
                  ifTypeEdfa(573),
                  ifTypeEdfaMid(574),
                  ifType10Gdw(575),
                  ifTypeOtu2Lan(576),
                  ifTypeOtu1Lan(577),
                  ifTypeOtu1Fc(578),
                  ifTypeOtu1Fc2G(579),
                  grpffpCh(1000),
                  grpffpOm(1001),
                  grpCrsDcn(1002),
                  grpLanDcn(1003),
                  conFanContainer(1101),
                  conModContainer(1102),
                  conPlugContainer(1103)
                }

FspR7EocProtAvailability ::= TEXTUAL-CONVENTION
  STATUS        current
  DESCRIPTION                                                    
         "ECC Protection Availability" 
  SYNTAX        INTEGER
                {
                  undefined(0),
                  no(1),
                  yes(2)
                }

FspR7EquipmentType ::= TEXTUAL-CONVENTION
  STATUS        current
  DESCRIPTION                                                    
         "The type of equipment based on plugged hardware
         (in contrast to TYPE__EQIPMENT). The __UNKNOWN value is to use in the
         case of uneqipped but assigned in database state." 
  SYNTAX        INTEGER
                {
                  undefined(0),
                  eqpSh1hu(1),
                  eqpSh1huDc(2),
                  eqpSh3hu(3),
                  eqpSh7hu(4),
                  eqpF2kSh5hu(5),
                  eqpF2kSh6hu(6),
                  eqpUnknown(19),
                  eqpNcu(20),
                  eqpNcutif(21),
                  eqpScu(22),
                  eqpScue(23),
                  eqpR6cu(24),
                  eqpPsu1huac(25),
                  eqpPsu7huac(26),
                  eqpPsu7hudc(27),
                  eqpFcu7hu(28),
                  eqp2clsmd(29),
                  eqp2absmc(30),
                  eqp2bsmd(31),
                  eqp1Gsmud(32),
                  eqp4gsmd(33),
                  eqp8gsmd(34),
                  eqp1csmuc(35),
                  eqp1csmuewc(36),
                  eqp4csmd(37),
                  eqp4csmud(38),
                  eqp4csmc(39),
                  eqpOsfm(40),
                  eqp1pm(41),
                  eqp2pm(42),
                  eqp40csmd(43),
                  eqpDcm(44),
                  eqpEdfas(45),
                  eqpEdfasgc(46),
                  eqpEdfadgc(47),
                  eqpRaman(48),
                  eqp4tcc2g5(49),
                  eqp4tcc2g5d(50),
                  eqp4tcc10gd(51),
                  eqp4tcc10gc(52),
                  eqpWcc10gd(53),
                  eqpWcc10gc(54),
                  eqpWcc2g7(55),
                  eqpWcc2g7d(56),
                  eqp2tcm2g5(57),
                  eqp2tca2g5(58),
                  eqp8tca10gd(59),
                  eqp8tca10gc(60),
                  eqpWca10gd(61),
                  eqpWca10gc(62),
                  eqp4tca4gd(63),
                  eqp4tca4gc(64),
                  eqpwca2g5(65),
                  eqp4tca1g3d(66),
                  eqp4tca1g3c(67),
                  eqp8tce2g5d(68),
                  eqp8tce2g5c(69),
                  eqpWcelsd(70),
                  eqpWcelsc(71),
                  eqpVsm(72),
                  eqpRsmolm(73),
                  eqpRsmsf(74),
                  eqpOscm(75),
                  eqp2oscm(76),
                  eqpDrm(77),
                  eqpXfpG(78),
                  eqpsfpd(79),
                  eqpSfpc(80),
                  eqpSfpg(81),
                  eqpSfpe(82),
                  eqpSh1hudcm(83),
                  eqpCustomc(84),
                  eqpCustomd(85),
                  eqpPsu1hudc(86),
                  eqpWcc2g7c(87),
                  eqp1csmuEwD(88),
                  eqp1csmuG(89),
                  eqp3BsmC(90),
                  eqp2Tca2g5s(91),
                  eqp8Csmuc(92),
                  eqpEdfaDgcb(93),
                  eqpOscm2n(94),
                  eqp4Tcc10gtd(95),
                  eqp4Tca4g(96),
                  eqpDcg(97),
                  eqp2Tcm2g5d(98),
                  eqp2Tcm2g5c(99),
                  eqpWcm2g5d(100),
                  eqpWcm2g5c(101),
                  eqpEdfmSgc(102),
                  eqpF2kDemiV2(103),
                  eqpPsm955(104)
                }

FspR7EquipmentTypeCaps ::= TEXTUAL-CONVENTION
  STATUS        current
  DESCRIPTION                                                    
         "The type of equipment based on plugged hardware
         (in contrast to TYPE__EQIPMENT). The __UNKNOWN value is to use in the
         case of uneqipped but assigned in database state." 
  SYNTAX        BITS
                {
                  capUndefined(0),
                  capEqpSh1hu(1),
                  capEqpSh1huDc(2),
                  capEqpSh3hu(3),
                  capEqpSh7hu(4),
                  capEqpF2kSh5hu(5),
                  capEqpF2kSh6hu(6),
                  capEqpUnknown(19),
                  capEqpNcu(20),
                  capEqpNcutif(21),
                  capEqpScu(22),
                  capEqpScue(23),
                  capEqpR6cu(24),
                  capEqpPsu1huac(25),
                  capEqpPsu7huac(26),
                  capEqpPsu7hudc(27),
                  capEqpFcu7hu(28),
                  capEqp2clsmd(29),
                  capEqp2absmc(30),
                  capEqp2bsmd(31),
                  capEqp1Gsmud(32),
                  capEqp4gsmd(33),
                  capEqp8gsmd(34),
                  capEqp1csmuc(35),
                  capEqp1csmuewc(36),
                  capEqp4csmd(37),
                  capEqp4csmud(38),
                  capEqp4csmc(39),
                  capEqpOsfm(40),
                  capEqp1pm(41),
                  capEqp2pm(42),
                  capEqp40csmd(43),
                  capEqpDcm(44),
                  capEqpEdfas(45),
                  capEqpEdfasgc(46),
                  capEqpEdfadgc(47),
                  capEqpRaman(48),
                  capEqp4tcc2g5(49),
                  capEqp4tcc2g5d(50),
                  capEqp4tcc10gd(51),
                  capEqp4tcc10gc(52),
                  capEqpWcc10gd(53),
                  capEqpWcc10gc(54),
                  capEqpWcc2g7(55),
                  capEqpWcc2g7d(56),
                  capEqp2tcm2g5(57),
                  capEqp2tca2g5(58),
                  capEqp8tca10gd(59),
                  capEqp8tca10gc(60),
                  capEqpWca10gd(61),
                  capEqpWca10gc(62),
                  capEqp4tca4gd(63),
                  capEqp4tca4gc(64),
                  capEqpwca2g5(65),
                  capEqp4tca1g3d(66),
                  capEqp4tca1g3c(67),
                  capEqp8tce2g5d(68),
                  capEqp8tce2g5c(69),
                  capEqpWcelsd(70),
                  capEqpWcelsc(71),
                  capEqpVsm(72),
                  capEqpRsmolm(73),
                  capEqpRsmsf(74),
                  capEqpOscm(75),
                  capEqp2oscm(76),
                  capEqpDrm(77),
                  capEqpXfpG(78),
                  capEqpsfpd(79),
                  capEqpSfpc(80),
                  capEqpSfpg(81),
                  capEqpSfpe(82),
                  capEqpSh1hudcm(83),
                  capEqpCustomc(84),
                  capEqpCustomd(85),
                  capEqpPsu1hudc(86),
                  capEqpWcc2g7c(87),
                  capEqp1csmuEwD(88),
                  capEqp1csmuG(89),
                  capEqp3BsmC(90),
                  capEqp2Tca2g5s(91),
                  capEqp8Csmuc(92),
                  capEqpEdfaDgcb(93),
                  capEqpOscm2n(94),
                  capEqp4Tcc10gtd(95),
                  capEqp4Tca4g(96),
                  capEqpDcg(97),
                  capEqp2Tcm2g5d(98),
                  capEqp2Tcm2g5c(99),
                  capEqpWcm2g5d(100),
                  capEqpWcm2g5c(101),
                  capEqpEdfmSgc(102),
                  capEqpF2kDemiV2(103),
                  capEqpPsm955(104)
                }

FspR7ErrorFwdMode ::= TEXTUAL-CONVENTION
  STATUS        current
  DESCRIPTION                                                    
         "Determines the reaction in forward direction in response to a LOS on
         the interface on the opposite side of the module: may override
         this behaviour in the interests of laser safety." 
  SYNTAX        INTEGER
                {
                  undefined(0),
                  ais(1),
                  epc(2),
                  idle(3),
                  lsrOff(4),
                  lsrBrk(5)
                }

FspR7ErrorFwdModeCaps ::= TEXTUAL-CONVENTION
  STATUS        current
  DESCRIPTION                                                    
         "Determines the reaction in forward direction in response to a LOS on
         the interface on the opposite side of the module: may override
         this behaviour in the interests of laser safety." 
  SYNTAX        BITS
                {
                  capUndefined(0),
                  capAis(1),
                  capEpc(2),
                  capIdle(3),
                  capLsrOff(4),
                  capLsrBrk(5)
                }

FspR7FecType ::= TEXTUAL-CONVENTION
  STATUS        current
  DESCRIPTION                                                    
         "Forward Error Correction (Only relevant where TYPE = OTU#)" 
  SYNTAX        INTEGER
                {
                  undefined(0),
                  gFec(1),
                  eFec(2),
                  noFec(3),
                  eFec1(4),
                  eFec2(5)
                }

FspR7FecTypeCaps ::= TEXTUAL-CONVENTION
  STATUS        current
  DESCRIPTION                                                    
         "Forward Error Correction (Only relevant where TYPE = OTU#)" 
  SYNTAX        BITS
                {
                  capUndefined(0),
                  capGFec(1),
                  capEFec(2),
                  capNoFec(3),
                  capEFec1(4),
                  capEFec2(5)
                }

FspR7FlowControlMode ::= TEXTUAL-CONVENTION
  STATUS        current
  DESCRIPTION                                                    
         "Flow Control mechanism" 
  SYNTAX        INTEGER
                {
                  undefined(0),
                  none(1),
                  hwControl(2),
                  pause(3)
                }

FspR7FlowControlModeCaps ::= TEXTUAL-CONVENTION
  STATUS        current
  DESCRIPTION                                                    
         "Flow Control mechanism" 
  SYNTAX        BITS
                {
                  capUndefined(0),
                  capNone(1),
                  capHwControl(2),
                  capPause(3)
                }

FspR7ForcedStatus ::= TEXTUAL-CONVENTION
  STATUS        current
  DESCRIPTION                                                    
         "Forced Destroy" 
  SYNTAX        INTEGER
                {
                  undefined(0),
                  active(1),
                  forcedDestroy(2)
                }

FspR7ForcedStatusCaps ::= TEXTUAL-CONVENTION
  STATUS        current
  DESCRIPTION                                                    
         "Forced Destroy" 
  SYNTAX        BITS
                {
                  capUndefined(0),
                  capActive(1),
                  capForcedDestroy(2)
                }

FspR7Gain ::= TEXTUAL-CONVENTION
  STATUS        current
  DESCRIPTION                                                    
         "Gain." 
  SYNTAX        INTEGER
                {
                  undefined(0),
                  gain24(1),
                  gain25(2)
                }

FspR7GainCaps ::= TEXTUAL-CONVENTION
  STATUS        current
  DESCRIPTION                                                    
         "Gain." 
  SYNTAX        BITS
                {
                  capUndefined(0),
                  capGain24(1),
                  capGain25(2)
                }

FspR7InterfaceFunction ::= TEXTUAL-CONVENTION
  STATUS        current
  DESCRIPTION                                                    
         "Interface Function" 
  SYNTAX        INTEGER
                {
                  undefined(0),
                  transport(1),
                  switch(2),
                  edfa(3),
                  super(4),
                  passive(5),
                  active(6)
                }

FspR7InterfaceFunctionCaps ::= TEXTUAL-CONVENTION
  STATUS        current
  DESCRIPTION                                                    
         "Interface Function" 
  SYNTAX        BITS
                {
                  capUndefined(0),
                  capTransport(1),
                  capSwitch(2),
                  capEdfa(3),
                  capSuper(4),
                  capPassive(5),
                  capActive(6)
                }

FspR7InterfaceType ::= TEXTUAL-CONVENTION
  STATUS        current
  DESCRIPTION                                                    
         "The TYPE defines the transport service type as wrapper with wrapper layer termination OR else as payload" 
  SYNTAX        INTEGER
                {
                  undefined(0),
                  ifTypeOtu1(1),
                  ifTypeOtu2(2),
                  ifType10GbE(3),
                  ifTypeOc192(4),
                  ifTypeOc48(5),
                  ifTypeStm16(6),
                  ifTypeStm64(7),
                  ifType10GFC(8),
                  ifTypeF1062(10),
                  ifTypeF1250(11),
                  ifTypeFC(12),
                  ifTypeF125(13),
                  ifTypeF200(14),
                  ifTypeF9953(15),
                  ifTypeF10312(16),
                  ifTypeF10518(17),
                  ifTypeF2488(18),
                  ifTypeGfpF(19),
                  ifTypeGfpT(20),
                  ifTypeDccL(21),
                  ifTypeDccS(22),
                  ifTypeDccP(23),
                  ifTypeOdu1(24),
                  ifTypeGcc0(25),
                  ifTypeGcc1(26),
                  ifTypeGcc2(27),
                  ifTypeoch(28),
                  ifTypeOm(29),
                  ifTypeOt(34),
                  ifTypeE10or100bt(36),
                  ifTypeE100fx(37),
                  ifTypeCl(38),
                  ifType2GFC(39),
                  ifType2GCL(40),
                  ifType1GbE(41),
                  ifTypeEoc(42),
                  ifTypeSwitch(43),
                  ifTypePassive(44),
                  ifTypeF2500(45),
                  ifTypeSc(46),
                  ifTypeUch(47),
                  ifTypeF155(48),
                  ifTypeF622(49),
                  ifTypeF2125(50),
                  ifTypeF2666(51),
                  ifTypeF2450(52),
                  ifTypeF10709(54),
                  ifTypeF11095(55),
                  ifTypeF11318(56),
                  ifTypeLs(57),
                  ifType4Gfc(58),
                  ifTypeGcc0S(59),
                  ifType2R(60),
                  ifTypePppIp(61),
                  ifTypeLanIp(62),
                  ifTypeSerial(64),
                  ifTypeModem(65),
                  ifTypeAdapt(66),
                  ifTypeAdaptd(67),
                  ifTypeGBEFR(69),
                  ifTypeVc4(70),
                  ifTypeVc3(71),
                  ifTypeSts1(72),
                  ifTypeEdfa(73),
                  ifTypeEdfaMid(74),
                  ifType10Gdw(75),
                  ifTypeOtu2Lan(76),
                  ifTypeOtu1Lan(77),
                  ifTypeOtu1Fc(78),
                  ifTypeOtu1Fc2G(79)
                }

FspR7InterfaceTypeCaps ::= TEXTUAL-CONVENTION
  STATUS        current
  DESCRIPTION                                                    
         "The TYPE defines the transport service type as wrapper with wrapper layer termination OR else as payload" 
  SYNTAX        BITS
                {
                  capUndefined(0),
                  capIfTypeOtu1(1),
                  capIfTypeOtu2(2),
                  capIfType10GbE(3),
                  capIfTypeOc192(4),
                  capIfTypeOc48(5),
                  capIfTypeStm16(6),
                  capIfTypeStm64(7),
                  capIfType10GFC(8),
                  capIfTypeF1062(10),
                  capIfTypeF1250(11),
                  capIfTypeFC(12),
                  capIfTypeF125(13),
                  capIfTypeF200(14),
                  capIfTypeF9953(15),
                  capIfTypeF10312(16),
                  capIfTypeF10518(17),
                  capIfTypeF2488(18),
                  capIfTypeGfpF(19),
                  capIfTypeGfpT(20),
                  capIfTypeDccL(21),
                  capIfTypeDccS(22),
                  capIfTypeDccP(23),
                  capIfTypeOdu1(24),
                  capIfTypeGcc0(25),
                  capIfTypeGcc1(26),
                  capIfTypeGcc2(27),
                  capIfTypeoch(28),
                  capIfTypeOm(29),
                  capIfTypeOt(34),
                  capIfTypeE10or100bt(36),
                  capIfTypeE100fx(37),
                  capIfTypeCl(38),
                  capIfType2GFC(39),
                  capIfType2GCL(40),
                  capIfType1GbE(41),
                  capIfTypeEoc(42),
                  capIfTypeSwitch(43),
                  capIfTypePassive(44),
                  capIfTypeF2500(45),
                  capIfTypeSc(46),
                  capIfTypeUch(47),
                  capIfTypeF155(48),
                  capIfTypeF622(49),
                  capIfTypeF2125(50),
                  capIfTypeF2666(51),
                  capIfTypeF2450(52),
                  capIfTypeF10709(54),
                  capIfTypeF11095(55),
                  capIfTypeF11318(56),
                  capIfTypeLs(57),
                  capIfType4Gfc(58),
                  capIfTypeGcc0S(59),
                  capIfType2R(60),
                  capIfTypePppIp(61),
                  capIfTypeLanIp(62),
                  capIfTypeSerial(64),
                  capIfTypeModem(65),
                  capIfTypeAdapt(66),
                  capIfTypeAdaptd(67),
                  capIfTypeGBEFR(69),
                  capIfTypeVc4(70),
                  capIfTypeVc3(71),
                  capIfTypeSts1(72),
                  capIfTypeEdfa(73),
                  capIfTypeEdfaMid(74),
                  capIfType10Gdw(75),
                  capIfTypeOtu2Lan(76),
                  capIfTypeOtu1Lan(77),
                  capIfTypeOtu1Fc(78),
                  capIfTypeOtu1Fc2G(79)
                }

FspR7Interger32Caps ::= TEXTUAL-CONVENTION
  STATUS        current
  DESCRIPTION                                                    
         "A FspR7Interger32Caps specification.
         1..4 bytes - minValue(Interger32),
         5..8 bytes - maxValue(Interger32).
        " 
  SYNTAX        OCTET STRING (SIZE(0..8))

FspR7LaserForcedOperation ::= TEXTUAL-CONVENTION
  STATUS        current
  DESCRIPTION                                                    
         "FspR7LaserForcedOperation variable." 
  SYNTAX        INTEGER
                {
                  undefined(0),
                  release(1),
                  operate(2)
                }

FspR7LaserOffDelayTime ::= TEXTUAL-CONVENTION
  STATUS        current
  DESCRIPTION                                                    
         "Hold-Off Period for Error Forwarding LKDO-OFF Consequent Action." 
  SYNTAX        INTEGER
                {
                  undefined(0),
                  del0ms(1),
                  del10ms(2),
                  del250ms(3)
                }

FspR7LaserOffDelayTimeCaps ::= TEXTUAL-CONVENTION
  STATUS        current
  DESCRIPTION                                                    
         "Hold-Off Period for Error Forwarding LKDO-OFF Consequent Action." 
  SYNTAX        BITS
                {
                  capUndefined(0),
                  capDel0ms(1),
                  capDel10ms(2),
                  capDel250ms(3)
                }

FspR7ModeDbInit ::= TEXTUAL-CONVENTION
  STATUS        current
  DESCRIPTION                                                    
         "Mode of Database Initialisation at Time of Last Start / Restart" 
  SYNTAX        INTEGER
                {
                  undefined(0),
                  none(1),
                  restore(2),
                  startUpDefault(3),
                  startUpEqpt(4)
                }

FspR7Model ::= TEXTUAL-CONVENTION
  STATUS        current
  DESCRIPTION                                                    
         "Marketing model name of System" 
  SYNTAX        INTEGER
                {
                  undefined(0),
                  fsp3000R7(1),
                  flashwave74200(2)
                }

FspR7NeType ::= TEXTUAL-CONVENTION
  STATUS        current
  DESCRIPTION                                                    
         "Type of Network Element" 
  SYNTAX        INTEGER
                {
                  undefined(0),
                  wdm(1)
                }

FspR7NoYes ::= TEXTUAL-CONVENTION
  STATUS        current
  DESCRIPTION                                                    
         "NoYes variable." 
  SYNTAX        INTEGER
                {
                  undefined(0),
                  no(1),
                  yes(2)
                }

FspR7NoYesCaps ::= TEXTUAL-CONVENTION
  STATUS        current
  DESCRIPTION                                                    
         "If Y then a default router entry with thid PPPIP as gateway will be set in the routing table if no default router is present yet. It can be enabled on multiple PPPIP instances. But this were an unlogical configuration." 
  SYNTAX        BITS
                {
                  capUndefined(0),
                  capNo(1),
                  capYes(2)
                }

FspR7OperState ::= TEXTUAL-CONVENTION
  STATUS        current
  DESCRIPTION                                                    
         "The Operational State will be displayed on the
         GUI with full name values; it will be differently
         displayed in TL1 syntax according to TL1 display rules." 
  SYNTAX        INTEGER
                {
                  undefined(0),
                  nr(1),
                  anr(2),
                  out(3),
                  un(4)
                }

FspR7OpticalBand ::= TEXTUAL-CONVENTION
  STATUS        current
  DESCRIPTION                                                    
         "OM Band - Inventory. BAND__PROVISION references to this." 
  SYNTAX        INTEGER
                {
                  undefined(0),
                  bandC(1),
                  bandL(2),
                  bandA(3),
                  bandB(4),
                  bandAny(5)
                }

FspR7OpticalBandCaps ::= TEXTUAL-CONVENTION
  STATUS        current
  DESCRIPTION                                                    
         "OM Band - Inventory. BAND__PROVISION references to this." 
  SYNTAX        BITS
                {
                  capUndefined(0),
                  capBandC(1),
                  capBandL(2),
                  capBandA(3),
                  capBandB(4),
                  capBandAny(5)
                }

FspR7OpticalFiberType ::= TEXTUAL-CONVENTION
  STATUS        current
  DESCRIPTION                                                    
         "Fiber of Optical Interface - Inventory. FIBER references to this." 
  SYNTAX        INTEGER
                {
                  undefined(0),
                  singleMode(1),
                  multiMode(2),
                  any(3)
                }

FspR7OpticalFiberTypeCaps ::= TEXTUAL-CONVENTION
  STATUS        current
  DESCRIPTION                                                    
         "Fiber of Optical Interface - Inventory. FIBER references to this." 
  SYNTAX        BITS
                {
                  capUndefined(0),
                  capSingleMode(1),
                  capMultiMode(2),
                  capAny(3)
                }

FspR7OpticalGroup ::= TEXTUAL-CONVENTION
  STATUS        current
  DESCRIPTION                                                    
         "Channel Group read from the hardware" 
  SYNTAX        INTEGER
                {
                  undefined(0),
                  d01d04(1),
                  d05d08(2),
                  d09d12(3),
                  d13d16(4),
                  d17d20(5),
                  d21d24(6),
                  d25d28(7),
                  d29d32(8),
                  d33d36(9),
                  d37d40(10),
                  d41d44(11),
                  d45d48(12),
                  d49d52(13),
                  d53d56(14),
                  d57d60(15),
                  d61d64(16),
                  any(17)
                }

FspR7OpticalGroupCaps ::= TEXTUAL-CONVENTION
  STATUS        current
  DESCRIPTION                                                    
         "Channel Group read from the hardware" 
  SYNTAX        BITS
                {
                  capUndefined(0),
                  capD01d04(1),
                  capD05d08(2),
                  capD09d12(3),
                  capD13d16(4),
                  capD17d20(5),
                  capD21d24(6),
                  capD25d28(7),
                  capD29d32(8),
                  capD33d36(9),
                  capD37d40(10),
                  capD41d44(11),
                  capD45d48(12),
                  capD49d52(13),
                  capD53d56(14),
                  capD57d60(15),
                  capD61d64(16),
                  capAny(17)
                }

FspR7OpticalInterfaceReach ::= TEXTUAL-CONVENTION
  STATUS        current
  DESCRIPTION                                                    
         "Reach" 
  SYNTAX        INTEGER
                {
                  undefined(0),
                  intra(1),
                  short(2),
                  long(4),
                  vlong(5),
                  ulong(6),
                  reg(7),
                  xlong(8)
                  -- any(9)
                }

FspR7OpticalInterfaceReachCaps ::= TEXTUAL-CONVENTION
  STATUS        current
  DESCRIPTION                                                    
         "Reach" 
  SYNTAX        BITS
                {
                  capUndefined(0),
                  capIntra(1),
                  capShort(2),
                  capLong(4),
                  capVlong(5),
                  capUlong(6),
                  capReg(7),
                  capXlong(8)
                  -- capAny(9)
                }

FspR7OpticalMultiplexLevel ::= TEXTUAL-CONVENTION
  STATUS        current
  DESCRIPTION                                                    
         "Optical Multiplex Level" 
  SYNTAX        INTEGER
                {
                  undefined(0),
                  levelOm1D(1),
                  levelOm1C(2),
                  levelOm4D(3),
                  levelOm4C(4),
                  levelOm16D(5),
                  levelOm32D(6),
                  levelOm40D(7),
                  levelOmC(9),
                  levelOmD(10),
                  levelOtD(11),
                  levelOtC(12),
                  levelOt(13)
                }

FspR7OpticalSubBand ::= TEXTUAL-CONVENTION
  STATUS        current
  DESCRIPTION                                                    
         "Subband - Inventory" 
  SYNTAX        INTEGER
                {
                  undefined(0),
                  d01d16(1),
                  d17d32(2),
                  d33d48(3),
                  d49d64(4),
                  subBandAny(5)
                }

FspR7OpticalSubBandCaps ::= TEXTUAL-CONVENTION
  STATUS        current
  DESCRIPTION                                                    
         "Subband - Inventory" 
  SYNTAX        BITS
                {
                  capUndefined(0),
                  capD01d16(1),
                  capD17d32(2),
                  capD33d48(3),
                  capD49d64(4),
                  capSubBandAny(5)
                }

FspR7OtdrPeriod ::= TEXTUAL-CONVENTION
  STATUS        current
  DESCRIPTION                                                    
         "NONE - OTDR measurement disabled otherwise the OTDR duration in minutes." 
  SYNTAX        INTEGER
                {
                  undefined(0),
                  periodNone(1),
                  period5ms(2),
                  period20ms(3),
                  period40ms(4),
                  period60ms(5)
                }

FspR7ParityBit ::= TEXTUAL-CONVENTION
  STATUS        current
  DESCRIPTION                                                    
         "Parity Bit Settings" 
  SYNTAX        INTEGER
                {
                  undefined(0),
                  no(1)
                }

FspR7PlugDataRate ::= TEXTUAL-CONVENTION
  STATUS        current
  DESCRIPTION                                                    
         "Rate" 
  SYNTAX        INTEGER
                {
                  undefined(0),
                  rateCouplingLink(1),
                  rateHighSpeed(2),
                  rateGBe(3),
                  rate2G1(4),
                  rate2G5(5),
                  rate4G(6),
                  rate10G(7),
                  any(8),
                  rate11G(9)
                }

FspR7PlugDataRateCaps ::= TEXTUAL-CONVENTION
  STATUS        current
  DESCRIPTION                                                    
         "Rate" 
  SYNTAX        BITS
                {
                  capUndefined(0),
                  capRateCouplingLink(1),
                  capRateHighSpeed(2),
                  capRateGBe(3),
                  capRate2G1(4),
                  capRate2G5(5),
                  capRate4G(6),
                  capRate10G(7),
                  capAny(8),
                  capRate11G(9)
                }

FspR7PortBehaviour ::= TEXTUAL-CONVENTION
  STATUS        current
  DESCRIPTION                                                    
         "Interface Behaviour" 
  SYNTAX        INTEGER
                {
                  undefined(0),
                  client(1),
                  network(2)
                }

FspR7PortBehaviourCaps ::= TEXTUAL-CONVENTION
  STATUS        current
  DESCRIPTION                                                    
         "Interface Behaviour" 
  SYNTAX        BITS
                {
                  capUndefined(0),
                  capClient(1),
                  capNetwork(2)
                }

FspR7PreferredFacilityType ::= TEXTUAL-CONVENTION
  STATUS        current
  DESCRIPTION                                                    
         "Default type of facility model to use for automatically created
         facilities. SDH will cause STM64, STM16, VC4, VC3 type
         facilities to be auto-created. SONET will cause OC192,
         OC48 and STS1 type facilities to be auto-created." 
  SYNTAX        INTEGER
                {
                  undefined(0),
                  sdh(1),
                  sonet(2)
                }

FspR7ProtectionRole ::= TEXTUAL-CONVENTION
  STATUS        current
  DESCRIPTION                                                    
         "The Path is Labelled Working or Protection" 
  SYNTAX        INTEGER
                {
                  undefined(0),
                  wkg(1),
                  protn(2),
                  na(3)
                }

FspR7ProtectionType ::= TEXTUAL-CONVENTION
  STATUS        current
  DESCRIPTION                                                    
         "This describes the topology and level of the protection (OCH or
         OM -Level on a ring; Line in PT-PT and Line or Dualhomed on a Feeder)." 
  SYNTAX        INTEGER
                {
                  undefined(0),
                  dpring(1),
                  line(2)
                }

FspR7ProtectionTypeCaps ::= TEXTUAL-CONVENTION
  STATUS        current
  DESCRIPTION                                                    
         "This describes the topology and level of the protection (OCH or
         OM -Level on a ring; Line in PT-PT and Line or Dualhomed on a Feeder)." 
  SYNTAX        BITS
                {
                  capUndefined(0),
                  capDpring(1),
                  capLine(2)
                }

FspR7RowStatusCaps ::= TEXTUAL-CONVENTION
  STATUS        current
  DESCRIPTION                                                    
         "RowStatus" 
  SYNTAX        BITS
                {
                  capUndefined(0),
                  capActive(1),
                  capNotInService(2),
                  capNotReady(3),
                  capCreateAndGo(4),
                  capCreateAndWait(5),
                  capDestroy(6)
                }

FspR7SignalMapping ::= TEXTUAL-CONVENTION
  STATUS        current
  DESCRIPTION                                                    
         "Mapping of Client Signal into some other format" 
  SYNTAX        INTEGER
                {
                  undefined(0),
                  gfp(1),
                  proprietary(2)
                }

FspR7SignalMappingCaps ::= TEXTUAL-CONVENTION
  STATUS        current
  DESCRIPTION                                                    
         "Mapping of Client Signal into some other format" 
  SYNTAX        BITS
                {
                  capUndefined(0),
                  capGfp(1),
                  capProprietary(2)
                }

FspR7StandingConditionTypes ::= TEXTUAL-CONVENTION
  STATUS        current
  DESCRIPTION                                                    
         "List of all alarms" 
  SYNTAX        INTEGER
                {
                  undefined(0),
                  thirdPartyPlug(1001),
                  facilityLoopback(1002),
                  terminalLoopback(1003),
                  facilityForcedOn(1004),
                  oosDisabled(1005),
                  receiverDisabled(1006),
                  transmitterDisabledOff(1007),
                  transmittedDisabledIdle(1008),
                  transmitterDisabledAis(1009),
                  transmitterDisabledEpc(1010),
                  oosManagement(1011),
                  oosMaintenance(1012),
                  oosAins(1013),
                  dcnCommunicationFail(1014),
                  removed(1015),
                  mismatch(1016),
                  equipmentNotAccepted(1017),
                  facilityDataRateNotSupported(1018),
                  equipmentNotSupportedByPhysicalLayer(1019),
                  equipmentNotApproved(1020),
                  equipmentMismatch(1021),
                  fuseAlarm1(1022),
                  fuseAlarm2(1023),
                  fanAlarm(1024),
                  fanUnitAlarm(1025),
                  powerMissing(1026),
                  -- powerFailure(1027),
                  voltageTooLow(1028),
                  voltageTooHigh(1029),
                  temperatureTooLow(1030),
                  temperatureTooHigh(1031),
                  -- receiverFailure(1032),
                  -- opticalInputPowerReceiverFailure(1033),
                  lossOfSignal(1034),
                  idleSignalReceived(1035),
                  lossOfLinkPulse(1036),
                  lossOfReceiverClockRecovery(1037),
                  elasticStoreOverflowReceiver(1038),
                  lossOfTransmitterClockRecovery(1039),
                  laserFailure(1040),
                  switchFailed(1041),
                  elasticStoreOverflowTransmitter(1042),
                  autoShutdownLaserOffDueToErrFwd(1043),
                  autoShutdown(1044),
                  autoShutdownAls(1045),
                  -- autoShutdownSendingIdle(1046),
                  thermoElectricCoolerEndOfLife(1047),
                  opticalInputPwrReceivedTooLow(1048),
                  opticalInputPwrReceivedTooHigh(1049),
                  laserTemperatureTooHigh(1050),
                  laserTemperatureTooLow(1051),
                  opticalOutputPowerTransmittedTooLow(1052),
                  opticalOutputPowerTransmittedTooHigh(1053),
                  laserBiasCurrentNormalizedtooHigh(1054),
                  lossOfSignalTransmitter(1055),
                  attOnReceiverFiberLowerThanMonitor(1056),
                  attOnReceiverFiberHigherThanMonitor(1057),
                  attOnTransmitterFiberLowerThanMonitor(1058),
                  attOnTransmitterFiberHigherThanMonitor(1059),
                  autoShutdownSendingAisOtu(1060),
                  lossOfFrameOtu(1061),
                  lossOfMultiFrameOtu(1062),
                  alarmIndicationSignalOtu(1063),
                  signalDegradeOtu(1064),
                  backwardDefectIndicationOtu(1065),
                  autoShutdownSendingAisOdu(1066),
                  lossOfFrameLossOfMultiFrameOdu(1067),
                  alarmIndicationSignalOdu(1068),
                  openConnectionIndicationOdu(1069),
                  lockedDefectOdu(1070),
                  signalDegradeOdu(1071),
                  backwardDefectIndicationOdu(1072),
                  alarmIndicationSignalOduTcmA(1073),
                  openConnectionIndicationOduTcmA(1074),
                  lockedDefectOduTcmA(1075),
                  lossofTandemConnectionOduTcmA(1076),
                  signalDegradeOduTcmA(1077),
                  backwardDefectIndicationOduTcmA(1078),
                  payloadMismatchOPU(1079),
                  multiplexStructureIdentifierMismatchOPU(1080),
                  lossOfFrame(1081),
                  sectionSignalFailure(1082),
                  autoShutdownSendingAisLine(1083),
                  alarmIndicationSignalLine(1084),
                  remoteDefectIndicationLine(1085),
                  signalDegradeLine(1086),
                  alarmIndicationSignalHigherOrderPath(1087),
                  lossOfPointerHigherOrderPath(1088),
                  lossofMultiframeHigherOrderPath(1089),
                  lossofSequenceHigherOrderPath(1090),
                  unequippedHigherOrderPath(1091),
                  payloadMismatchHigherOrderPath(1092),
                  remoteDefectIndicationHigherOrderPath(1093),
                  signalDegradeHigherOrderPath(1094),
                  alarmIndicationSignalLowerOrderPath(1095),
                  lossOfPointerLowerOrderPath(1096),
                  lossofMultiframeLowerOrderPath(1097),
                  lossofSequenceLowerOrderPath(1098),
                  unequippedLowerOrderPath(1099),
                  payloadMismatchLowerOrderPath(1100),
                  remoteDefectIndicationLowerOrderPath(1101),
                  lossOfMultiframeVCG(1102),
                  lossOfSequenceVCG(1103),
                  lossofAlignmentVCG(1104),
                  autoShutdownSendingEPC(1105),
                  thres15MinExceededPhysConvES(1106),
                  thres15MinExceededPhysConvCV(1107),
                  thres15MinExceededPhysConvDE(1108),
                  thres15MinExceededPhysConvCVDE(1109),
                  lossOfGfpFrame(1110),
                  payloadMismatchGfp(1111),
                  gfpLossOfClientSig(1112),
                  lossOfCharSyncFromFarEnd(1113),
                  switchtoProtectionInhibited(1114),
                  switchtoWorkingInhibited(1115),
                  oTDRMeasuringinProgress(1116),
                  protectionNotAvailable(1117),
                  apsConfigMismatch(1118),
                  embeddedOperationsChannelFailure(1119),
                  signalDegradeSection(1120),
                  signalDegradationonLinkVector(1121),
                  signalFailureonLinkVector(1122),
                  inputVoltageFailure(1123),
                  powerSupplyUnitFailure(1124),
                  currentTooLow(1125),
                  currentTooHigh(1126),
                  multipleFanFailure(1127),
                  singleFanFailure(1128),
                  linkDown(1129),
                  voltageOutOfRange(1130),
                  peerLink(1131),
                  hwFailure(1132),
                  alarmIndicationSignalOduTcmB(1133),
                  openConnectionIndicationOduTcmB(1134),
                  lockedDefectOduTcmB(1135),
                  lossofTandemConnectionOduTcmB(1136),
                  signalDegradeOduTcmB(1137),
                  backwardDefectIndicationOduTcmB(1138),
                  apsProtocolFailure(1139),
                  apdLowVoltage(1140),
                  apdHighVoltage(1141),
                  linkControlProtocolFailure(1142),
                  receiverLowTemp(1143),
                  receiverHighTemp(1144),
                  thermoElectricCoolerCurrentTooLow(1145),
                  thermoElectricCoolerCurrentTooHigh(1146),
                  subModuleTempTooHigh(1147),
                  signalDegradeOlm(1148),
                  receiverOverloadProtection(1149),
                  lossOfFrameMux(1150),
                  lossOfFrameMuxFarEnd(1151),
                  lossOfCharSync(1152),
                  thres15MinExceededFecCE(1153),
                  thres15MinExceededFecUBE(1154),
                  thres15MinExceededFecES(1155),
                  thres15MinExceededFecSES(1156),
                  thres15MinExceededMuxES(1157),
                  thres15MinExceededMuxSES(1158),
                  thres15MinExceededGfpCHEC(1159),
                  thres15MinExceededGfpTHEC(1160),
                  thres15MinExceededGfpTHecDisc(1161),
                  thres15MinExceededGfpTsuperblockDisc(1162),
                  -- intrusionRx(1163),
                  -- intrusionTx(1164),
                  autoShutdownLaserOffDueToHighTemp(1165),
                  autoShutdownLaserOffDueToHighTxPwr(1166),
                  laserEndOfLife(1167),
                  laserBiasCurrAbnormal(1168),
                  opticalPowerTxLOS(1169),
                  midstageFault(1170),
                  farEndIpAddressUnknown(1171),
                  topologyDataCalculationInProgress(1172),
                  ntpServer1Unreachable(1173),
                  ntpServer2Unreachable(1174),
                  ntpServer3Unreachable(1175),
                  autoShutdownSendingAisOpu(1176),
                  alarmIndicationSignalOpu(1177),
                  alarmIndicationSignalOduTcmC(1178),
                  backwardDefectIndicationOduTcmC(1179),
                  lockedDefectOduTcmC(1180),
                  lossofTandemConnectionOduTcmC(1181),
                  openConnectionIndicationOduTcmC(1182),
                  signalDegradeOduTcmC(1183),
                  loopbackError(1184)
                }

FspR7SupplyType ::= TEXTUAL-CONVENTION
  STATUS        current
  DESCRIPTION                                                    
         "The kind of power supply - provisioned value" 
  SYNTAX        INTEGER
                {
                  undefined(0),
                  front(1),
                  rear(2)
                }

FspR7SupplyTypeCaps ::= TEXTUAL-CONVENTION
  STATUS        current
  DESCRIPTION                                                    
         "The kind of power supply - provisioned value" 
  SYNTAX        BITS
                {
                  capUndefined(0),
                  capFront(1),
                  capRear(2)
                }

FspR7SysType ::= TEXTUAL-CONVENTION
  STATUS        current
  DESCRIPTION                                                    
         "Type of Network Element" 
  SYNTAX        INTEGER
                {
                  undefined(0),
                  otm(1),
                  oadm(2),
                  converter(3)
                }

FspR7Time ::= TEXTUAL-CONVENTION
  DISPLAY-HINT "1d-1d-1d"
  STATUS        current
  DESCRIPTION                                                    
         "A time specification.
         
         field octets contents range
         ----- ------ -------- -----
         1 1 hour 0..23
         2 2 minutes 0..59
         3 3 seconds 0..60
         (use 60 for leap-second)
         
         
         
         For example:
         13-10-26" 
  SYNTAX        OCTET STRING (SIZE(3))

FspR7TopologyType ::= TEXTUAL-CONVENTION
  STATUS        current
  DESCRIPTION                                                    
         "Monitored Topology Type" 
  SYNTAX        INTEGER
                {
                  undefined(0),
                  lad(1),
                  ring(2),
                  p2p(3),
                  unknown(4)
                }

FspR7TopologyTypeCaps ::= TEXTUAL-CONVENTION
  STATUS        current
  DESCRIPTION                                                    
         "Monitored Topology Type" 
  SYNTAX        BITS
                {
                  capUndefined(0),
                  capLad(1),
                  capRing(2),
                  capP2p(3),
                  capUnknown(4)
                }

FspR7TransmissionMode ::= TEXTUAL-CONVENTION
  STATUS        current
  DESCRIPTION                                                    
         "The transmission mode of the module." 
  SYNTAX        INTEGER
                {
                  undefined(0),
                  trans(1),
                  transE(2),
                  transW(3),
                  transHst(4),
                  mux(5),
                  muxE(6),
                  muxW(7),
                  muxHst(8),
                  regen1Way(9),
                  regen2Way(10),
                  obsolete(11)
                }

FspR7TransmissionModeCaps ::= TEXTUAL-CONVENTION
  STATUS        current
  DESCRIPTION                                                    
         "The transmission mode of the module." 
  SYNTAX        BITS
                {
                  capUndefined(0),
                  capTrans(1),
                  capTransE(2),
                  capTransW(3),
                  capTransHst(4),
                  capMux(5),
                  capMuxE(6),
                  capMuxW(7),
                  capMuxHst(8),
                  capRegen1Way(9),
                  capRegen2Way(10),
                  capObsolete(11)
                }

FspR7TypeConnection ::= TEXTUAL-CONVENTION
  STATUS        current
  DESCRIPTION                                                    
         "Type of equipment connection" 
  SYNTAX        INTEGER
                {
                  undefined(0),
                  connection1Way(1),
                  connection2Way(2)
                }

FspR7TypeConnectionCaps ::= TEXTUAL-CONVENTION
  STATUS        current
  DESCRIPTION                                                    
         "Type of Cross-Connect" 
  SYNTAX        BITS
                {
                  capUndefined(0),
                  capConnection1Way(1),
                  capConnection2Way(2)
                }

FspR7Unsigned32Caps ::= TEXTUAL-CONVENTION
  STATUS        current
  DESCRIPTION                                                    
         "A FspR7Unsigned32Caps specification.
         1..4 bytes - minValue(Unsigned32),
         5..8 bytes - maxValue(Unsigned32).
        " 
  SYNTAX        OCTET STRING (SIZE(0..8))

FspR7YesNo ::= TEXTUAL-CONVENTION
  STATUS        current
  DESCRIPTION                                                    
         "YesNo variable." 
  SYNTAX        INTEGER
                {
                  undefined(0),
                  yes(1),
                  no(2)
                }

FspR7YesNoCaps ::= TEXTUAL-CONVENTION
  STATUS        current
  DESCRIPTION                                                    
         "YesNo capability variable." 
  SYNTAX        BITS
                {
                  capUndefined(0),
                  capYes(1),
                  capNo(2)
                }



-- fspR7MIB 

fspR7V1 OBJECT-IDENTITY
    STATUS current
    DESCRIPTION        
            "This object uniquely identifies a Network Element
       using the current FspR7MIB release. V1 will be used
       for all releases until major changes require a new
       sysObjectID to assure backward compatibility."
    ::= { fspR7Products 1 }


neSystemId OBJECT-TYPE
    SYNTAX      SnmpAdminString
    MAX-ACCESS  read-write
    STATUS      current 
    DESCRIPTION
        "sid description" 
    ::=  { neAdmin 1 }

neSysType OBJECT-TYPE
    SYNTAX      FspR7SysType
    MAX-ACCESS  read-write
    STATUS      current 
    DESCRIPTION
        "Type of Network Element" 
    ::=  { neAdmin 2 }

neAutoProvisioning OBJECT-TYPE
    SYNTAX      FspR7YesNo
    MAX-ACCESS  read-write
    STATUS      current 
    DESCRIPTION
        "Global system variable. Enables or disables athe auto-provisioning functionality." 
    ::=  { neAdmin 3 }

neType OBJECT-TYPE
    SYNTAX      FspR7NeType
    MAX-ACCESS  read-write
    STATUS      current 
    DESCRIPTION
        "Type of Network Element" 
    ::=  { neAdmin 4 }

neSwVersion OBJECT-TYPE
    SYNTAX      SnmpAdminString
    MAX-ACCESS  read-only
    STATUS      current 
    DESCRIPTION
        "Software Version of the NCU software. <x>.<y>[.<z>]" 
    ::=  { neAdmin 5 }

neGradeInventory OBJECT-TYPE
    SYNTAX      Grade
    MAX-ACCESS  read-only
    STATUS      current 
    DESCRIPTION
        "Used to distinguish between NCU capabilities (range of supported services or applications)" 
    ::=  { neAdmin 6 }

neModel OBJECT-TYPE
    SYNTAX      FspR7Model
    MAX-ACCESS  read-only
    STATUS      current 
    DESCRIPTION
        "Marketing model name of System" 
    ::=  { neAdmin 7 }

neVendorId OBJECT-TYPE
    SYNTAX      SnmpAdminString
    MAX-ACCESS  read-only
    STATUS      current 
    DESCRIPTION
        "The name of the manufacturer" 
    ::=  { neAdmin 8 }

neAINSProvEnabled OBJECT-TYPE
    SYNTAX      FspR7YesNo
    MAX-ACCESS  read-write
    STATUS      current 
    DESCRIPTION
        "Global system variable. Automatic IN-Service Provisioning ENAbled flag.
         This value is controlled by settings in the system configuration file.
         If Y, entities which are autoprovisioned will be created with an initial
         state of OOS-AU,AINS. If N, autoprovisioned entities will be created in
         an ISNR state. Entities in an OOS-AU,AINS state will automatically
         transition to an in-service state after a continuous interval
         without any active service affecting conditions. The duration of this
         interval is equal to that given by the AISPDEFTM attribute at the start
         of the continuous interval." 
    ::=  { neAdmin 9 }

neAINSDefaultTimer OBJECT-TYPE
    SYNTAX      Unsigned32 (0..5760)
    UNITS       "Min"
    MAX-ACCESS  read-write
    STATUS      current 
    DESCRIPTION
        "AINS Default Signal Timer. The length of time in minutes
         for which an entity must be free of service affecting conditions in
         order to automatically transition from an OOS-AU,AINS state to
         an inservice state. The value is set via the system configuration file.
         If the value is set to 0, an entity in the OOS-AU,AINS
         state will immediately transition to an in-service state." 
    ::=  { neAdmin 10 }

nePreferredFacilityType OBJECT-TYPE
    SYNTAX      FspR7PreferredFacilityType
    MAX-ACCESS  read-write
    STATUS      current 
    DESCRIPTION
        "Default type of facility model to use for automatically created
         facilities. SDH will cause STM64, STM16, VC4, VC3 type
         facilities to be auto-created. SONET will cause OC192,
         OC48 and STS1 type facilities to be auto-created." 
    ::=  { neAdmin 11 }

neForceDelete OBJECT-TYPE
    SYNTAX      EnableState
    MAX-ACCESS  read-write
    STATUS      current 
    DESCRIPTION
        "Force Delete" 
    ::=  { neAdmin 12 }

neSdhSesThreshold OBJECT-TYPE
    SYNTAX      Unsigned32 (0..100)
    UNITS       "%"
    MAX-ACCESS  read-write
    STATUS      current 
    DESCRIPTION
        "Severely Errorred Seconds percentage for SDH facilities. Sets the
         default relative percentage of Errorred Seconds within a PM interval
         at which Severely Errorred Seconds will be declared." 
    ::=  { neAdmin 14 }

neOtnSesThreshold OBJECT-TYPE
    SYNTAX      Unsigned32 (0..100)
    UNITS       "%"
    MAX-ACCESS  read-write
    STATUS      current 
    DESCRIPTION
        "Severely Errorred Seconds percentage for OTN facilities. Sets the
         default relative percentage of Errorred Seconds within a PM interval
         at which Severely Errorred Seconds will be declared." 
    ::=  { neAdmin 15 }

neTopologyType OBJECT-TYPE
    SYNTAX      FspR7TopologyType
    MAX-ACCESS  read-write
    STATUS      deprecated
    DESCRIPTION
        "Type of monitored topology." 
    ::=  { neAdmin 16 }

neDatabaseSerialNumber OBJECT-TYPE
    SYNTAX      SnmpAdminString
    MAX-ACCESS  read-only
    STATUS      current 
    DESCRIPTION
        "read from Master Shelf and stored in the DB 'once'; only changed when a command which implies a change is given (INIT__SYS with DBSRST = ACCEPT)" 
    ::=  { neAdmin 17 }

neDatabaseType OBJECT-TYPE
    SYNTAX      FspR7DatabaseType
    MAX-ACCESS  read-only
    STATUS      current 
    DESCRIPTION
        "this shows whether the system is running on a temporary auxiliary DB or on the DB in ACT, which is the normal situation" 
    ::=  { neAdmin 18 }

neTimeConfig   OBJECT IDENTIFIER ::= { neAdmin 30 }

neDate OBJECT-TYPE
    SYNTAX      FspR7Date
    MAX-ACCESS  read-write
    STATUS      current 
    DESCRIPTION
        "Get or Set the current date on the Network Element." 
    ::=  { neTimeConfig 1 }

neTime OBJECT-TYPE
    SYNTAX      FspR7Time
    MAX-ACCESS  read-write
    STATUS      current 
    DESCRIPTION
        "Get or Set the current time on the Network Element." 
    ::=  { neTimeConfig 2 }

neTimeZone OBJECT-TYPE
    SYNTAX      SnmpAdminString
    MAX-ACCESS  read-write
    STATUS      current 
    DESCRIPTION
        "Get or Set the timezone on the Network Element." 
    ::=  { neTimeConfig 3 }

neNetworkTimeProtocol OBJECT-TYPE
    SYNTAX      EnableState
    MAX-ACCESS  read-write
    STATUS      current 
    DESCRIPTION
        "This parameter controls whether the Network Time Protocol is enabled or not." 
    ::=  { neTimeConfig 4 }

neNtpServer1 OBJECT-TYPE
    SYNTAX      IpAddress
    MAX-ACCESS  read-write
    STATUS      current 
    DESCRIPTION
        "The IP address of NTP server number 1." 
    ::=  { neTimeConfig 5 }

neNtpServer2 OBJECT-TYPE
    SYNTAX      IpAddress
    MAX-ACCESS  read-write
    STATUS      current 
    DESCRIPTION
        "The IP address of NTP server number 2." 
    ::=  { neTimeConfig 6 }

neNtpServer3 OBJECT-TYPE
    SYNTAX      IpAddress
    MAX-ACCESS  read-write
    STATUS      current 
    DESCRIPTION
        "The IP address of NTP server number 3." 
    ::=  { neTimeConfig 7 }

conditionSeverityTable OBJECT-TYPE
    SYNTAX      SEQUENCE OF ConditionSeverityEntry
    MAX-ACCESS  not-accessible
    STATUS      current 
    DESCRIPTION
        "This table contains a severity value for each defined
         Standing condition reported by an entity in the NE." 
    ::=  { conditionFilters 1 }

conditionSeverityEntry OBJECT-TYPE
    SYNTAX      ConditionSeverityEntry
    MAX-ACCESS  not-accessible
    STATUS      current 
    DESCRIPTION
        "Each entry in the table represents the severity
         assigned to a condition." 
    INDEX       { entityIndex,conditionSeverityType } 
    ::=  { conditionSeverityTable  1  }

ConditionSeverityEntry ::=  SEQUENCE
  { conditionSeverityType FspR7StandingConditionTypes,
    conditionSeverityValue TrapAlarmSeverity }


  
conditionSeverityType OBJECT-TYPE
    SYNTAX      FspR7StandingConditionTypes
    MAX-ACCESS  not-accessible
    STATUS      current 
    DESCRIPTION
        "This object identifies the type of alarm." 
    ::=  { conditionSeverityEntry 1 }

conditionSeverityValue OBJECT-TYPE
    SYNTAX      TrapAlarmSeverity
    MAX-ACCESS  read-write
    STATUS      current 
    DESCRIPTION
        "This object identifies the severity assigned to this
         alarm." 
    ::=  { conditionSeverityEntry 2 }

currentConditionTable OBJECT-TYPE
    SYNTAX      SEQUENCE OF CurrentConditionEntry
    MAX-ACCESS  not-accessible
    STATUS      current 
    DESCRIPTION
        "" 
    ::=  { currentConditions 1 }

currentConditionEntry OBJECT-TYPE
    SYNTAX      CurrentConditionEntry
    MAX-ACCESS  not-accessible
    STATUS      current 
    DESCRIPTION
        "" 
    INDEX       { entityIndex,currentConditionType } 
    ::=  { currentConditionTable  1  }

CurrentConditionEntry ::=  SEQUENCE
  { currentConditionType FspR7StandingConditionTypes,
    currentConditionSeverity TrapAlarmSeverity,
    currentConditionAffect ServiceImpairment,
    currentConditionTimeStamp DateAndTime }


  
currentConditionType OBJECT-TYPE
    SYNTAX      FspR7StandingConditionTypes
    MAX-ACCESS  not-accessible
    STATUS      current 
    DESCRIPTION
        "List of all interface conditions" 
    ::=  { currentConditionEntry 1 }

currentConditionSeverity OBJECT-TYPE
    SYNTAX      TrapAlarmSeverity
    MAX-ACCESS  read-only
    STATUS      current 
    DESCRIPTION
        "List of all interface conditions" 
    ::=  { currentConditionEntry 2 }

currentConditionAffect OBJECT-TYPE
    SYNTAX      ServiceImpairment
    MAX-ACCESS  read-only
    STATUS      current 
    DESCRIPTION
        "This object indicates the service impairment affect of the alarm." 
    ::=  { currentConditionEntry 3 }

currentConditionTimeStamp OBJECT-TYPE
    SYNTAX      DateAndTime
    MAX-ACCESS  read-only
    STATUS      current 
    DESCRIPTION
        "List of all alarms" 
    ::=  { currentConditionEntry 4 }

chassisCreation NOTIFICATION-TYPE 
    OBJECTS     { entityClass,neEventLogTimeStamp,neEventLogIdentityTranslation } 
    STATUS      current 
    DESCRIPTION
        "
         This trap is sent every time a chassis is created. No
         containers or other sub-entities in the chassis are reported
         created by this trap, the NMS must read these data. The trap is
         sent when all the sub-entities are present in the entity just
         created.
         Note: not sent for insertion of NCU chassis, but this is
         instead represented by a coldStart trap.
        " 
    ::=  { trapMibPrefix 2 }

chassisDeletion NOTIFICATION-TYPE 
    OBJECTS     { entityClass,neEventLogTimeStamp,neEventLogIdentityTranslation } 
    STATUS      current 
    DESCRIPTION
        "
         This trap is sent every time a chassis is deleted.
         The sub-entities (containers, modules, etc.) are not reported
         deleted.
         Note: cannot be reported when the NCU chassis
         is removed or fails.
        " 
    ::=  { trapMibPrefix 3 }

entityCreation NOTIFICATION-TYPE 
    OBJECTS     { entityContainedIn,entityClass,neEventLogTimeStamp,neEventLogIdentityTranslation } 
    STATUS      current 
    DESCRIPTION
        "This trap is sent every time an entity is created. No
         containers or other sub-entities in the chassis are reported
         created by this trap, the NMS must read these data." 
    ::=  { trapMibPrefix 4 }

entityDeletion NOTIFICATION-TYPE 
    OBJECTS     { entityClass,neEventLogTimeStamp,neEventLogIdentityTranslation } 
    STATUS      current 
    DESCRIPTION
        "This trap is sent every time an entity is deleted.
         The sub-entities (containers, modules, etc.) are not reported
         deleted." 
    ::=  { trapMibPrefix 5 }

neTrapsinkObjectCreation NOTIFICATION-TYPE 
    OBJECTS     { neTrapsinkAddress,neEventLogTimeStamp,neEventLogIdentityTranslation } 
    STATUS      current 
    DESCRIPTION
        "
         This trap is sent every time a trapsink is created.
        " 
    ::=  { trapMibPrefix 6 }

neTrapsinkObjectDeletion NOTIFICATION-TYPE 
    OBJECTS     { neTrapsinkAddress,neEventLogTimeStamp,neEventLogIdentityTranslation } 
    STATUS      current 
    DESCRIPTION
        "
         This trap is sent every time a trapsink is deleted..
        " 
    ::=  { trapMibPrefix 7 }

equipmentInserted NOTIFICATION-TYPE 
    OBJECTS     { entityClass,neEventLogTimeStamp,neEventLogIdentityTranslation } 
    STATUS      current 
    DESCRIPTION
        "
         This trap is sent every time an equipment is inserted. 
        " 
    ::=  { trapMibPrefix 8 }

equipmentRemoved NOTIFICATION-TYPE 
    OBJECTS     { entityClass,neEventLogTimeStamp,neEventLogIdentityTranslation } 
    STATUS      current 
    DESCRIPTION
        "
         This trap is sent every time an equipment is removed.
        " 
    ::=  { trapMibPrefix 9 }

neStateChange NOTIFICATION-TYPE 
    OBJECTS     { neEventLogTimeStamp,neEventLogIdentityTranslation } 
    STATUS      current 
    DESCRIPTION
        "
         This trap is sent when an network element state is changed.
         Only one state is present in each trap. The first varbind
         will contain one of the following scalar entries:
         neSwUpgradeState (ADVA Common MIB).
        " 
    ::=  { trapMibPrefix 20 }

entityStateChange NOTIFICATION-TYPE 
    OBJECTS     { neEventLogTimeStamp,neEventLogIdentityTranslation } 
    STATUS      current 
    DESCRIPTION
        "
         This trap is sent when an entity state is changed.
         Only one state is present in each trap. The first varbind
         will contain one of the following table entries:
         entityStateAdmin,
         entityStateOper,
         entitySecondaryStates.
        " 
    ::=  { trapMibPrefix 21 }

neSysTypeChanged NOTIFICATION-TYPE 
    OBJECTS     { neSysType,neEventLogTimeStamp } 
    STATUS      current 
    DESCRIPTION
        "
         This trap is sent when changes are detected in the
         nodeTrafficConfig..
        " 
    ::=  { trapMibPrefix 22 }

neAttributeValueChange NOTIFICATION-TYPE 
    OBJECTS     { neEventLogTimeStamp,neEventLogIdentityTranslation } 
    STATUS      current 
    DESCRIPTION
        "
         This trap is sent when an attribute related to the
         Network Element is changed.
         One attribute is present in each trap. The first varbind
         contains one of the following scalar or table entries:
         sysLocation (RFC 1213)
         sysContact (RFC 1213)
         
         neTrapsinkTable (ADVAMIB):
         neTrapsinkCommunity
         neSwUpgradeRequest (ADVAMIB)
         neSwUpgradeServerAddress (ADVAMIB)
         neSwUpgradeServerLogin (ADVAMIB)
         neSwUpgradeServerPasswd (ADVAMIB)
         neSwUpgradeServerDirectory (ADVAMIB)
         neSwUpgradeFileName (ADVAMIB).
        " 
    ::=  { trapMibPrefix 30 }

facilityAttributeValueChange NOTIFICATION-TYPE 
    OBJECTS     { neEventLogTimeStamp,neEventLogIdentityTranslation } 
    STATUS      current 
    DESCRIPTION
        "
         This trap is sent when an attribute related to a facility is changed.
         One attribute is present in each trap. The first varbind
         contains one of the following table entries:
         gfpVchConfigTable,
         gfpVchConfigCir,
        " 
    ::=  { trapMibPrefix 31 }

alarmthirdPartyPlug NOTIFICATION-TYPE 
    OBJECTS     { currentConditionSeverity,currentConditionAffect,neEventLogTimeStamp,neEventLogIdentityTranslation } 
    STATUS      current 
    DESCRIPTION
        "Equipment Accepted by Customer with Voided Warranty" 
    ::=  { trapMibPrefix 1001 }

alarmFacilityLoopback NOTIFICATION-TYPE 
    OBJECTS     { currentConditionSeverity,currentConditionAffect,neEventLogTimeStamp,neEventLogIdentityTranslation } 
    STATUS      current 
    DESCRIPTION
        "External(Line) Loopback on Interface" 
    ::=  { trapMibPrefix 1002 }

alarmTerminalLoopback NOTIFICATION-TYPE 
    OBJECTS     { currentConditionSeverity,currentConditionAffect,neEventLogTimeStamp,neEventLogIdentityTranslation } 
    STATUS      current 
    DESCRIPTION
        "Inward Loopback on Interface" 
    ::=  { trapMibPrefix 1003 }

alarmFacilityForcedOn NOTIFICATION-TYPE 
    OBJECTS     { currentConditionSeverity,currentConditionAffect,neEventLogTimeStamp,neEventLogIdentityTranslation } 
    STATUS      current 
    DESCRIPTION
        "Laser or Switch forced ON" 
    ::=  { trapMibPrefix 1004 }

alarmOosDisabled NOTIFICATION-TYPE 
    OBJECTS     { currentConditionSeverity,currentConditionAffect,neEventLogTimeStamp,neEventLogIdentityTranslation } 
    STATUS      current 
    DESCRIPTION
        "Non-Specific Disablement of Management Access" 
    ::=  { trapMibPrefix 1005 }

alarmReceiverDisabled NOTIFICATION-TYPE 
    OBJECTS     { currentConditionSeverity,currentConditionAffect,neEventLogTimeStamp,neEventLogIdentityTranslation } 
    STATUS      current 
    DESCRIPTION
        "Disablement of Management Access with Receiver OFF" 
    ::=  { trapMibPrefix 1006 }

alarmTransmitterDisabledOff NOTIFICATION-TYPE 
    OBJECTS     { currentConditionSeverity,currentConditionAffect,neEventLogTimeStamp,neEventLogIdentityTranslation } 
    STATUS      current 
    DESCRIPTION
        "Disablement of Management Access with Transmitter OFF" 
    ::=  { trapMibPrefix 1007 }

alarmTransmittedDisabledIdle NOTIFICATION-TYPE 
    OBJECTS     { currentConditionSeverity,currentConditionAffect,neEventLogTimeStamp,neEventLogIdentityTranslation } 
    STATUS      current 
    DESCRIPTION
        "Disablement of Management Access with Transmitter IDLE" 
    ::=  { trapMibPrefix 1008 }

alarmTransmitterDisabledAis NOTIFICATION-TYPE 
    OBJECTS     { currentConditionSeverity,currentConditionAffect,neEventLogTimeStamp,neEventLogIdentityTranslation } 
    STATUS      current 
    DESCRIPTION
        "Disablement of Management Access with Transmitter Sending Maintenance Signal AIS" 
    ::=  { trapMibPrefix 1009 }

alarmTransmitterDisabledEpc NOTIFICATION-TYPE 
    OBJECTS     { currentConditionSeverity,currentConditionAffect,neEventLogTimeStamp,neEventLogIdentityTranslation } 
    STATUS      current 
    DESCRIPTION
        "Disablement of Management Access with Transmitter Sending Maintenance Signal EPC" 
    ::=  { trapMibPrefix 1010 }

alarmOosManagement NOTIFICATION-TYPE 
    OBJECTS     { currentConditionSeverity,currentConditionAffect,neEventLogTimeStamp,neEventLogIdentityTranslation } 
    STATUS      current 
    DESCRIPTION
        "Alarms are logged but not notified, service affecting changes are permitted" 
    ::=  { trapMibPrefix 1011 }

alarmOosMaintenance NOTIFICATION-TYPE 
    OBJECTS     { currentConditionSeverity,currentConditionAffect,neEventLogTimeStamp,neEventLogIdentityTranslation } 
    STATUS      current 
    DESCRIPTION
        "Alarms are logged but not notified, service affecting changes and operations are permitted" 
    ::=  { trapMibPrefix 1012 }

alarmOosAins NOTIFICATION-TYPE 
    OBJECTS     { currentConditionSeverity,currentConditionAffect,neEventLogTimeStamp,neEventLogIdentityTranslation } 
    STATUS      current 
    DESCRIPTION
        "Automatic In Service" 
    ::=  { trapMibPrefix 1013 }

alarmDcnCommunicationFail NOTIFICATION-TYPE 
    OBJECTS     { currentConditionSeverity,currentConditionAffect,neEventLogTimeStamp,neEventLogIdentityTranslation } 
    STATUS      current 
    DESCRIPTION
        "The connection to the shelf is dysfunctional or the connection to the module within the shelf is dysfunctional" 
    ::=  { trapMibPrefix 1014 }

alarmRemoved NOTIFICATION-TYPE 
    OBJECTS     { currentConditionSeverity,currentConditionAffect,neEventLogTimeStamp,neEventLogIdentityTranslation } 
    STATUS      current 
    DESCRIPTION
        "The equipment has been removed / unplugged / disconnected.
         This condition has been determined to be more probable than that below,
         which is also supersedes." 
    ::=  { trapMibPrefix 1015 }

alarmMismatch NOTIFICATION-TYPE 
    OBJECTS     { currentConditionSeverity,currentConditionAffect,neEventLogTimeStamp,neEventLogIdentityTranslation } 
    STATUS      current 
    DESCRIPTION
        "Non-Specific Mismatch. Equipment Not Match Provisioned Hardware" 
    ::=  { trapMibPrefix 1016 }

alarmEquipmentNotAccepted NOTIFICATION-TYPE 
    OBJECTS     { currentConditionSeverity,currentConditionAffect,neEventLogTimeStamp,neEventLogIdentityTranslation } 
    STATUS      current 
    DESCRIPTION
        "The Plug cannot support any of the services provisionable on this card OR the Plug is unrecognizable" 
    ::=  { trapMibPrefix 1017 }

alarmFacilityDataRateNotSupported NOTIFICATION-TYPE 
    OBJECTS     { currentConditionSeverity,currentConditionAffect,neEventLogTimeStamp,neEventLogIdentityTranslation } 
    STATUS      current 
    DESCRIPTION
        "The Plug inserted cannot support the actual service provisioned on this card: this is superseded by the above" 
    ::=  { trapMibPrefix 1018 }

alarmEquipmentNotSupportedByPhysicalLayer NOTIFICATION-TYPE 
    OBJECTS     { currentConditionSeverity,currentConditionAffect,neEventLogTimeStamp,neEventLogIdentityTranslation } 
    STATUS      current 
    DESCRIPTION
        "Equipment not Support Configured Physical Layer" 
    ::=  { trapMibPrefix 1019 }

alarmEquipmentNotApproved NOTIFICATION-TYPE 
    OBJECTS     { currentConditionSeverity,currentConditionAffect,neEventLogTimeStamp,neEventLogIdentityTranslation } 
    STATUS      current 
    DESCRIPTION
        "The Plug is recognizable to the extent that service support can
         be determined, but is not approved: this is susperseded by SGEO-RATE" 
    ::=  { trapMibPrefix 1020 }

alarmEquipmentMismatch NOTIFICATION-TYPE 
    OBJECTS     { currentConditionSeverity,currentConditionAffect,neEventLogTimeStamp,neEventLogIdentityTranslation } 
    STATUS      current 
    DESCRIPTION
        "The Plug is approved but does not match the specific Plug provisioned: this is superseded by SGEO-RATE, MEA-APPROVE" 
    ::=  { trapMibPrefix 1021 }

alarmFuseAlarm1 NOTIFICATION-TYPE 
    OBJECTS     { currentConditionSeverity,currentConditionAffect,neEventLogTimeStamp,neEventLogIdentityTranslation } 
    STATUS      current 
    DESCRIPTION
        "" 
    ::=  { trapMibPrefix 1022 }

alarmFuseAlarm2 NOTIFICATION-TYPE 
    OBJECTS     { currentConditionSeverity,currentConditionAffect,neEventLogTimeStamp,neEventLogIdentityTranslation } 
    STATUS      current 
    DESCRIPTION
        "" 
    ::=  { trapMibPrefix 1023 }

alarmFanAlarm NOTIFICATION-TYPE 
    OBJECTS     { currentConditionSeverity,currentConditionAffect,neEventLogTimeStamp,neEventLogIdentityTranslation } 
    STATUS      current 
    DESCRIPTION
        "A FAN has failed" 
    ::=  { trapMibPrefix 1024 }

alarmFanUnitAlarm NOTIFICATION-TYPE 
    OBJECTS     { currentConditionSeverity,currentConditionAffect,neEventLogTimeStamp,neEventLogIdentityTranslation } 
    STATUS      current 
    DESCRIPTION
        "More than one FAN has failed within the FANUNIT" 
    ::=  { trapMibPrefix 1025 }

alarmPowerMissing NOTIFICATION-TYPE 
    OBJECTS     { currentConditionSeverity,currentConditionAffect,neEventLogTimeStamp,neEventLogIdentityTranslation } 
    STATUS      current 
    DESCRIPTION
        "Power Unit Missing" 
    ::=  { trapMibPrefix 1026 }

alarmPowerFailure NOTIFICATION-TYPE 
    OBJECTS     { currentConditionSeverity,currentConditionAffect,neEventLogTimeStamp,neEventLogIdentityTranslation } 
    STATUS      deprecated 
    DESCRIPTION
        "Power Unit Failure" 
    ::=  { trapMibPrefix 1027 }

alarmVoltageTooLow NOTIFICATION-TYPE 
    OBJECTS     { currentConditionSeverity,currentConditionAffect,neEventLogTimeStamp,neEventLogIdentityTranslation } 
    STATUS      current 
    DESCRIPTION
        "Voltage Too Low" 
    ::=  { trapMibPrefix 1028 }

alarmVoltageTooHigh NOTIFICATION-TYPE 
    OBJECTS     { currentConditionSeverity,currentConditionAffect,neEventLogTimeStamp,neEventLogIdentityTranslation } 
    STATUS      current 
    DESCRIPTION
        "Voltage Too High" 
    ::=  { trapMibPrefix 1029 }

alarmTemperatureTooLow NOTIFICATION-TYPE 
    OBJECTS     { currentConditionSeverity,currentConditionAffect,neEventLogTimeStamp,neEventLogIdentityTranslation } 
    STATUS      current 
    DESCRIPTION
        "Temperature Too Low" 
    ::=  { trapMibPrefix 1030 }

alarmTemperatureTooHigh NOTIFICATION-TYPE 
    OBJECTS     { currentConditionSeverity,currentConditionAffect,neEventLogTimeStamp,neEventLogIdentityTranslation } 
    STATUS      current 
    DESCRIPTION
        "Temperature Too High" 
    ::=  { trapMibPrefix 1031 }

alarmReceiverFailure NOTIFICATION-TYPE 
    OBJECTS     { currentConditionSeverity,currentConditionAffect,neEventLogTimeStamp,neEventLogIdentityTranslation } 
    STATUS      deprecated 
    DESCRIPTION
        "Rx Failure" 
    ::=  { trapMibPrefix 1032 }

alarmOpticalInputPowerReceiverFailure NOTIFICATION-TYPE 
    OBJECTS     { currentConditionSeverity,currentConditionAffect,neEventLogTimeStamp,neEventLogIdentityTranslation } 
    STATUS      deprecated 
    DESCRIPTION
        "???" 
    ::=  { trapMibPrefix 1033 }

alarmLossOfSignal NOTIFICATION-TYPE 
    OBJECTS     { currentConditionSeverity,currentConditionAffect,neEventLogTimeStamp,neEventLogIdentityTranslation } 
    STATUS      current 
    DESCRIPTION
        "Loss Of Signal" 
    ::=  { trapMibPrefix 1034 }

alarmIdleSignalReceived NOTIFICATION-TYPE 
    OBJECTS     { currentConditionSeverity,currentConditionAffect,neEventLogTimeStamp,neEventLogIdentityTranslation } 
    STATUS      current 
    DESCRIPTION
        "" 
    ::=  { trapMibPrefix 1035 }

alarmLossOfLinkPulse NOTIFICATION-TYPE 
    OBJECTS     { currentConditionSeverity,currentConditionAffect,neEventLogTimeStamp,neEventLogIdentityTranslation } 
    STATUS      current 
    DESCRIPTION
        "Loss Of Link Pulse" 
    ::=  { trapMibPrefix 1036 }

alarmLossOfReceiverClockRecovery NOTIFICATION-TYPE 
    OBJECTS     { currentConditionSeverity,currentConditionAffect,neEventLogTimeStamp,neEventLogIdentityTranslation } 
    STATUS      current 
    DESCRIPTION
        "Rx Clock Sync Failure" 
    ::=  { trapMibPrefix 1037 }

alarmElasticStoreOverflowReceiver NOTIFICATION-TYPE 
    OBJECTS     { currentConditionSeverity,currentConditionAffect,neEventLogTimeStamp,neEventLogIdentityTranslation } 
    STATUS      current 
    DESCRIPTION
        "Rx Elast. Store Overflow" 
    ::=  { trapMibPrefix 1038 }

alarmLossOfTransmitterClockRecovery NOTIFICATION-TYPE 
    OBJECTS     { currentConditionSeverity,currentConditionAffect,neEventLogTimeStamp,neEventLogIdentityTranslation } 
    STATUS      current 
    DESCRIPTION
        "Tx Clock Sync Failure" 
    ::=  { trapMibPrefix 1039 }

alarmLaserFailure NOTIFICATION-TYPE 
    OBJECTS     { currentConditionSeverity,currentConditionAffect,neEventLogTimeStamp,neEventLogIdentityTranslation } 
    STATUS      current 
    DESCRIPTION
        "Optical Power Transmitted Failure: Laser Failure" 
    ::=  { trapMibPrefix 1040 }

alarmSwitchFailed NOTIFICATION-TYPE 
    OBJECTS     { currentConditionSeverity,currentConditionAffect,neEventLogTimeStamp,neEventLogIdentityTranslation } 
    STATUS      current 
    DESCRIPTION
        "Failure to Respond to Switch/Bridge Request within 50 ms" 
    ::=  { trapMibPrefix 1041 }

alarmElasticStoreOverflowTransmitter NOTIFICATION-TYPE 
    OBJECTS     { currentConditionSeverity,currentConditionAffect,neEventLogTimeStamp,neEventLogIdentityTranslation } 
    STATUS      current 
    DESCRIPTION
        "Tx Elast. Store Overflow" 
    ::=  { trapMibPrefix 1042 }

alarmAutoShutdownLaserOffDueToErrFwd NOTIFICATION-TYPE 
    OBJECTS     { currentConditionSeverity,currentConditionAffect,neEventLogTimeStamp,neEventLogIdentityTranslation } 
    STATUS      current 
    DESCRIPTION
        "Forward ALS" 
    ::=  { trapMibPrefix 1043 }

alarmAutoShutdown NOTIFICATION-TYPE 
    OBJECTS     { currentConditionSeverity,currentConditionAffect,neEventLogTimeStamp,neEventLogIdentityTranslation } 
    STATUS      current 
    DESCRIPTION
        "Automatic Shutdown with Transmitter sending Connection Detection Pulses" 
    ::=  { trapMibPrefix 1044 }

alarmAutoShutdownAls NOTIFICATION-TYPE 
    OBJECTS     { currentConditionSeverity,currentConditionAffect,neEventLogTimeStamp,neEventLogIdentityTranslation } 
    STATUS      current 
    DESCRIPTION
        "Auto Shutdown (ALS)" 
    ::=  { trapMibPrefix 1045 }

alarmAutoShutdownSendingIdle NOTIFICATION-TYPE 
    OBJECTS     { currentConditionSeverity,currentConditionAffect,neEventLogTimeStamp,neEventLogIdentityTranslation } 
    STATUS      deprecated 
    DESCRIPTION
        "Auto Shutdown (IDLE)" 
    ::=  { trapMibPrefix 1046 }

alarmThermoElectricCoolerEndOfLife NOTIFICATION-TYPE 
    OBJECTS     { currentConditionSeverity,currentConditionAffect,neEventLogTimeStamp,neEventLogIdentityTranslation } 
    STATUS      current 
    DESCRIPTION
        "TEC End of Life" 
    ::=  { trapMibPrefix 1047 }

alarmOpticalInputPwrReceivedTooLow NOTIFICATION-TYPE 
    OBJECTS     { currentConditionSeverity,currentConditionAffect,neEventLogTimeStamp,neEventLogIdentityTranslation } 
    STATUS      current 
    DESCRIPTION
        "Optical Power Rx too Low" 
    ::=  { trapMibPrefix 1048 }

alarmOpticalInputPwrReceivedTooHigh NOTIFICATION-TYPE 
    OBJECTS     { currentConditionSeverity,currentConditionAffect,neEventLogTimeStamp,neEventLogIdentityTranslation } 
    STATUS      current 
    DESCRIPTION
        "Optical Power Rx too High" 
    ::=  { trapMibPrefix 1049 }

alarmLaserTemperatureTooHigh NOTIFICATION-TYPE 
    OBJECTS     { currentConditionSeverity,currentConditionAffect,neEventLogTimeStamp,neEventLogIdentityTranslation } 
    STATUS      current 
    DESCRIPTION
        "TCA - Fixed high threshold of Laser Temperature has been crossed." 
    ::=  { trapMibPrefix 1050 }

alarmLaserTemperatureTooLow NOTIFICATION-TYPE 
    OBJECTS     { currentConditionSeverity,currentConditionAffect,neEventLogTimeStamp,neEventLogIdentityTranslation } 
    STATUS      current 
    DESCRIPTION
        "TCA - Fixed low threshold of Laser Temperature has been crossed." 
    ::=  { trapMibPrefix 1051 }

alarmOpticalOutputPowerTransmittedTooLow NOTIFICATION-TYPE 
    OBJECTS     { currentConditionSeverity,currentConditionAffect,neEventLogTimeStamp,neEventLogIdentityTranslation } 
    STATUS      current 
    DESCRIPTION
        "TCA - Optical Power Transmitted (output) too low" 
    ::=  { trapMibPrefix 1052 }

alarmOpticalOutputPowerTransmittedTooHigh NOTIFICATION-TYPE 
    OBJECTS     { currentConditionSeverity,currentConditionAffect,neEventLogTimeStamp,neEventLogIdentityTranslation } 
    STATUS      current 
    DESCRIPTION
        "TCA - Optical Power Transmitted (output) too high" 
    ::=  { trapMibPrefix 1053 }

alarmLaserBiasCurrentNormalizedtooHigh NOTIFICATION-TYPE 
    OBJECTS     { currentConditionSeverity,currentConditionAffect,neEventLogTimeStamp,neEventLogIdentityTranslation } 
    STATUS      current 
    DESCRIPTION
        "TCA - Laser Bias Current Level too High. Fixed threshold has been crossed." 
    ::=  { trapMibPrefix 1054 }

alarmLossOfSignalTransmitter NOTIFICATION-TYPE 
    OBJECTS     { currentConditionSeverity,currentConditionAffect,neEventLogTimeStamp,neEventLogIdentityTranslation } 
    STATUS      current 
    DESCRIPTION
        "A Loss of signal has been detected on the FAR-END facility." 
    ::=  { trapMibPrefix 1055 }

alarmAttOnReceiverFiberLowerThanMonitor NOTIFICATION-TYPE 
    OBJECTS     { currentConditionSeverity,currentConditionAffect,neEventLogTimeStamp,neEventLogIdentityTranslation } 
    STATUS      current 
    DESCRIPTION
        "Attenuation Rx Too Low" 
    ::=  { trapMibPrefix 1056 }

alarmAttOnReceiverFiberHigherThanMonitor NOTIFICATION-TYPE 
    OBJECTS     { currentConditionSeverity,currentConditionAffect,neEventLogTimeStamp,neEventLogIdentityTranslation } 
    STATUS      current 
    DESCRIPTION
        "Attenuation Rx Too High" 
    ::=  { trapMibPrefix 1057 }

alarmAttOnTransmitterFiberLowerThanMonitor NOTIFICATION-TYPE 
    OBJECTS     { currentConditionSeverity,currentConditionAffect,neEventLogTimeStamp,neEventLogIdentityTranslation } 
    STATUS      current 
    DESCRIPTION
        "Attenuation Tx Too Low" 
    ::=  { trapMibPrefix 1058 }

alarmAttOnTransmitterFiberHigherThanMonitor NOTIFICATION-TYPE 
    OBJECTS     { currentConditionSeverity,currentConditionAffect,neEventLogTimeStamp,neEventLogIdentityTranslation } 
    STATUS      current 
    DESCRIPTION
        "Attenuation Tx Too High" 
    ::=  { trapMibPrefix 1059 }

alarmAutoShutdownSendingAisOtu NOTIFICATION-TYPE 
    OBJECTS     { currentConditionSeverity,currentConditionAffect,neEventLogTimeStamp,neEventLogIdentityTranslation } 
    STATUS      current 
    DESCRIPTION
        "Auto Shutdown (OTU-AIS)" 
    ::=  { trapMibPrefix 1060 }

alarmLossOfFrameOtu NOTIFICATION-TYPE 
    OBJECTS     { currentConditionSeverity,currentConditionAffect,neEventLogTimeStamp,neEventLogIdentityTranslation } 
    STATUS      current 
    DESCRIPTION
        "OTU LOF" 
    ::=  { trapMibPrefix 1061 }

alarmLossOfMultiFrameOtu NOTIFICATION-TYPE 
    OBJECTS     { currentConditionSeverity,currentConditionAffect,neEventLogTimeStamp,neEventLogIdentityTranslation } 
    STATUS      current 
    DESCRIPTION
        "OTU LOM" 
    ::=  { trapMibPrefix 1062 }

alarmAlarmIndicationSignalOtu NOTIFICATION-TYPE 
    OBJECTS     { currentConditionSeverity,currentConditionAffect,neEventLogTimeStamp,neEventLogIdentityTranslation } 
    STATUS      current 
    DESCRIPTION
        "Alarm Indication Signal OTU Section Monitoring" 
    ::=  { trapMibPrefix 1063 }

alarmSignalDegradeOtu NOTIFICATION-TYPE 
    OBJECTS     { currentConditionSeverity,currentConditionAffect,neEventLogTimeStamp,neEventLogIdentityTranslation } 
    STATUS      current 
    DESCRIPTION
        "OTU Signal Degrade" 
    ::=  { trapMibPrefix 1064 }

alarmBackwardDefectIndicationOtu NOTIFICATION-TYPE 
    OBJECTS     { currentConditionSeverity,currentConditionAffect,neEventLogTimeStamp,neEventLogIdentityTranslation } 
    STATUS      current 
    DESCRIPTION
        "OTU Backward Defect Indication" 
    ::=  { trapMibPrefix 1065 }

alarmAutoShutdownSendingAisOdu NOTIFICATION-TYPE 
    OBJECTS     { currentConditionSeverity,currentConditionAffect,neEventLogTimeStamp,neEventLogIdentityTranslation } 
    STATUS      current 
    DESCRIPTION
        "Auto Shutdown (ODU-AIS)" 
    ::=  { trapMibPrefix 1066 }

alarmLossOfFrameLossOfMultiFrameOdu NOTIFICATION-TYPE 
    OBJECTS     { currentConditionSeverity,currentConditionAffect,neEventLogTimeStamp,neEventLogIdentityTranslation } 
    STATUS      current 
    DESCRIPTION
        "ODU LOF/LOM" 
    ::=  { trapMibPrefix 1067 }

alarmAlarmIndicationSignalOdu NOTIFICATION-TYPE 
    OBJECTS     { currentConditionSeverity,currentConditionAffect,neEventLogTimeStamp,neEventLogIdentityTranslation } 
    STATUS      current 
    DESCRIPTION
        "Alarm Indication Signal ODU Path Monitoring" 
    ::=  { trapMibPrefix 1068 }

alarmOpenConnectionIndicationOdu NOTIFICATION-TYPE 
    OBJECTS     { currentConditionSeverity,currentConditionAffect,neEventLogTimeStamp,neEventLogIdentityTranslation } 
    STATUS      current 
    DESCRIPTION
        "???" 
    ::=  { trapMibPrefix 1069 }

alarmLockedDefectOdu NOTIFICATION-TYPE 
    OBJECTS     { currentConditionSeverity,currentConditionAffect,neEventLogTimeStamp,neEventLogIdentityTranslation } 
    STATUS      current 
    DESCRIPTION
        "ODU Locked" 
    ::=  { trapMibPrefix 1070 }

alarmSignalDegradeOdu NOTIFICATION-TYPE 
    OBJECTS     { currentConditionSeverity,currentConditionAffect,neEventLogTimeStamp,neEventLogIdentityTranslation } 
    STATUS      current 
    DESCRIPTION
        "Related to a configurable threshold" 
    ::=  { trapMibPrefix 1071 }

alarmBackwardDefectIndicationOdu NOTIFICATION-TYPE 
    OBJECTS     { currentConditionSeverity,currentConditionAffect,neEventLogTimeStamp,neEventLogIdentityTranslation } 
    STATUS      current 
    DESCRIPTION
        "ODU Backward Defect Indication" 
    ::=  { trapMibPrefix 1072 }

alarmAlarmIndicationSignalOduTcmA NOTIFICATION-TYPE 
    OBJECTS     { currentConditionSeverity,currentConditionAffect,neEventLogTimeStamp,neEventLogIdentityTranslation } 
    STATUS      current 
    DESCRIPTION
        "Alarm Indication Signal ODU Tandem Connection Monitoring Instance A" 
    ::=  { trapMibPrefix 1073 }

alarmOpenConnectionIndicationOduTcmA NOTIFICATION-TYPE 
    OBJECTS     { currentConditionSeverity,currentConditionAffect,neEventLogTimeStamp,neEventLogIdentityTranslation } 
    STATUS      current 
    DESCRIPTION
        "Open Connection Indication ODU Tandem Connection Monitoring A" 
    ::=  { trapMibPrefix 1074 }

alarmLockedDefectOduTcmA NOTIFICATION-TYPE 
    OBJECTS     { currentConditionSeverity,currentConditionAffect,neEventLogTimeStamp,neEventLogIdentityTranslation } 
    STATUS      current 
    DESCRIPTION
        "Locked Defect ODU TCM Instance A" 
    ::=  { trapMibPrefix 1075 }

alarmLossofTandemConnectionOduTcmA NOTIFICATION-TYPE 
    OBJECTS     { currentConditionSeverity,currentConditionAffect,neEventLogTimeStamp,neEventLogIdentityTranslation } 
    STATUS      current 
    DESCRIPTION
        "Loss of Tandem Connection ODU Tandem Connection Monitoring Instane A" 
    ::=  { trapMibPrefix 1076 }

alarmSignalDegradeOduTcmA NOTIFICATION-TYPE 
    OBJECTS     { currentConditionSeverity,currentConditionAffect,neEventLogTimeStamp,neEventLogIdentityTranslation } 
    STATUS      current 
    DESCRIPTION
        "Signal Degrade ODU Tandem Connection Monitoring Instance A. Related to a configurable threshold" 
    ::=  { trapMibPrefix 1077 }

alarmBackwardDefectIndicationOduTcmA NOTIFICATION-TYPE 
    OBJECTS     { currentConditionSeverity,currentConditionAffect,neEventLogTimeStamp,neEventLogIdentityTranslation } 
    STATUS      current 
    DESCRIPTION
        "Backward Defect Indication ODU Tandem Connection Monitoring Instance A." 
    ::=  { trapMibPrefix 1078 }

alarmPayloadMismatchOPU NOTIFICATION-TYPE 
    OBJECTS     { currentConditionSeverity,currentConditionAffect,neEventLogTimeStamp,neEventLogIdentityTranslation } 
    STATUS      current 
    DESCRIPTION
        "ODU Payload Mismatch" 
    ::=  { trapMibPrefix 1079 }

alarmMultiplexStructureIdentifierMismatchOPU NOTIFICATION-TYPE 
    OBJECTS     { currentConditionSeverity,currentConditionAffect,neEventLogTimeStamp,neEventLogIdentityTranslation } 
    STATUS      current 
    DESCRIPTION
        "???" 
    ::=  { trapMibPrefix 1080 }

alarmLossOfFrame NOTIFICATION-TYPE 
    OBJECTS     { currentConditionSeverity,currentConditionAffect,neEventLogTimeStamp,neEventLogIdentityTranslation } 
    STATUS      current 
    DESCRIPTION
        "Section (SONET) / Regeneration Section (SDH) - Loss Of Frame" 
    ::=  { trapMibPrefix 1081 }

alarmSectionSignalFailure NOTIFICATION-TYPE 
    OBJECTS     { currentConditionSeverity,currentConditionAffect,neEventLogTimeStamp,neEventLogIdentityTranslation } 
    STATUS      current 
    DESCRIPTION
        "This is a very severe degradation BER >= 10**-3" 
    ::=  { trapMibPrefix 1082 }

alarmAutoShutdownSendingAisLine NOTIFICATION-TYPE 
    OBJECTS     { currentConditionSeverity,currentConditionAffect,neEventLogTimeStamp,neEventLogIdentityTranslation } 
    STATUS      current 
    DESCRIPTION
        "Auto Shutdown (L-AIS)" 
    ::=  { trapMibPrefix 1083 }

alarmAlarmIndicationSignalLine NOTIFICATION-TYPE 
    OBJECTS     { currentConditionSeverity,currentConditionAffect,neEventLogTimeStamp,neEventLogIdentityTranslation } 
    STATUS      current 
    DESCRIPTION
        "Alarm Indication Signal Line / Multiplex Section" 
    ::=  { trapMibPrefix 1084 }

alarmRemoteDefectIndicationLine NOTIFICATION-TYPE 
    OBJECTS     { currentConditionSeverity,currentConditionAffect,neEventLogTimeStamp,neEventLogIdentityTranslation } 
    STATUS      current 
    DESCRIPTION
        "Line / Multiplex Section RDI" 
    ::=  { trapMibPrefix 1085 }

alarmSignalDegradeLine NOTIFICATION-TYPE 
    OBJECTS     { currentConditionSeverity,currentConditionAffect,neEventLogTimeStamp,neEventLogIdentityTranslation } 
    STATUS      current 
    DESCRIPTION
        "Line/Mux Section SD" 
    ::=  { trapMibPrefix 1086 }

alarmAlarmIndicationSignalHigherOrderPath NOTIFICATION-TYPE 
    OBJECTS     { currentConditionSeverity,currentConditionAffect,neEventLogTimeStamp,neEventLogIdentityTranslation } 
    STATUS      current 
    DESCRIPTION
        "Alarm Indication Signal Path" 
    ::=  { trapMibPrefix 1087 }

alarmLossOfPointerHigherOrderPath NOTIFICATION-TYPE 
    OBJECTS     { currentConditionSeverity,currentConditionAffect,neEventLogTimeStamp,neEventLogIdentityTranslation } 
    STATUS      current 
    DESCRIPTION
        "Path LOP" 
    ::=  { trapMibPrefix 1088 }

alarmLossofMultiframeHigherOrderPath NOTIFICATION-TYPE 
    OBJECTS     { currentConditionSeverity,currentConditionAffect,neEventLogTimeStamp,neEventLogIdentityTranslation } 
    STATUS      current 
    DESCRIPTION
        "Path LOM" 
    ::=  { trapMibPrefix 1089 }

alarmLossofSequenceHigherOrderPath NOTIFICATION-TYPE 
    OBJECTS     { currentConditionSeverity,currentConditionAffect,neEventLogTimeStamp,neEventLogIdentityTranslation } 
    STATUS      current 
    DESCRIPTION
        "???" 
    ::=  { trapMibPrefix 1090 }

alarmUnequippedHigherOrderPath NOTIFICATION-TYPE 
    OBJECTS     { currentConditionSeverity,currentConditionAffect,neEventLogTimeStamp,neEventLogIdentityTranslation } 
    STATUS      current 
    DESCRIPTION
        "Path UNEQ" 
    ::=  { trapMibPrefix 1091 }

alarmPayloadMismatchHigherOrderPath NOTIFICATION-TYPE 
    OBJECTS     { currentConditionSeverity,currentConditionAffect,neEventLogTimeStamp,neEventLogIdentityTranslation } 
    STATUS      current 
    DESCRIPTION
        "SONET/SDH Path Payload Mismatch" 
    ::=  { trapMibPrefix 1092 }

alarmRemoteDefectIndicationHigherOrderPath NOTIFICATION-TYPE 
    OBJECTS     { currentConditionSeverity,currentConditionAffect,neEventLogTimeStamp,neEventLogIdentityTranslation } 
    STATUS      current 
    DESCRIPTION
        "Path RDI" 
    ::=  { trapMibPrefix 1093 }

alarmSignalDegradeHigherOrderPath NOTIFICATION-TYPE 
    OBJECTS     { currentConditionSeverity,currentConditionAffect,neEventLogTimeStamp,neEventLogIdentityTranslation } 
    STATUS      current 
    DESCRIPTION
        "Path Signal Degrade" 
    ::=  { trapMibPrefix 1094 }

alarmAlarmIndicationSignalLowerOrderPath NOTIFICATION-TYPE 
    OBJECTS     { currentConditionSeverity,currentConditionAffect,neEventLogTimeStamp,neEventLogIdentityTranslation } 
    STATUS      current 
    DESCRIPTION
        "Alarm Indication Signal Lower Order Path" 
    ::=  { trapMibPrefix 1095 }

alarmLossOfPointerLowerOrderPath NOTIFICATION-TYPE 
    OBJECTS     { currentConditionSeverity,currentConditionAffect,neEventLogTimeStamp,neEventLogIdentityTranslation } 
    STATUS      current 
    DESCRIPTION
        "Is this the same as LOF-LP" 
    ::=  { trapMibPrefix 1096 }

alarmLossofMultiframeLowerOrderPath NOTIFICATION-TYPE 
    OBJECTS     { currentConditionSeverity,currentConditionAffect,neEventLogTimeStamp,neEventLogIdentityTranslation } 
    STATUS      current 
    DESCRIPTION
        "LO-Path Loss Of Multiframe Condition" 
    ::=  { trapMibPrefix 1097 }

alarmLossofSequenceLowerOrderPath NOTIFICATION-TYPE 
    OBJECTS     { currentConditionSeverity,currentConditionAffect,neEventLogTimeStamp,neEventLogIdentityTranslation } 
    STATUS      current 
    DESCRIPTION
        "LO-Path Loss Of Sequence" 
    ::=  { trapMibPrefix 1098 }

alarmUnequippedLowerOrderPath NOTIFICATION-TYPE 
    OBJECTS     { currentConditionSeverity,currentConditionAffect,neEventLogTimeStamp,neEventLogIdentityTranslation } 
    STATUS      current 
    DESCRIPTION
        "LO-Path Unequipped" 
    ::=  { trapMibPrefix 1099 }

alarmPayloadMismatchLowerOrderPath NOTIFICATION-TYPE 
    OBJECTS     { currentConditionSeverity,currentConditionAffect,neEventLogTimeStamp,neEventLogIdentityTranslation } 
    STATUS      current 
    DESCRIPTION
        "LO-Path Payload Mismatch" 
    ::=  { trapMibPrefix 1100 }

alarmRemoteDefectIndicationLowerOrderPath NOTIFICATION-TYPE 
    OBJECTS     { currentConditionSeverity,currentConditionAffect,neEventLogTimeStamp,neEventLogIdentityTranslation } 
    STATUS      current 
    DESCRIPTION
        "LO-Path Remote Defect Indication" 
    ::=  { trapMibPrefix 1101 }

alarmLossOfMultiframeVCG NOTIFICATION-TYPE 
    OBJECTS     { currentConditionSeverity,currentConditionAffect,neEventLogTimeStamp,neEventLogIdentityTranslation } 
    STATUS      current 
    DESCRIPTION
        "Until the VCG is cross-connected the alarm should not be sent" 
    ::=  { trapMibPrefix 1102 }

alarmLossOfSequenceVCG NOTIFICATION-TYPE 
    OBJECTS     { currentConditionSeverity,currentConditionAffect,neEventLogTimeStamp,neEventLogIdentityTranslation } 
    STATUS      current 
    DESCRIPTION
        "Until the VCG is cross-connected the alarm should not be sent" 
    ::=  { trapMibPrefix 1103 }

alarmLossofAlignmentVCG NOTIFICATION-TYPE 
    OBJECTS     { currentConditionSeverity,currentConditionAffect,neEventLogTimeStamp,neEventLogIdentityTranslation } 
    STATUS      current 
    DESCRIPTION
        "Until the VCG is cross-connected the alarm should not be sent" 
    ::=  { trapMibPrefix 1104 }

alarmAutoShutdownSendingEPC NOTIFICATION-TYPE 
    OBJECTS     { currentConditionSeverity,currentConditionAffect,neEventLogTimeStamp,neEventLogIdentityTranslation } 
    STATUS      current 
    DESCRIPTION
        "Auto Shutdown (EPC)" 
    ::=  { trapMibPrefix 1105 }

alarmThres15MinExceededPhysConvES NOTIFICATION-TYPE 
    OBJECTS     { currentConditionSeverity,currentConditionAffect,neEventLogTimeStamp,neEventLogIdentityTranslation } 
    STATUS      current 
    DESCRIPTION
        "Errored Seconds Physical Coding Layer" 
    ::=  { trapMibPrefix 1106 }

alarmThres15MinExceededPhysConvCV NOTIFICATION-TYPE 
    OBJECTS     { currentConditionSeverity,currentConditionAffect,neEventLogTimeStamp,neEventLogIdentityTranslation } 
    STATUS      current 
    DESCRIPTION
        "Coding Violations Physical Coding Layer" 
    ::=  { trapMibPrefix 1107 }

alarmThres15MinExceededPhysConvDE NOTIFICATION-TYPE 
    OBJECTS     { currentConditionSeverity,currentConditionAffect,neEventLogTimeStamp,neEventLogIdentityTranslation } 
    STATUS      current 
    DESCRIPTION
        "Disparity Errors Physical Coding Layer" 
    ::=  { trapMibPrefix 1108 }

alarmThres15MinExceededPhysConvCVDE NOTIFICATION-TYPE 
    OBJECTS     { currentConditionSeverity,currentConditionAffect,neEventLogTimeStamp,neEventLogIdentityTranslation } 
    STATUS      current 
    DESCRIPTION
        "Coding Violations And Disparity Errors Physical Coding Layer" 
    ::=  { trapMibPrefix 1109 }

alarmLossOfGfpFrame NOTIFICATION-TYPE 
    OBJECTS     { currentConditionSeverity,currentConditionAffect,neEventLogTimeStamp,neEventLogIdentityTranslation } 
    STATUS      current 
    DESCRIPTION
        "GFP LOF" 
    ::=  { trapMibPrefix 1110 }

alarmPayloadMismatchGfp NOTIFICATION-TYPE 
    OBJECTS     { currentConditionSeverity,currentConditionAffect,neEventLogTimeStamp,neEventLogIdentityTranslation } 
    STATUS      current 
    DESCRIPTION
        "GFP Payload Mismatch" 
    ::=  { trapMibPrefix 1111 }

alarmGfpLossOfClientSig NOTIFICATION-TYPE 
    OBJECTS     { currentConditionSeverity,currentConditionAffect,neEventLogTimeStamp,neEventLogIdentityTranslation } 
    STATUS      current 
    DESCRIPTION
        "GFP Loss Of Client Signal" 
    ::=  { trapMibPrefix 1112 }

alarmLossOfCharSyncFromFarEnd NOTIFICATION-TYPE 
    OBJECTS     { currentConditionSeverity,currentConditionAffect,neEventLogTimeStamp,neEventLogIdentityTranslation } 
    STATUS      current 
    DESCRIPTION
        "Loss of Character Synchronization from FEND" 
    ::=  { trapMibPrefix 1113 }

alarmSwitchtoProtectionInhibited NOTIFICATION-TYPE 
    OBJECTS     { currentConditionSeverity,currentConditionAffect,neEventLogTimeStamp,neEventLogIdentityTranslation } 
    STATUS      current 
    DESCRIPTION
        "Protection Switch Inhibited. Switch to PROTN facility Locked Out. Reported by WKG facility. Leads to PSI state." 
    ::=  { trapMibPrefix 1114 }

alarmSwitchtoWorkingInhibited NOTIFICATION-TYPE 
    OBJECTS     { currentConditionSeverity,currentConditionAffect,neEventLogTimeStamp,neEventLogIdentityTranslation } 
    STATUS      current 
    DESCRIPTION
        "Protection Release Inhibited. Switch back to WKG facility Locked Out. Reported by PROTN facility. Leads to PRI state." 
    ::=  { trapMibPrefix 1115 }

alarmOTDRMeasuringinProgress NOTIFICATION-TYPE 
    OBJECTS     { currentConditionSeverity,currentConditionAffect,neEventLogTimeStamp,neEventLogIdentityTranslation } 
    STATUS      current 
    DESCRIPTION
        "On an OLM, the pilot laser has been switched off for a defined
         period to allow an Optical Time Domain Reflectometer to be deployed" 
    ::=  { trapMibPrefix 1116 }

alarmProtectionNotAvailable NOTIFICATION-TYPE 
    OBJECTS     { currentConditionSeverity,currentConditionAffect,neEventLogTimeStamp,neEventLogIdentityTranslation } 
    STATUS      current 
    DESCRIPTION
        "In the case of Channel Card Protection: due to unequipped or
         mismatched partner equipment - sent by active facility.In the case
         of HST Channel Protection: due to unequipped or mismatched partner
         plug - sent by active facility." 
    ::=  { trapMibPrefix 1117 }

alarmApsConfigMismatch NOTIFICATION-TYPE 
    OBJECTS     { currentConditionSeverity,currentConditionAffect,neEventLogTimeStamp,neEventLogIdentityTranslation } 
    STATUS      current 
    DESCRIPTION
        "Configuration Mismatch between NEND and FEND. Reported by protecting facility (PATHID==PROTN)." 
    ::=  { trapMibPrefix 1118 }

alarmEmbeddedOperationsChannelFailure NOTIFICATION-TYPE 
    OBJECTS     { currentConditionSeverity,currentConditionAffect,neEventLogTimeStamp,neEventLogIdentityTranslation } 
    STATUS      current 
    DESCRIPTION
        "Embedded Management Communication Channel Failure" 
    ::=  { trapMibPrefix 1119 }

alarmSignalDegradeSection NOTIFICATION-TYPE 
    OBJECTS     { currentConditionSeverity,currentConditionAffect,neEventLogTimeStamp,neEventLogIdentityTranslation } 
    STATUS      current 
    DESCRIPTION
        "Section / Regeneration Section SD" 
    ::=  { trapMibPrefix 1120 }

alarmSignalDegradationonLinkVector NOTIFICATION-TYPE 
    OBJECTS     { currentConditionSeverity,currentConditionAffect,neEventLogTimeStamp,neEventLogIdentityTranslation } 
    STATUS      current 
    DESCRIPTION
        "Signal Degradation on Link Vector. Superseeded by SF-LINK." 
    ::=  { trapMibPrefix 1121 }

alarmSignalFailureonLinkVector NOTIFICATION-TYPE 
    OBJECTS     { currentConditionSeverity,currentConditionAffect,neEventLogTimeStamp,neEventLogIdentityTranslation } 
    STATUS      current 
    DESCRIPTION
        "Signal Fail Link Vector" 
    ::=  { trapMibPrefix 1122 }

alarmInputVoltageFailure NOTIFICATION-TYPE 
    OBJECTS     { currentConditionSeverity,currentConditionAffect,neEventLogTimeStamp,neEventLogIdentityTranslation } 
    STATUS      current 
    DESCRIPTION
        "Failure of Input Voltage" 
    ::=  { trapMibPrefix 1123 }

alarmPowerSupplyUnitFailure NOTIFICATION-TYPE 
    OBJECTS     { currentConditionSeverity,currentConditionAffect,neEventLogTimeStamp,neEventLogIdentityTranslation } 
    STATUS      current 
    DESCRIPTION
        "Severe Fault in Power Supply Unit" 
    ::=  { trapMibPrefix 1124 }

alarmCurrentTooLow NOTIFICATION-TYPE 
    OBJECTS     { currentConditionSeverity,currentConditionAffect,neEventLogTimeStamp,neEventLogIdentityTranslation } 
    STATUS      current 
    DESCRIPTION
        "Current Too Low" 
    ::=  { trapMibPrefix 1125 }

alarmCurrentTooHigh NOTIFICATION-TYPE 
    OBJECTS     { currentConditionSeverity,currentConditionAffect,neEventLogTimeStamp,neEventLogIdentityTranslation } 
    STATUS      current 
    DESCRIPTION
        "Current Too High" 
    ::=  { trapMibPrefix 1126 }

alarmMultipleFanFailure NOTIFICATION-TYPE 
    OBJECTS     { currentConditionSeverity,currentConditionAffect,neEventLogTimeStamp,neEventLogIdentityTranslation } 
    STATUS      current 
    DESCRIPTION
        "Fault in Fan Control Unit (more than one FAN is faulty)" 
    ::=  { trapMibPrefix 1127 }

alarmSingleFanFailure NOTIFICATION-TYPE 
    OBJECTS     { currentConditionSeverity,currentConditionAffect,neEventLogTimeStamp,neEventLogIdentityTranslation } 
    STATUS      current 
    DESCRIPTION
        "Abnormality in Fan Control Unit (one FAN is faulty)" 
    ::=  { trapMibPrefix 1128 }

alarmLinkDown NOTIFICATION-TYPE 
    OBJECTS     { currentConditionSeverity,currentConditionAffect,neEventLogTimeStamp,neEventLogIdentityTranslation } 
    STATUS      current 
    DESCRIPTION
        "Failure of External Linkage" 
    ::=  { trapMibPrefix 1129 }

alarmVoltageOutOfRange NOTIFICATION-TYPE 
    OBJECTS     { currentConditionSeverity,currentConditionAffect,neEventLogTimeStamp,neEventLogIdentityTranslation } 
    STATUS      current 
    DESCRIPTION
        "Voltage out of Range" 
    ::=  { trapMibPrefix 1130 }

alarmPeerLink NOTIFICATION-TYPE 
    OBJECTS     { currentConditionSeverity,currentConditionAffect,neEventLogTimeStamp,neEventLogIdentityTranslation } 
    STATUS      current 
    DESCRIPTION
        "Failure of Internal Link or Link Protocol (could be protocol incompatibility) between Cards in Protection or Regeneration Pair" 
    ::=  { trapMibPrefix 1131 }

alarmHwFailure NOTIFICATION-TYPE 
    OBJECTS     { currentConditionSeverity,currentConditionAffect,neEventLogTimeStamp,neEventLogIdentityTranslation } 
    STATUS      current 
    DESCRIPTION
        "General Hardware Failure" 
    ::=  { trapMibPrefix 1132 }

alarmAlarmIndicationSignalOduTcmB NOTIFICATION-TYPE 
    OBJECTS     { currentConditionSeverity,currentConditionAffect,neEventLogTimeStamp,neEventLogIdentityTranslation } 
    STATUS      current 
    DESCRIPTION
        "Alarm Indication Signal ODU Tandem Connection Monitoring Instance B" 
    ::=  { trapMibPrefix 1133 }

alarmOpenConnectionIndicationOduTcmB NOTIFICATION-TYPE 
    OBJECTS     { currentConditionSeverity,currentConditionAffect,neEventLogTimeStamp,neEventLogIdentityTranslation } 
    STATUS      current 
    DESCRIPTION
        "Open Connection Indication ODU Tandem Connection Monitoring B" 
    ::=  { trapMibPrefix 1134 }

alarmLockedDefectOduTcmB NOTIFICATION-TYPE 
    OBJECTS     { currentConditionSeverity,currentConditionAffect,neEventLogTimeStamp,neEventLogIdentityTranslation } 
    STATUS      current 
    DESCRIPTION
        "Locked Defect ODU TCM Instance B" 
    ::=  { trapMibPrefix 1135 }

alarmLossofTandemConnectionOduTcmB NOTIFICATION-TYPE 
    OBJECTS     { currentConditionSeverity,currentConditionAffect,neEventLogTimeStamp,neEventLogIdentityTranslation } 
    STATUS      current 
    DESCRIPTION
        "Loss of Tandem Connection ODU Tandem Connection Monitoring Instane B" 
    ::=  { trapMibPrefix 1136 }

alarmSignalDegradeOduTcmB NOTIFICATION-TYPE 
    OBJECTS     { currentConditionSeverity,currentConditionAffect,neEventLogTimeStamp,neEventLogIdentityTranslation } 
    STATUS      current 
    DESCRIPTION
        "Signal Degrade ODU Tandem Connection Monitoring Instance B. Related to a configurable threshold" 
    ::=  { trapMibPrefix 1137 }

alarmBackwardDefectIndicationOduTcmB NOTIFICATION-TYPE 
    OBJECTS     { currentConditionSeverity,currentConditionAffect,neEventLogTimeStamp,neEventLogIdentityTranslation } 
    STATUS      current 
    DESCRIPTION
        "Backward Defect Indication ODU Tandem Connection Monitoring Instance B." 
    ::=  { trapMibPrefix 1138 }

alarmApsProtocolFailure NOTIFICATION-TYPE 
    OBJECTS     { currentConditionSeverity,currentConditionAffect,neEventLogTimeStamp,neEventLogIdentityTranslation } 
    STATUS      current 
    DESCRIPTION
        "Protocol Failure between NEND and FEND. Reported by protecting facility (PATHID==PROTN)." 
    ::=  { trapMibPrefix 1139 }

alarmApdLowVoltage NOTIFICATION-TYPE 
    OBJECTS     { currentConditionSeverity,currentConditionAffect,neEventLogTimeStamp,neEventLogIdentityTranslation } 
    STATUS      current 
    DESCRIPTION
        "Instantaneous Amplifying Photo Diode Low Voltage" 
    ::=  { trapMibPrefix 1140 }

alarmApdHighVoltage NOTIFICATION-TYPE 
    OBJECTS     { currentConditionSeverity,currentConditionAffect,neEventLogTimeStamp,neEventLogIdentityTranslation } 
    STATUS      current 
    DESCRIPTION
        "Instantaneous Amplifying Photo Diode High Voltage" 
    ::=  { trapMibPrefix 1141 }

alarmLinkControlProtocolFailure NOTIFICATION-TYPE 
    OBJECTS     { currentConditionSeverity,currentConditionAffect,neEventLogTimeStamp,neEventLogIdentityTranslation } 
    STATUS      current 
    DESCRIPTION
        "Link Control Protocol setup error or timeout" 
    ::=  { trapMibPrefix 1142 }

alarmReceiverLowTemp NOTIFICATION-TYPE 
    OBJECTS     { currentConditionSeverity,currentConditionAffect,neEventLogTimeStamp,neEventLogIdentityTranslation } 
    STATUS      current 
    DESCRIPTION
        "Instantaneous Receiver Temperature" 
    ::=  { trapMibPrefix 1143 }

alarmReceiverHighTemp NOTIFICATION-TYPE 
    OBJECTS     { currentConditionSeverity,currentConditionAffect,neEventLogTimeStamp,neEventLogIdentityTranslation } 
    STATUS      current 
    DESCRIPTION
        "Instantaneous Receiver Temperature" 
    ::=  { trapMibPrefix 1144 }

alarmThermoElectricCoolerCurrentTooLow NOTIFICATION-TYPE 
    OBJECTS     { currentConditionSeverity,currentConditionAffect,neEventLogTimeStamp,neEventLogIdentityTranslation } 
    STATUS      current 
    DESCRIPTION
        "Thermo Elecetric Cooler Low Current Level" 
    ::=  { trapMibPrefix 1145 }

alarmThermoElectricCoolerCurrentTooHigh NOTIFICATION-TYPE 
    OBJECTS     { currentConditionSeverity,currentConditionAffect,neEventLogTimeStamp,neEventLogIdentityTranslation } 
    STATUS      current 
    DESCRIPTION
        "Thermo Elecetric Cooler High Current Level" 
    ::=  { trapMibPrefix 1146 }

alarmSubModuleTempTooHigh NOTIFICATION-TYPE 
    OBJECTS     { currentConditionSeverity,currentConditionAffect,neEventLogTimeStamp,neEventLogIdentityTranslation } 
    STATUS      current 
    DESCRIPTION
        "Submodule Temperature too High" 
    ::=  { trapMibPrefix 1147 }

alarmSignalDegradeOlm NOTIFICATION-TYPE 
    OBJECTS     { currentConditionSeverity,currentConditionAffect,neEventLogTimeStamp,neEventLogIdentityTranslation } 
    STATUS      current 
    DESCRIPTION
        "Signal Degrade" 
    ::=  { trapMibPrefix 1148 }

alarmReceiverOverloadProtection NOTIFICATION-TYPE 
    OBJECTS     { currentConditionSeverity,currentConditionAffect,neEventLogTimeStamp,neEventLogIdentityTranslation } 
    STATUS      current 
    DESCRIPTION
        "Safety condition, protecting the system against too high receive power." 
    ::=  { trapMibPrefix 1149 }

alarmLossOfFrameMux NOTIFICATION-TYPE 
    OBJECTS     { currentConditionSeverity,currentConditionAffect,neEventLogTimeStamp,neEventLogIdentityTranslation } 
    STATUS      current 
    DESCRIPTION
        "Multiplexer Loss Of Frame" 
    ::=  { trapMibPrefix 1150 }

alarmLossOfFrameMuxFarEnd NOTIFICATION-TYPE 
    OBJECTS     { currentConditionSeverity,currentConditionAffect,neEventLogTimeStamp,neEventLogIdentityTranslation } 
    STATUS      current 
    DESCRIPTION
        "Multiplexer Loss of Frame on Far End" 
    ::=  { trapMibPrefix 1151 }

alarmLossOfCharSync NOTIFICATION-TYPE 
    OBJECTS     { currentConditionSeverity,currentConditionAffect,neEventLogTimeStamp,neEventLogIdentityTranslation } 
    STATUS      current 
    DESCRIPTION
        "Unable to syncronise on the characters in the incoming datastream" 
    ::=  { trapMibPrefix 1152 }

alarmThres15MinExceededFecCE NOTIFICATION-TYPE 
    OBJECTS     { currentConditionSeverity,currentConditionAffect,neEventLogTimeStamp,neEventLogIdentityTranslation } 
    STATUS      current 
    DESCRIPTION
        "Corr. FEC 15Min Exceeded" 
    ::=  { trapMibPrefix 1153 }

alarmThres15MinExceededFecUBE NOTIFICATION-TYPE 
    OBJECTS     { currentConditionSeverity,currentConditionAffect,neEventLogTimeStamp,neEventLogIdentityTranslation } 
    STATUS      current 
    DESCRIPTION
        "Uncorr. FEC 15Min Exceed" 
    ::=  { trapMibPrefix 1154 }

alarmThres15MinExceededFecES NOTIFICATION-TYPE 
    OBJECTS     { currentConditionSeverity,currentConditionAffect,neEventLogTimeStamp,neEventLogIdentityTranslation } 
    STATUS      current 
    DESCRIPTION
        "" 
    ::=  { trapMibPrefix 1155 }

alarmThres15MinExceededFecSES NOTIFICATION-TYPE 
    OBJECTS     { currentConditionSeverity,currentConditionAffect,neEventLogTimeStamp,neEventLogIdentityTranslation } 
    STATUS      current 
    DESCRIPTION
        "FEC-SES 15Min Exceeded" 
    ::=  { trapMibPrefix 1156 }

alarmThres15MinExceededMuxES NOTIFICATION-TYPE 
    OBJECTS     { currentConditionSeverity,currentConditionAffect,neEventLogTimeStamp,neEventLogIdentityTranslation } 
    STATUS      current 
    DESCRIPTION
        "" 
    ::=  { trapMibPrefix 1157 }

alarmThres15MinExceededMuxSES NOTIFICATION-TYPE 
    OBJECTS     { currentConditionSeverity,currentConditionAffect,neEventLogTimeStamp,neEventLogIdentityTranslation } 
    STATUS      current 
    DESCRIPTION
        "Mux-SES 15Min Exceeded" 
    ::=  { trapMibPrefix 1158 }

alarmThres15MinExceededGfpCHEC NOTIFICATION-TYPE 
    OBJECTS     { currentConditionSeverity,currentConditionAffect,neEventLogTimeStamp,neEventLogIdentityTranslation } 
    STATUS      current 
    DESCRIPTION
        "C-HEC 15Min Exceeded" 
    ::=  { trapMibPrefix 1159 }

alarmThres15MinExceededGfpTHEC NOTIFICATION-TYPE 
    OBJECTS     { currentConditionSeverity,currentConditionAffect,neEventLogTimeStamp,neEventLogIdentityTranslation } 
    STATUS      current 
    DESCRIPTION
        "tHEC-cor. 15Min Exceeded" 
    ::=  { trapMibPrefix 1160 }

alarmThres15MinExceededGfpTHecDisc NOTIFICATION-TYPE 
    OBJECTS     { currentConditionSeverity,currentConditionAffect,neEventLogTimeStamp,neEventLogIdentityTranslation } 
    STATUS      current 
    DESCRIPTION
        "tHECdisc. 15Min Exceeded" 
    ::=  { trapMibPrefix 1161 }

alarmThres15MinExceededGfpTsuperblockDisc NOTIFICATION-TYPE 
    OBJECTS     { currentConditionSeverity,currentConditionAffect,neEventLogTimeStamp,neEventLogIdentityTranslation } 
    STATUS      current 
    DESCRIPTION
        "" 
    ::=  { trapMibPrefix 1162 }

alarmIntrusionRx NOTIFICATION-TYPE 
    OBJECTS     { currentConditionSeverity,currentConditionAffect,neEventLogTimeStamp,neEventLogIdentityTranslation } 
    STATUS      deprecated 
    DESCRIPTION
        "Intrusion on the Receiver Fiber based on GRADHT-AT keyword." 
    ::=  { trapMibPrefix 1163 }

alarmIntrusionTx NOTIFICATION-TYPE 
    OBJECTS     { currentConditionSeverity,currentConditionAffect,neEventLogTimeStamp,neEventLogIdentityTranslation } 
    STATUS      deprecated 
    DESCRIPTION
        "Intrusion on the Receiver Fiber based on GRADHT-AT keyword." 
    ::=  { trapMibPrefix 1164 }

alarmAutoShutdownLaserOffDueToHighTemp NOTIFICATION-TYPE 
    OBJECTS     { currentConditionSeverity,currentConditionAffect,neEventLogTimeStamp,neEventLogIdentityTranslation } 
    STATUS      current 
    DESCRIPTION
        "Facility Autonomously Shut Down with Transmitter OFF due to Excessive Temperature." 
    ::=  { trapMibPrefix 1165 }

alarmAutoShutdownLaserOffDueToHighTxPwr NOTIFICATION-TYPE 
    OBJECTS     { currentConditionSeverity,currentConditionAffect,neEventLogTimeStamp,neEventLogIdentityTranslation } 
    STATUS      current 
    DESCRIPTION
        "Facility Autonomously Shut Down with Transmitter OFF because of excessiv optical Power Transmitted." 
    ::=  { trapMibPrefix 1166 }

alarmLaserEndOfLife NOTIFICATION-TYPE 
    OBJECTS     { currentConditionSeverity,currentConditionAffect,neEventLogTimeStamp,neEventLogIdentityTranslation } 
    STATUS      current 
    DESCRIPTION
        "End Of Life [laser degrade]." 
    ::=  { trapMibPrefix 1167 }

alarmLaserBiasCurrAbnormal NOTIFICATION-TYPE 
    OBJECTS     { currentConditionSeverity,currentConditionAffect,neEventLogTimeStamp,neEventLogIdentityTranslation } 
    STATUS      current 
    DESCRIPTION
        "Abnormally High Laser Bias Current Level under the current operating conditions." 
    ::=  { trapMibPrefix 1168 }

alarmOpticalPowerTxLOS NOTIFICATION-TYPE 
    OBJECTS     { currentConditionSeverity,currentConditionAffect,neEventLogTimeStamp,neEventLogIdentityTranslation } 
    STATUS      current 
    DESCRIPTION
        "Optical Power Transmission Fault (Tx LOS)." 
    ::=  { trapMibPrefix 1169 }

alarmMidstageFault NOTIFICATION-TYPE 
    OBJECTS     { currentConditionSeverity,currentConditionAffect,neEventLogTimeStamp,neEventLogIdentityTranslation } 
    STATUS      current 
    DESCRIPTION
        "Out of Service due to Midstage Fault." 
    ::=  { trapMibPrefix 1170 }

alarmFarEndIpAddressUnknown NOTIFICATION-TYPE 
    OBJECTS     { currentConditionSeverity,currentConditionAffect,neEventLogTimeStamp,neEventLogIdentityTranslation } 
    STATUS      current 
    DESCRIPTION
        "Send by active facility. If an FEND IP Address is changed the corresponding NODE-IP cannot be determined by the OSCM" 
    ::=  { trapMibPrefix 1171 }

alarmTopologyDataCalculationInProgress NOTIFICATION-TYPE 
    OBJECTS     { currentConditionSeverity,currentConditionAffect,neEventLogTimeStamp,neEventLogIdentityTranslation } 
    STATUS      current 
    DESCRIPTION
        "Calculation of topology in progress" 
    ::=  { trapMibPrefix 1172 }

alarmNtpServer1Unreachable NOTIFICATION-TYPE 
    OBJECTS     { currentConditionSeverity,currentConditionAffect,neEventLogTimeStamp,neEventLogIdentityTranslation } 
    STATUS      current 
    DESCRIPTION
        "alarm will be raised if the configured NTP server is not reacheble" 
    ::=  { trapMibPrefix 1173 }

alarmNtpServer2Unreachable NOTIFICATION-TYPE 
    OBJECTS     { currentConditionSeverity,currentConditionAffect,neEventLogTimeStamp,neEventLogIdentityTranslation } 
    STATUS      current 
    DESCRIPTION
        "alarm will be raised if the configured NTP server is not reacheble" 
    ::=  { trapMibPrefix 1174 }

alarmNtpServer3Unreachable NOTIFICATION-TYPE 
    OBJECTS     { currentConditionSeverity,currentConditionAffect,neEventLogTimeStamp,neEventLogIdentityTranslation } 
    STATUS      current 
    DESCRIPTION
        "alarm will be raised if the configured NTP server is not reacheble" 
    ::=  { trapMibPrefix 1175 }

alarmAutoShutdownSendingAisOpu NOTIFICATION-TYPE 
    OBJECTS     { currentConditionSeverity,currentConditionAffect,neEventLogTimeStamp,neEventLogIdentityTranslation } 
    STATUS      current 
    DESCRIPTION
        "Auto Shutdown (OPU-AIS)" 
    ::=  { trapMibPrefix 1176 }

alarmAlarmIndicationSignalOpu NOTIFICATION-TYPE 
    OBJECTS     { currentConditionSeverity,currentConditionAffect,neEventLogTimeStamp,neEventLogIdentityTranslation } 
    STATUS      current 
    DESCRIPTION
        "Alarm Indication Signal OPU Path Monitoring" 
    ::=  { trapMibPrefix 1177 }

alarmAlarmIndicationSignalOduTcmC NOTIFICATION-TYPE 
    OBJECTS     { currentConditionSeverity,currentConditionAffect,neEventLogTimeStamp,neEventLogIdentityTranslation } 
    STATUS      current 
    DESCRIPTION
        "Alarm Indication Signal ODU Tandem Connection Monitoring Instance C" 
    ::=  { trapMibPrefix 1178 }

alarmBackwardDefectIndicationOduTcmC NOTIFICATION-TYPE 
    OBJECTS     { currentConditionSeverity,currentConditionAffect,neEventLogTimeStamp,neEventLogIdentityTranslation } 
    STATUS      current 
    DESCRIPTION
        "Backward Defect Indication ODU Tandem Connection Monitoring Instance C." 
    ::=  { trapMibPrefix 1179 }

alarmLockedDefectOduTcmC NOTIFICATION-TYPE 
    OBJECTS     { currentConditionSeverity,currentConditionAffect,neEventLogTimeStamp,neEventLogIdentityTranslation } 
    STATUS      current 
    DESCRIPTION
        "Locked Defect ODU TCM Instance C" 
    ::=  { trapMibPrefix 1180 }

alarmLossofTandemConnectionOduTcmC NOTIFICATION-TYPE 
    OBJECTS     { currentConditionSeverity,currentConditionAffect,neEventLogTimeStamp,neEventLogIdentityTranslation } 
    STATUS      current 
    DESCRIPTION
        "Loss of Tandem Connection ODU Tandem Connection Monitoring Instane C" 
    ::=  { trapMibPrefix 1181 }

alarmOpenConnectionIndicationOduTcmC NOTIFICATION-TYPE 
    OBJECTS     { currentConditionSeverity,currentConditionAffect,neEventLogTimeStamp,neEventLogIdentityTranslation } 
    STATUS      current 
    DESCRIPTION
        "Open Connection Indication ODU Tandem Connection Monitoring C" 
    ::=  { trapMibPrefix 1182 }

alarmSignalDegradeOduTcmC NOTIFICATION-TYPE 
    OBJECTS     { currentConditionSeverity,currentConditionAffect,neEventLogTimeStamp,neEventLogIdentityTranslation } 
    STATUS      current 
    DESCRIPTION
        "Signal Degrade ODU Tandem Connection Monitoring Instance C. Related to a configurable threshold" 
    ::=  { trapMibPrefix 1183 }

alarmLoopbackError NOTIFICATION-TYPE 
    OBJECTS     { currentConditionSeverity,currentConditionAffect,neEventLogTimeStamp,neEventLogIdentityTranslation } 
    STATUS      current 
    DESCRIPTION
        "A loop in the PPP-IP path is detected" 
    ::=  { trapMibPrefix 1184 }

transientThres1DayExceededPhysConvES NOTIFICATION-TYPE 
    OBJECTS     { entityIndex,neEventLogTimeStamp,neEventLogIdentityTranslation } 
    STATUS      current 
    DESCRIPTION
        "Errored Seconds Physical Coding Layer" 
    ::=  { trapMibPrefix 3001 }

transientThres1DayExceededPhysConvCV NOTIFICATION-TYPE 
    OBJECTS     { entityIndex,neEventLogTimeStamp,neEventLogIdentityTranslation } 
    STATUS      current 
    DESCRIPTION
        "Coding Violations Physical Coding Layer" 
    ::=  { trapMibPrefix 3002 }

transientThres1DayExceededPhysConvDE NOTIFICATION-TYPE 
    OBJECTS     { entityIndex,neEventLogTimeStamp,neEventLogIdentityTranslation } 
    STATUS      current 
    DESCRIPTION
        "Disparity Errors Physical Coding Layer" 
    ::=  { trapMibPrefix 3003 }

transientThres1DayExceededPhysConvCVDE NOTIFICATION-TYPE 
    OBJECTS     { entityIndex,neEventLogTimeStamp,neEventLogIdentityTranslation } 
    STATUS      current 
    DESCRIPTION
        "Coding Violations And Disparity Errors Physical Coding Layer" 
    ::=  { trapMibPrefix 3004 }

transientMin15RecordsAvailable NOTIFICATION-TYPE 
    OBJECTS     { entityIndex,neEventLogTimeStamp,neEventLogIdentityTranslation } 
    STATUS      current 
    DESCRIPTION
        "Performance Monitoring Server has collected all 15-MIN records." 
    ::=  { trapMibPrefix 3005 }

transientDay1RecordsAvailable NOTIFICATION-TYPE 
    OBJECTS     { entityIndex,neEventLogTimeStamp,neEventLogIdentityTranslation } 
    STATUS      current 
    DESCRIPTION
        "Performance Monitoring Server has collected all 1-DAY records." 
    ::=  { trapMibPrefix 3006 }

transientWeek1RecordsAvailable NOTIFICATION-TYPE 
    OBJECTS     { entityIndex,neEventLogTimeStamp,neEventLogIdentityTranslation } 
    STATUS      current 
    DESCRIPTION
        "Performance Monitoring Server has collected all 1-WEEK records." 
    ::=  { trapMibPrefix 3007 }

transientNeColdStart NOTIFICATION-TYPE 
    OBJECTS     { entityIndex,neEventLogTimeStamp,neEventLogIdentityTranslation } 
    STATUS      current 
    DESCRIPTION
        "" 
    ::=  { trapMibPrefix 3008 }

transientWorkingSwitchedtoProtection NOTIFICATION-TYPE 
    OBJECTS     { entityIndex,neEventLogTimeStamp,neEventLogIdentityTranslation } 
    STATUS      current 
    DESCRIPTION
        "Working Traffic (ACT) switched from WKG facility to PROTN facility automatically, sent by WKG." 
    ::=  { trapMibPrefix 3009 }

transientWorkingSwitchedBacktoWorking NOTIFICATION-TYPE 
    OBJECTS     { entityIndex,neEventLogTimeStamp,neEventLogIdentityTranslation } 
    STATUS      current 
    DESCRIPTION
        "Working Traffic (ACT) switched back to WKG facilty from PROTN facility automatically: sent by PROTN." 
    ::=  { trapMibPrefix 3010 }

transientManualWorkingSwitchedtoProtection NOTIFICATION-TYPE 
    OBJECTS     { entityIndex,neEventLogTimeStamp,neEventLogIdentityTranslation } 
    STATUS      current 
    DESCRIPTION
        "Working Traffic (ACT) switched from WKG facility to PROTN facility manually: sent by WKG." 
    ::=  { trapMibPrefix 3011 }

transientManualWorkingSwitchedBacktoWorking NOTIFICATION-TYPE 
    OBJECTS     { entityIndex,neEventLogTimeStamp,neEventLogIdentityTranslation } 
    STATUS      current 
    DESCRIPTION
        "Working Traffic (ACT) switched back to WKG facility from PROTN facility manually: sent by PROTN." 
    ::=  { trapMibPrefix 3012 }

transientForcedWorkingSwitchedBacktoWorking NOTIFICATION-TYPE 
    OBJECTS     { entityIndex,neEventLogTimeStamp,neEventLogIdentityTranslation } 
    STATUS      current 
    DESCRIPTION
        "Forced Working Switched Back to Working" 
    ::=  { trapMibPrefix 3013 }

transientForcedWorkingSwitchedBacktoProtection NOTIFICATION-TYPE 
    OBJECTS     { entityIndex,neEventLogTimeStamp,neEventLogIdentityTranslation } 
    STATUS      current 
    DESCRIPTION
        "Forced Working Switched Back to Protection" 
    ::=  { trapMibPrefix 3014 }

transientThres1DayExceededBytesTx NOTIFICATION-TYPE 
    OBJECTS     { entityIndex,neEventLogTimeStamp,neEventLogIdentityTranslation } 
    STATUS      current 
    DESCRIPTION
        "" 
    ::=  { trapMibPrefix 3015 }

transientThres1DayExceededFecCE NOTIFICATION-TYPE 
    OBJECTS     { entityIndex,neEventLogTimeStamp,neEventLogIdentityTranslation } 
    STATUS      current 
    DESCRIPTION
        "Corr. FEC 1Day Exceeded" 
    ::=  { trapMibPrefix 3016 }

transientThres1DayExceededFecUBE NOTIFICATION-TYPE 
    OBJECTS     { entityIndex,neEventLogTimeStamp,neEventLogIdentityTranslation } 
    STATUS      current 
    DESCRIPTION
        "Uncorr. FEC 1Day Exceed" 
    ::=  { trapMibPrefix 3017 }

transientThres1DayExceededFecES NOTIFICATION-TYPE 
    OBJECTS     { entityIndex,neEventLogTimeStamp,neEventLogIdentityTranslation } 
    STATUS      current 
    DESCRIPTION
        "" 
    ::=  { trapMibPrefix 3018 }

transientThres1DayExceededFecSES NOTIFICATION-TYPE 
    OBJECTS     { entityIndex,neEventLogTimeStamp,neEventLogIdentityTranslation } 
    STATUS      current 
    DESCRIPTION
        "FEC-SES 1Day Exceeded" 
    ::=  { trapMibPrefix 3019 }

transientThres1DayExceededMuxES NOTIFICATION-TYPE 
    OBJECTS     { entityIndex,neEventLogTimeStamp,neEventLogIdentityTranslation } 
    STATUS      current 
    DESCRIPTION
        "" 
    ::=  { trapMibPrefix 3020 }

transientThres1DayExceededMuxSES NOTIFICATION-TYPE 
    OBJECTS     { entityIndex,neEventLogTimeStamp,neEventLogIdentityTranslation } 
    STATUS      current 
    DESCRIPTION
        "Mux-SES 1Day Exceeded" 
    ::=  { trapMibPrefix 3021 }

transientTopologyDataInvalid NOTIFICATION-TYPE 
    OBJECTS     { entityIndex,neEventLogTimeStamp,neEventLogIdentityTranslation } 
    STATUS      current 
    DESCRIPTION
        "Topology Detection Data invalid" 
    ::=  { trapMibPrefix 3022 }

transientCopyFileFailNotExist NOTIFICATION-TYPE 
    OBJECTS     { entityIndex,neEventLogTimeStamp,neEventLogIdentityTranslation } 
    STATUS      current 
    DESCRIPTION
        "Copy File: File Does Not Exist" 
    ::=  { trapMibPrefix 3023 }

transientCopyFileConnectionFail NOTIFICATION-TYPE 
    OBJECTS     { entityIndex,neEventLogTimeStamp,neEventLogIdentityTranslation } 
    STATUS      current 
    DESCRIPTION
        "Copy File: File Transfer Connect Fail, Server not reachable." 
    ::=  { trapMibPrefix 3024 }

transientCopyFileLoginFail NOTIFICATION-TYPE 
    OBJECTS     { entityIndex,neEventLogTimeStamp,neEventLogIdentityTranslation } 
    STATUS      current 
    DESCRIPTION
        "Copy File: Server Login Fail" 
    ::=  { trapMibPrefix 3025 }

transientCopyFileSpaceFail NOTIFICATION-TYPE 
    OBJECTS     { entityIndex,neEventLogTimeStamp,neEventLogIdentityTranslation } 
    STATUS      current 
    DESCRIPTION
        "Copy File: Insufficient File Space" 
    ::=  { trapMibPrefix 3026 }

transientCopyFileProtocolFail NOTIFICATION-TYPE 
    OBJECTS     { entityIndex,neEventLogTimeStamp,neEventLogIdentityTranslation } 
    STATUS      current 
    DESCRIPTION
        "Copy File: File Transfer Protocol Fail" 
    ::=  { trapMibPrefix 3027 }

transientCopyFileAccessDenied NOTIFICATION-TYPE 
    OBJECTS     { entityIndex,neEventLogTimeStamp,neEventLogIdentityTranslation } 
    STATUS      current 
    DESCRIPTION
        "Copy File: File Access Denied" 
    ::=  { trapMibPrefix 3028 }

transientCopyFileChecksumFail NOTIFICATION-TYPE 
    OBJECTS     { entityIndex,neEventLogTimeStamp,neEventLogIdentityTranslation } 
    STATUS      current 
    DESCRIPTION
        "Copy File: File Checksum Fail" 
    ::=  { trapMibPrefix 3029 }

transientCopyFileDownloadingStart NOTIFICATION-TYPE 
    OBJECTS     { entityIndex,neEventLogTimeStamp,neEventLogIdentityTranslation } 
    STATUS      current 
    DESCRIPTION
        "Copy File: 00.0% Complete" 
    ::=  { trapMibPrefix 3030 }

transientCopyFileDownloadingInProgress NOTIFICATION-TYPE 
    OBJECTS     { entityIndex,neEventLogTimeStamp,neEventLogIdentityTranslation } 
    STATUS      current 
    DESCRIPTION
        "Copy File: 50.0% Complete" 
    ::=  { trapMibPrefix 3031 }

transientCopyFileDownloadingComplete NOTIFICATION-TYPE 
    OBJECTS     { entityIndex,neEventLogTimeStamp,neEventLogIdentityTranslation } 
    STATUS      current 
    DESCRIPTION
        "Copy File: 100 % Complete" 
    ::=  { trapMibPrefix 3032 }

transientLocalCopyMemFail NOTIFICATION-TYPE 
    OBJECTS     { entityIndex,neEventLogTimeStamp,neEventLogIdentityTranslation } 
    STATUS      current 
    DESCRIPTION
        "Local Copy File Fail" 
    ::=  { trapMibPrefix 3033 }

transientLocalCopyFileStarted NOTIFICATION-TYPE 
    OBJECTS     { entityIndex,neEventLogTimeStamp,neEventLogIdentityTranslation } 
    STATUS      current 
    DESCRIPTION
        "Local Copy File Started." 
    ::=  { trapMibPrefix 3034 }

transientLocalCopyMemComplted NOTIFICATION-TYPE 
    OBJECTS     { entityIndex,neEventLogTimeStamp,neEventLogIdentityTranslation } 
    STATUS      current 
    DESCRIPTION
        "Local Copy File Completed" 
    ::=  { trapMibPrefix 3035 }

transientSoftwareActivation NOTIFICATION-TYPE 
    OBJECTS     { entityIndex,neEventLogTimeStamp,neEventLogIdentityTranslation } 
    STATUS      current 
    DESCRIPTION
        "Reboot starts immediately." 
    ::=  { trapMibPrefix 3036 }

transientSoftwareActivationFail NOTIFICATION-TYPE 
    OBJECTS     { entityIndex,neEventLogTimeStamp,neEventLogIdentityTranslation } 
    STATUS      current 
    DESCRIPTION
        "Software Activation /Reversion Failed." 
    ::=  { trapMibPrefix 3037 }

transientDatabaseActivationFail NOTIFICATION-TYPE 
    OBJECTS     { entityIndex,neEventLogTimeStamp,neEventLogIdentityTranslation } 
    STATUS      current 
    DESCRIPTION
        "DBS Activation / Restoration Failed." 
    ::=  { trapMibPrefix 3038 }

transientDatabaseActivation NOTIFICATION-TYPE 
    OBJECTS     { entityIndex,neEventLogTimeStamp,neEventLogIdentityTranslation } 
    STATUS      current 
    DESCRIPTION
        "DBS Activation /Restoration starts immediately." 
    ::=  { trapMibPrefix 3039 }

transientBootUpFailed NOTIFICATION-TYPE 
    OBJECTS     { entityIndex,neEventLogTimeStamp,neEventLogIdentityTranslation } 
    STATUS      current 
    DESCRIPTION
        "Boot up failed" 
    ::=  { trapMibPrefix 3040 }

transientBootUpCompleted NOTIFICATION-TYPE 
    OBJECTS     { entityIndex,neEventLogTimeStamp,neEventLogIdentityTranslation } 
    STATUS      current 
    DESCRIPTION
        "Boot up completed" 
    ::=  { trapMibPrefix 3041 }

transientBootUpStarted NOTIFICATION-TYPE 
    OBJECTS     { entityIndex,neEventLogTimeStamp,neEventLogIdentityTranslation } 
    STATUS      current 
    DESCRIPTION
        "Boot up started" 
    ::=  { trapMibPrefix 3042 }

transientIntrusionRx NOTIFICATION-TYPE 
    OBJECTS     { entityIndex,neEventLogTimeStamp,neEventLogIdentityTranslation } 
    STATUS      current 
    DESCRIPTION
        "Intrusion on the Receiver Fiber based on GRADHT-AT keyword." 
    ::=  { trapMibPrefix 3043 }

transientIntrusionTx NOTIFICATION-TYPE 
    OBJECTS     { entityIndex,neEventLogTimeStamp,neEventLogIdentityTranslation } 
    STATUS      current 
    DESCRIPTION
        "Intrusion on the Receiver Fiber based on GRADHT-AT keyword." 
    ::=  { trapMibPrefix 3044 }

transientDatabaseMismatch NOTIFICATION-TYPE 
    OBJECTS     { entityIndex,neEventLogTimeStamp,neEventLogIdentityTranslation } 
    STATUS      current 
    DESCRIPTION
        "compare DBACT__FAIL x.y.z in UBR note DBTYPE is retrievable immediately with RTRV-SYS, we do not currently supported a RTRV-COND-SYS" 
    ::=  { trapMibPrefix 3045 }

entityStateTable OBJECT-TYPE
    SYNTAX      SEQUENCE OF EntityStateEntry
    MAX-ACCESS  not-accessible
    STATUS      current 
    DESCRIPTION
        "" 
    ::=  { commonConfigAndStatus 1 }

entityStateEntry OBJECT-TYPE
    SYNTAX      EntityStateEntry
    MAX-ACCESS  not-accessible
    STATUS      current 
    DESCRIPTION
        "" 
    INDEX       { entityIndex } 
    ::=  { entityStateTable  1  }

EntityStateEntry ::=  SEQUENCE
  { entityStateAdmin FspR7AdminState,
    entityStateOper FspR7OperState,
    entityStateSecondaryStates FspR7EntitySecondaryStates }


  
entityStateAdmin OBJECT-TYPE
    SYNTAX      FspR7AdminState
    MAX-ACCESS  read-write
    STATUS      current 
    DESCRIPTION
        "The Adminstrative State will be displayed in the GUI with full name values;
         it will be differently displayed in TL1 SYNTAX according to TL1 display rules.
         The transaction into the UAS state requires a special destroy/delete function." 
    ::=  { entityStateEntry 1 }

entityStateOper OBJECT-TYPE
    SYNTAX      FspR7OperState
    MAX-ACCESS  read-only
    STATUS      current 
    DESCRIPTION
        "The Operational State will be displayed on the GUI with full name values;
         it will be differently displayed in TL1 SYNTAX according to TL1 display rules" 
    ::=  { entityStateEntry 2 }

entityStateSecondaryStates OBJECT-TYPE
    SYNTAX      FspR7EntitySecondaryStates
    MAX-ACCESS  read-only
    STATUS      current 
    DESCRIPTION
        "" 
    ::=  { entityStateEntry 3 }

moduleDiagnosticsTable OBJECT-TYPE
    SYNTAX      SEQUENCE OF ModuleDiagnosticsEntry
    MAX-ACCESS  not-accessible
    STATUS      current 
    DESCRIPTION
        "The ModuleDiagnostics table. This table extends the entries
         in the inventoryTable for the FspR7 modules." 
    ::=  { equipmentConfigAndStatus 1 }

moduleDiagnosticsEntry OBJECT-TYPE
    SYNTAX      ModuleDiagnosticsEntry
    MAX-ACCESS  not-accessible
    STATUS      current 
    DESCRIPTION
        "An entry in the ModuleDiagnostics table. Each entry in this table represents
         a field replacable module in a shelf, which is inserted into or removed from
         a container (slot)." 
    INDEX       { entityIndex } 
    ::=  { moduleDiagnosticsTable  1  }

ModuleDiagnosticsEntry ::=  SEQUENCE
  { moduleDiagnosticsTemp Integer32,
    moduleDiagnosticsUpperTempThres Integer32,
    moduleDiagnosticsLowerTempThres Integer32 }


  
moduleDiagnosticsTemp OBJECT-TYPE
    SYNTAX      Integer32
    UNITS       "0.1 °C"
    MAX-ACCESS  read-only
    STATUS      current 
    DESCRIPTION
        "Actual temperature on the module." 
    ::=  { moduleDiagnosticsEntry 1 }

moduleDiagnosticsUpperTempThres OBJECT-TYPE
    SYNTAX      Integer32
    UNITS       "0.1 °C"
    MAX-ACCESS  read-only
    STATUS      current 
    DESCRIPTION
        "Upper temperature threshold for threshold crossing alarm.
         temperatures above this value will cause a Notification." 
    ::=  { moduleDiagnosticsEntry 2 }

moduleDiagnosticsLowerTempThres OBJECT-TYPE
    SYNTAX      Integer32
    UNITS       "0.1 °C"
    MAX-ACCESS  read-only
    STATUS      current 
    DESCRIPTION
        "Lower temperature threshold for threshold crossing alarm.
         temperatures below this value will cause a Notification." 
    ::=  { moduleDiagnosticsEntry 3 }

currentDiagnosticsTable OBJECT-TYPE
    SYNTAX      SEQUENCE OF CurrentDiagnosticsEntry
    MAX-ACCESS  not-accessible
    STATUS      current 
    DESCRIPTION
        "The currentDiagnostics table. This table extends the entries
         in the inventoryTable for the FspR7 modules." 
    ::=  { equipmentConfigAndStatus 2 }

currentDiagnosticsEntry OBJECT-TYPE
    SYNTAX      CurrentDiagnosticsEntry
    MAX-ACCESS  not-accessible
    STATUS      current 
    DESCRIPTION
        "An entry in the currentDiagnostics table." 
    INDEX       { entityIndex } 
    ::=  { currentDiagnosticsTable  1  }

CurrentDiagnosticsEntry ::=  SEQUENCE
  { currentDiagnosticsAmpere Unsigned32,
    currentDiagnosticsUpperThres Unsigned32 }


  
currentDiagnosticsAmpere OBJECT-TYPE
    SYNTAX      Unsigned32
    UNITS       "0.001 A"
    MAX-ACCESS  read-only
    STATUS      current 
    DESCRIPTION
        "Instantaneous current measured." 
    ::=  { currentDiagnosticsEntry 1 }

currentDiagnosticsUpperThres OBJECT-TYPE
    SYNTAX      Unsigned32
    UNITS       "0.001 A"
    MAX-ACCESS  read-only
    STATUS      current 
    DESCRIPTION
        "Upper current threshold for threshold crossing condition.
         Currents above this value will cause a Notification" 
    ::=  { currentDiagnosticsEntry 2 }

moduleConfigTable OBJECT-TYPE
    SYNTAX      SEQUENCE OF ModuleConfigEntry
    MAX-ACCESS  not-accessible
    STATUS      current 
    DESCRIPTION
        "The ModuleConfig table. This table extends the entries
         in the inventoryTable for the FspR7 modules." 
    ::=  { equipmentConfigAndStatus 3 }

moduleConfigEntry OBJECT-TYPE
    SYNTAX      ModuleConfigEntry
    MAX-ACCESS  not-accessible
    STATUS      current 
    DESCRIPTION
        "An entry in the ModuleConfig table. Each entry in this table represents
         a field replacable module in a shelf, which is inserted into or removed
         from a container (slot)." 
    INDEX       { entityIndex } 
    ::=  { moduleConfigTable  1  }

ModuleConfigEntry ::=  SEQUENCE
  { moduleConfigAlias SnmpAdminString }


  
moduleConfigAlias OBJECT-TYPE
    SYNTAX      SnmpAdminString
    MAX-ACCESS  read-write
    STATUS      current 
    DESCRIPTION
        "A string, configurable by the operator, containing a
         symbolic name for the module." 
    ::=  { moduleConfigEntry 1 }

moduleDataTable OBJECT-TYPE
    SYNTAX      SEQUENCE OF ModuleDataEntry
    MAX-ACCESS  not-accessible
    STATUS      current 
    DESCRIPTION
        "" 
    ::=  { equipmentConfigAndStatus 4 }

moduleDataEntry OBJECT-TYPE
    SYNTAX      ModuleDataEntry
    MAX-ACCESS  not-accessible
    STATUS      current 
    DESCRIPTION
        "" 
    INDEX       { entityIndex } 
    ::=  { moduleDataTable  1  }

ModuleDataEntry ::=  SEQUENCE
  { moduleDataDeploymentScenario FspR7DeploymentScenario }


  
moduleDataDeploymentScenario OBJECT-TYPE
    SYNTAX      FspR7DeploymentScenario
    MAX-ACCESS  read-only
    STATUS      current 
    DESCRIPTION
        "Describes how the card is applied related to a network scenario" 
    ::=  { moduleDataEntry 1 }

wdmChannelModuleInventoryTable OBJECT-TYPE
    SYNTAX      SEQUENCE OF WdmChannelModuleInventoryEntry
    MAX-ACCESS  not-accessible
    STATUS      current 
    DESCRIPTION
        "The WdmChannelModuleInventory table. This table extends the entries in
         the inventoryTable for the FspR7 wdmChannelModules." 
    ::=  { equipmentConfigAndStatus 5 }

wdmChannelModuleInventoryEntry OBJECT-TYPE
    SYNTAX      WdmChannelModuleInventoryEntry
    MAX-ACCESS  not-accessible
    STATUS      current 
    DESCRIPTION
        "An entry in the WdmChannelModuleInventory table. Each entry in this table
         represents a field replacable wdmChannelModule in a shelf, which is inserted
         into or removed from a container (slot)." 
    INDEX       { entityIndex } 
    ::=  { wdmChannelModuleInventoryTable  1  }

WdmChannelModuleInventoryEntry ::=  SEQUENCE
  { wdmChannelModuleInventoryChannelId FspR7ChannelIdentifier,
    wdmChannelModuleInventoryReach FspR7OpticalInterfaceReach }


  
wdmChannelModuleInventoryChannelId OBJECT-TYPE
    SYNTAX      FspR7ChannelIdentifier
    MAX-ACCESS  read-only
    STATUS      current 
    DESCRIPTION
        "The WDM channel identifier of the wdmChannelModule." 
    ::=  { wdmChannelModuleInventoryEntry 1 }

wdmChannelModuleInventoryReach OBJECT-TYPE
    SYNTAX      FspR7OpticalInterfaceReach
    MAX-ACCESS  read-only
    STATUS      current 
    DESCRIPTION
        "The optical reach of the wdmChannelModule." 
    ::=  { wdmChannelModuleInventoryEntry 2 }

wdmChannelModuleDataTable OBJECT-TYPE
    SYNTAX      SEQUENCE OF WdmChannelModuleDataEntry
    MAX-ACCESS  not-accessible
    STATUS      current 
    DESCRIPTION
        "The WdmChannelModuleData table. This table extends the entries
         in the inventoryTable for the FspR7 wdmChannelModules." 
    ::=  { equipmentConfigAndStatus 6 }

wdmChannelModuleDataEntry OBJECT-TYPE
    SYNTAX      WdmChannelModuleDataEntry
    MAX-ACCESS  not-accessible
    STATUS      current 
    DESCRIPTION
        "An entry in the WdmChannelModuleData table. Each entry in this table
         represents a field replacable wdmChannelModule in a shelf, which is
         inserted into or removed from a container (slot)." 
    INDEX       { entityIndex } 
    ::=  { wdmChannelModuleDataTable  1  }

WdmChannelModuleDataEntry ::=  SEQUENCE
  { wdmChannelModuleDataSuppClientPlugRates FspR7PlugDataRateCaps,
    wdmChannelModuleDataSuppNetworkPlugRates FspR7PlugDataRateCaps,
    wdmChannelModuleDataSuppClientPlugTypes FspR7EquipmentTypeCaps,
    wdmChannelModuleDataSuppNetworkPlugTypes FspR7EquipmentTypeCaps }


  
wdmChannelModuleDataSuppClientPlugRates OBJECT-TYPE
    SYNTAX      FspR7PlugDataRateCaps
    MAX-ACCESS  read-only
    STATUS      current 
    DESCRIPTION
        "The supported client plug rates of the wdmChannelModule." 
    ::=  { wdmChannelModuleDataEntry 1 }

wdmChannelModuleDataSuppNetworkPlugRates OBJECT-TYPE
    SYNTAX      FspR7PlugDataRateCaps
    MAX-ACCESS  read-only
    STATUS      current 
    DESCRIPTION
        "The supported network plug rates of the wdmChannelModule." 
    ::=  { wdmChannelModuleDataEntry 2 }

wdmChannelModuleDataSuppClientPlugTypes OBJECT-TYPE
    SYNTAX      FspR7EquipmentTypeCaps
    MAX-ACCESS  read-only
    STATUS      current 
    DESCRIPTION
        "The supported client plug types of the wdmChannelModule." 
    ::=  { wdmChannelModuleDataEntry 3 }

wdmChannelModuleDataSuppNetworkPlugTypes OBJECT-TYPE
    SYNTAX      FspR7EquipmentTypeCaps
    MAX-ACCESS  read-only
    STATUS      current 
    DESCRIPTION
        "The supported network plug types of the wdmChannelModule." 
    ::=  { wdmChannelModuleDataEntry 4 }

plugInventoryTable OBJECT-TYPE
    SYNTAX      SEQUENCE OF PlugInventoryEntry
    MAX-ACCESS  not-accessible
    STATUS      current 
    DESCRIPTION
        "The PlugInventory table. This table extends the entries
         in the inventoryTable for the FspR7 plugs (SFP/XFP). The data in this table
         only applies to equipped plugs." 
    ::=  { equipmentConfigAndStatus 7 }

plugInventoryEntry OBJECT-TYPE
    SYNTAX      PlugInventoryEntry
    MAX-ACCESS  not-accessible
    STATUS      current 
    DESCRIPTION
        "An entry in the PlugInventory table. Each entry in this table represents
         a field replacable plug in a card, which is inserted into or removed from
         a container (slot)." 
    INDEX       { entityIndex } 
    ::=  { plugInventoryTable  1  }

PlugInventoryEntry ::=  SEQUENCE
  { plugInventoryMaxDataRate FspR7PlugDataRate,
    plugInventoryChannelId FspR7ChannelIdentifier,
    plugInventoryReach FspR7OpticalInterfaceReach }


  
plugInventoryMaxDataRate OBJECT-TYPE
    SYNTAX      FspR7PlugDataRate
    MAX-ACCESS  read-only
    STATUS      current 
    DESCRIPTION
        "The maximal supported data rate of the plug." 
    ::=  { plugInventoryEntry 1 }

plugInventoryChannelId OBJECT-TYPE
    SYNTAX      FspR7ChannelIdentifier
    MAX-ACCESS  read-only
    STATUS      current 
    DESCRIPTION
        "The supported optical channel of the plug." 
    ::=  { plugInventoryEntry 2 }

plugInventoryReach OBJECT-TYPE
    SYNTAX      FspR7OpticalInterfaceReach
    MAX-ACCESS  read-only
    STATUS      current 
    DESCRIPTION
        "The supported optical reach of the plug." 
    ::=  { plugInventoryEntry 3 }

plugDataTable OBJECT-TYPE
    SYNTAX      SEQUENCE OF PlugDataEntry
    MAX-ACCESS  not-accessible
    STATUS      current 
    DESCRIPTION
        "The plugData table. This table extends the entries
         in the entityTable for the FspR7 plugs (SFP/XFP)." 
    ::=  { equipmentConfigAndStatus 8 }

plugDataEntry OBJECT-TYPE
    SYNTAX      PlugDataEntry
    MAX-ACCESS  not-accessible
    STATUS      current 
    DESCRIPTION
        "An entry in the plugData table. Each entry in this table represents
         a field replacable plug in a card, which may be inserted into or
         removed from a container (slot)." 
    INDEX       { entityIndex } 
    ::=  { plugDataTable  1  }

PlugDataEntry ::=  SEQUENCE
  { plugDataConnectorType FspR7ConnectorType,
    plugDataFiberType FspR7OpticalFiberType }


  
plugDataConnectorType OBJECT-TYPE
    SYNTAX      FspR7ConnectorType
    MAX-ACCESS  read-only
    STATUS      current 
    DESCRIPTION
        "The type of external connector on a plug
         (eg. SC, LC, RJ45, etc)." 
    ::=  { plugDataEntry 1 }

plugDataFiberType OBJECT-TYPE
    SYNTAX      FspR7OpticalFiberType
    MAX-ACCESS  read-only
    STATUS      current 
    DESCRIPTION
        "The fiber type of this plug." 
    ::=  { plugDataEntry 2 }

apsConfigTable OBJECT-TYPE
    SYNTAX      SEQUENCE OF ApsConfigEntry
    MAX-ACCESS  not-accessible
    STATUS      current 
    DESCRIPTION
        "This table contains attributes related to the automatic
         protection switching (APS) functionality." 
    ::=  { equipmentConfigAndStatus 9 }

apsConfigEntry OBJECT-TYPE
    SYNTAX      ApsConfigEntry
    MAX-ACCESS  not-accessible
    STATUS      current 
    DESCRIPTION
        "An entry in the APS configuration table. There is one entry
         in this table for each FFP-x protection group." 
    INDEX       { entityIndex } 
    ::=  { apsConfigTable  1  }

ApsConfigEntry ::=  SEQUENCE
  { apsConfigSDswitching EnableState,
    apsConfigHoldOffTime ApsHoldoffTime }


  
apsConfigSDswitching OBJECT-TYPE
    SYNTAX      EnableState
    MAX-ACCESS  read-write
    STATUS      current 
    DESCRIPTION
        "This state controls whether the switch criteria for the
         APS group will include the Signal
         Degrade alarm." 
    ::=  { apsConfigEntry 1 }

apsConfigHoldOffTime OBJECT-TYPE
    SYNTAX      ApsHoldoffTime
    MAX-ACCESS  read-write
    STATUS      current 
    DESCRIPTION
        "This value controls the switch delay (0 to 90 seconds in
         100ms steps) for the protection group. Changing the hold-off
         time when the timer is active will not affect the active
         timer. The change will take effect the next time the timer
         is active." 
    ::=  { apsConfigEntry 2 }

apsProtGroupStatusTable OBJECT-TYPE
    SYNTAX      SEQUENCE OF ApsProtGroupStatusEntry
    MAX-ACCESS  not-accessible
    STATUS      current 
    DESCRIPTION
        "This table contains status information related to the automatic
         protection switching (APS) functionality." 
    ::=  { equipmentConfigAndStatus 10 }

apsProtGroupStatusEntry OBJECT-TYPE
    SYNTAX      ApsProtGroupStatusEntry
    MAX-ACCESS  not-accessible
    STATUS      current 
    DESCRIPTION
        "An entry in the APS status table. There is one entry
         in this table for each FFP-x protection group." 
    INDEX       { entityIndex } 
    ::=  { apsProtGroupStatusTable  1  }

ApsProtGroupStatusEntry ::=  SEQUENCE
  { apsProtGroupStatusApsType ApsType,
    apsProtGroupStatusDirection ApsDirection,
    apsProtGroupStatusRevertiveMode ApsRevertMode,
    apsProtGroupStatusProtectionMech ProtectionMech,
    apsProtGroupStatusWorkingIndex EntityIndex,
    apsProtGroupStatusProtectionIndex EntityIndex,
    apsProtGroupStatusProtectionType FspR7ProtectionType }


  
apsProtGroupStatusApsType OBJECT-TYPE
    SYNTAX      ApsType
    MAX-ACCESS  read-only
    STATUS      current 
    DESCRIPTION
        "The type of APS implemented in this protection group." 
    ::=  { apsProtGroupStatusEntry 1 }

apsProtGroupStatusDirection OBJECT-TYPE
    SYNTAX      ApsDirection
    MAX-ACCESS  read-only
    STATUS      current 
    DESCRIPTION
        "Indicates whether the APS function is 'unidirectional'
         (single-ended) or 'bidirectional' (dual-ended)." 
    ::=  { apsProtGroupStatusEntry 2 }

apsProtGroupStatusRevertiveMode OBJECT-TYPE
    SYNTAX      ApsRevertMode
    MAX-ACCESS  read-only
    STATUS      current 
    DESCRIPTION
        "Indicates if revertive switching is enable dor disabled." 
    ::=  { apsProtGroupStatusEntry 3 }

apsProtGroupStatusProtectionMech OBJECT-TYPE
    SYNTAX      ProtectionMech
    MAX-ACCESS  read-only
    STATUS      current 
    DESCRIPTION
        "The protection type of this protection group." 
    ::=  { apsProtGroupStatusEntry 4 }

apsProtGroupStatusWorkingIndex OBJECT-TYPE
    SYNTAX      EntityIndex
    MAX-ACCESS  read-only
    STATUS      current 
    DESCRIPTION
        "The entityIndex of the working section in the APS group." 
    ::=  { apsProtGroupStatusEntry 5 }

apsProtGroupStatusProtectionIndex OBJECT-TYPE
    SYNTAX      EntityIndex
    MAX-ACCESS  read-only
    STATUS      current 
    DESCRIPTION
        "The entityIndex of the protection section. The protection section will
         become the active section when an APS switch occurs (ie, as a result of
         a failure on the working section)." 
    ::=  { apsProtGroupStatusEntry 6 }

apsProtGroupStatusProtectionType OBJECT-TYPE
    SYNTAX      FspR7ProtectionType
    MAX-ACCESS  read-only
    STATUS      current 
    DESCRIPTION
        "This describes the topology and level of the protection (OCH or
         OM -Level on a ring; Line in PT-PT and Line or Dualhomed on a Feeder)." 
    ::=  { apsProtGroupStatusEntry 7 }

apsProtFacilityConfigTable OBJECT-TYPE
    SYNTAX      SEQUENCE OF ApsProtFacilityConfigEntry
    MAX-ACCESS  not-accessible
    STATUS      current 
    DESCRIPTION
        "This table contains attributes related to the automatic
         protection switching (APS) functionality on a facility involved
         in a protection group." 
    ::=  { equipmentConfigAndStatus 11 }

apsProtFacilityConfigEntry OBJECT-TYPE
    SYNTAX      ApsProtFacilityConfigEntry
    MAX-ACCESS  not-accessible
    STATUS      current 
    DESCRIPTION
        "An entry in the APS configuration table. There is one entry
         in this table for each facility involved in a protection group." 
    INDEX       { entityIndex } 
    ::=  { apsProtFacilityConfigTable  1  }

ApsProtFacilityConfigEntry ::=  SEQUENCE
  { apsProtFacilityConfigSwitchCommand FspR7APSCommand,
    apsProtFacilityConfigInhibitSwitchToProt FspR7YesNo,
    apsProtFacilityConfigInhibitSwitchToWork FspR7YesNo }


  
apsProtFacilityConfigSwitchCommand OBJECT-TYPE
    SYNTAX      FspR7APSCommand
    MAX-ACCESS  read-write
    STATUS      current 
    DESCRIPTION
        "The switch command action for this facility. A command
         resulting in a switch event will also cause a change of
         the facility secondary state and a corresponding condition.
         Addressed by this command is the active port, the port to switch away from.
         Since this is a manual switch command, it will not switch if other port
         suffers from a signalfailure or a signal degrade." 
    ::=  { apsProtFacilityConfigEntry 1 }

apsProtFacilityConfigInhibitSwitchToProt OBJECT-TYPE
    SYNTAX      FspR7YesNo
    MAX-ACCESS  read-write
    STATUS      current 
    DESCRIPTION
        "Inhibit Switch to protection facility. Inhibition blocks an automatic switch
         to the protection facility. Valid only for the working facility." 
    ::=  { apsProtFacilityConfigEntry 2 }

apsProtFacilityConfigInhibitSwitchToWork OBJECT-TYPE
    SYNTAX      FspR7YesNo
    MAX-ACCESS  read-write
    STATUS      current 
    DESCRIPTION
        "Inhibit Switch to working facility. Inhibition blocks an automatic switch
         to the working facility. Valid only for the protection facility." 
    ::=  { apsProtFacilityConfigEntry 3 }

shelfDiagnosticsTable OBJECT-TYPE
    SYNTAX      SEQUENCE OF ShelfDiagnosticsEntry
    MAX-ACCESS  not-accessible
    STATUS      current 
    DESCRIPTION
        "The ShelfDiagnostics table. This table extends the entries
         in the inventoryTable for the FspR7 shelves." 
    ::=  { equipmentConfigAndStatus 12 }

shelfDiagnosticsEntry OBJECT-TYPE
    SYNTAX      ShelfDiagnosticsEntry
    MAX-ACCESS  not-accessible
    STATUS      current 
    DESCRIPTION
        "An entry in the ShelfDiagnostics table. Each entry in this table
         represents a shelf." 
    INDEX       { entityIndex } 
    ::=  { shelfDiagnosticsTable  1  }

ShelfDiagnosticsEntry ::=  SEQUENCE
  { shelfDiagnosticsPowerConsumption Unsigned32,
    shelfDiagnosticsPowerOutput Unsigned32 }


  
shelfDiagnosticsPowerConsumption OBJECT-TYPE
    SYNTAX      Unsigned32
    UNITS       "W"
    MAX-ACCESS  read-only
    STATUS      current 
    DESCRIPTION
        "Actual power consumption of the shelf." 
    ::=  { shelfDiagnosticsEntry 1 }

shelfDiagnosticsPowerOutput OBJECT-TYPE
    SYNTAX      Unsigned32
    UNITS       "W"
    MAX-ACCESS  read-only
    STATUS      current 
    DESCRIPTION
        "Actual power output of the shelf." 
    ::=  { shelfDiagnosticsEntry 2 }

dcnTopologyDataTable OBJECT-TYPE
    SYNTAX      SEQUENCE OF DcnTopologyDataEntry
    MAX-ACCESS  not-accessible
    STATUS      current 
    DESCRIPTION
        "" 
    ::=  { equipmentConfigAndStatus 13 }

dcnTopologyDataEntry OBJECT-TYPE
    SYNTAX      DcnTopologyDataEntry
    MAX-ACCESS  not-accessible
    STATUS      current 
    DESCRIPTION
        "List of detected nodes in the DCN topology." 
    INDEX       { entityIndex,dcnTopologyDataIndex } 
    ::=  { dcnTopologyDataTable  1  }

DcnTopologyDataEntry ::=  SEQUENCE
  { dcnTopologyDataIndex Unsigned32,
    dcnTopologyDataNodeIpAddress IpAddress }


  
dcnTopologyDataIndex OBJECT-TYPE
    SYNTAX      Unsigned32
    MAX-ACCESS  not-accessible
    STATUS      current 
    DESCRIPTION
        "" 
    ::=  { dcnTopologyDataEntry 1 }

dcnTopologyDataNodeIpAddress OBJECT-TYPE
    SYNTAX      IpAddress
    MAX-ACCESS  read-only
    STATUS      current 
    DESCRIPTION
        "List of IP Addresses, Position of list is the internal NODE-ID in the ring" 
    ::=  { dcnTopologyDataEntry 2 }

dcnTopologyConfigTable OBJECT-TYPE
    SYNTAX      SEQUENCE OF DcnTopologyConfigEntry
    MAX-ACCESS  not-accessible
    STATUS      current 
    DESCRIPTION
        "" 
    ::=  { equipmentConfigAndStatus 14 }

dcnTopologyConfigEntry OBJECT-TYPE
    SYNTAX      DcnTopologyConfigEntry
    MAX-ACCESS  not-accessible
    STATUS      current 
    DESCRIPTION
        "" 
    INDEX       { entityIndex } 
    ::=  { dcnTopologyConfigTable  1  }

DcnTopologyConfigEntry ::=  SEQUENCE
  { dcnTopologyConfigActivateDetect FspR7YesNo }


  
dcnTopologyConfigActivateDetect OBJECT-TYPE
    SYNTAX      FspR7YesNo
    MAX-ACCESS  read-write
    STATUS      current 
    DESCRIPTION
        "Initialize Topology Detection" 
    ::=  { dcnTopologyConfigEntry 1 }

dcnTopologyStatusTable OBJECT-TYPE
    SYNTAX      SEQUENCE OF DcnTopologyStatusEntry
    MAX-ACCESS  not-accessible
    STATUS      current 
    DESCRIPTION
        "" 
    ::=  { equipmentConfigAndStatus 15 }

dcnTopologyStatusEntry OBJECT-TYPE
    SYNTAX      DcnTopologyStatusEntry
    MAX-ACCESS  not-accessible
    STATUS      current 
    DESCRIPTION
        "" 
    INDEX       { entityIndex } 
    ::=  { dcnTopologyStatusTable  1  }

DcnTopologyStatusEntry ::=  SEQUENCE
  { dcnTopologyStatusTopologyType FspR7TopologyType }


  
dcnTopologyStatusTopologyType OBJECT-TYPE
    SYNTAX      FspR7TopologyType
    MAX-ACCESS  read-only
    STATUS      current 
    DESCRIPTION
        "Monitored Topology Type" 
    ::=  { dcnTopologyStatusEntry 1 }

edfaDiagnosticsTable OBJECT-TYPE
    SYNTAX      SEQUENCE OF EdfaDiagnosticsEntry
    MAX-ACCESS  not-accessible
    STATUS      current 
    DESCRIPTION
        "" 
    ::=  { equipmentConfigAndStatus 19 }

edfaDiagnosticsEntry OBJECT-TYPE
    SYNTAX      EdfaDiagnosticsEntry
    MAX-ACCESS  not-accessible
    STATUS      current 
    DESCRIPTION
        "" 
    INDEX       { entityIndex } 
    ::=  { edfaDiagnosticsTable  1  }

EdfaDiagnosticsEntry ::=  SEQUENCE
  { edfaDiagnosticsSubTemp Integer32,
    edfaDiagnosticsUpperSubTempThres Integer32 }


  
edfaDiagnosticsSubTemp OBJECT-TYPE
    SYNTAX      Integer32
    UNITS       "0.1 °C"
    MAX-ACCESS  read-only
    STATUS      current 
    DESCRIPTION
        "Submodule Temperature" 
    ::=  { edfaDiagnosticsEntry 1 }

edfaDiagnosticsUpperSubTempThres OBJECT-TYPE
    SYNTAX      Integer32
    UNITS       "0.1 °C"
    MAX-ACCESS  read-only
    STATUS      current 
    DESCRIPTION
        "Submodule High Temperature Threshold" 
    ::=  { edfaDiagnosticsEntry 2 }

shelfConfigTable OBJECT-TYPE
    SYNTAX      SEQUENCE OF ShelfConfigEntry
    MAX-ACCESS  not-accessible
    STATUS      current 
    DESCRIPTION
        "" 
    ::=  { equipmentConfigAndStatus 20 }

shelfConfigEntry OBJECT-TYPE
    SYNTAX      ShelfConfigEntry
    MAX-ACCESS  not-accessible
    STATUS      current 
    DESCRIPTION
        "" 
    INDEX       { entityIndex } 
    ::=  { shelfConfigTable  1  }

ShelfConfigEntry ::=  SEQUENCE
  { shelfConfigRack SnmpAdminString }


  
shelfConfigRack OBJECT-TYPE
    SYNTAX      SnmpAdminString
    MAX-ACCESS  read-write
    STATUS      current 
    DESCRIPTION
        "Rack Containing Shelf" 
    ::=  { shelfConfigEntry 1 }

interfaceConfigTable OBJECT-TYPE
    SYNTAX      SEQUENCE OF InterfaceConfigEntry
    MAX-ACCESS  not-accessible
    STATUS      current 
    DESCRIPTION
        "Contains entries for the configuration of interfaces.
         This table extends the entries in
         the ifTable (RFC 2863)." 
    ::=  { interfaceConfigAndStatus 1 }

interfaceConfigEntry OBJECT-TYPE
    SYNTAX      InterfaceConfigEntry
    MAX-ACCESS  not-accessible
    STATUS      current 
    DESCRIPTION
        "The gpiTTP and ocTTP interfaces will have an entry
         in this table." 
    INDEX       { entityIndex } 
    ::=  { interfaceConfigTable  1  }

InterfaceConfigEntry ::=  SEQUENCE
  { interfaceConfigIdentifier SnmpAdminString,
    interfaceConfigLoopConfig LoopConfig }


  
interfaceConfigIdentifier OBJECT-TYPE
    SYNTAX      SnmpAdminString
    MAX-ACCESS  read-write
    STATUS      current 
    DESCRIPTION
        "A string, configurable by the operator, containing a
         symbolic name for the trail which is terminated at
         this interface." 
    ::=  { interfaceConfigEntry 1 }

interfaceConfigLoopConfig OBJECT-TYPE
    SYNTAX      LoopConfig
    MAX-ACCESS  read-write
    STATUS      current 
    DESCRIPTION
        "The configuration of the loopback function.
         - noLoop: no loop configuration on the interface.
         - lineLoop: the incoming signal is looped to the outgoing
         line on the interface. The incoming signal is sent
         in the downstream direction and processed as normal.
         - inwardLoop: the output signal is looped to the incoming line
         on the interface. The looped signal is transmitted
         unchanged on the optical output." 
    ::=  { interfaceConfigEntry 2 }

interfaceDataTable OBJECT-TYPE
    SYNTAX      SEQUENCE OF InterfaceDataEntry
    MAX-ACCESS  not-accessible
    STATUS      current 
    DESCRIPTION
        "Contains entries for the configuration of interfaces.
         This table extends the entries in
         the ifTable (RFC 2863)." 
    ::=  { interfaceConfigAndStatus 2 }

interfaceDataEntry OBJECT-TYPE
    SYNTAX      InterfaceDataEntry
    MAX-ACCESS  not-accessible
    STATUS      current 
    DESCRIPTION
        "The gpiTTP and ocTTP interfaces will have an entry
         in this table." 
    INDEX       { entityIndex } 
    ::=  { interfaceDataTable  1  }

InterfaceDataEntry ::=  SEQUENCE
  { interfaceDataConnector FspR7ConnectorType,
    interfaceDataSignalMapping FspR7SignalMapping,
    interfaceDataRate Unsigned32,
    interfaceDataBehaviour FspR7PortBehaviour,
    interfaceDataTermLevel OhTerminationLevel,
    interfaceDataConnectionType FspR7TypeConnection,
    interfaceDataMonLevel OhTerminationLevel,
    interfaceDataValidSignalTimer Unsigned32,
    interfaceDataPayload OtnPayloadType,
    interfaceDataParity FspR7ParityBit }


  
interfaceDataConnector OBJECT-TYPE
    SYNTAX      FspR7ConnectorType
    MAX-ACCESS  read-only
    STATUS      current 
    DESCRIPTION
        "The textual description of the external connector type
         provided for an interface (eg. SC, LC, RJ45, etc)." 
    ::=  { interfaceDataEntry 1 }

interfaceDataSignalMapping OBJECT-TYPE
    SYNTAX      FspR7SignalMapping
    MAX-ACCESS  read-only
    STATUS      deprecated
    DESCRIPTION
        "The signal mapping of the interface." 
    ::=  { interfaceDataEntry 2 }

interfaceDataRate OBJECT-TYPE
    SYNTAX      Unsigned32
    UNITS       "Mbit/s"
    MAX-ACCESS  read-only
    STATUS      current 
    DESCRIPTION
        "The data rate configured for this interface." 
    ::=  { interfaceDataEntry 3 }

interfaceDataBehaviour OBJECT-TYPE
    SYNTAX      FspR7PortBehaviour
    MAX-ACCESS  read-only
    STATUS      current 
    DESCRIPTION
        "The configured behaviour of the interface. If configured as a network interface,
         the interface will use a WDM laser, and configuration restrictions may apply." 
    ::=  { interfaceDataEntry 4 }

interfaceDataTermLevel OBJECT-TYPE
    SYNTAX      OhTerminationLevel
    MAX-ACCESS  read-only
    STATUS      current 
    DESCRIPTION
        "Configures the signal overhead termination level of the interface." 
    ::=  { interfaceDataEntry 5 }

interfaceDataConnectionType OBJECT-TYPE
    SYNTAX      FspR7TypeConnection
    MAX-ACCESS  read-only
    STATUS      current 
    DESCRIPTION
        "Uni- or bidirectional traffic." 
    ::=  { interfaceDataEntry 6 }

interfaceDataMonLevel OBJECT-TYPE
    SYNTAX      OhTerminationLevel
    MAX-ACCESS  read-only
    STATUS      current 
    DESCRIPTION
        "Shows highest protocol layer which can be monitored. 
         The value of this parameter will depend on the interfaceDataTermLevel." 
    ::=  { interfaceDataEntry 7 }

interfaceDataValidSignalTimer OBJECT-TYPE
    SYNTAX      Unsigned32 (0..5760)
    UNITS       "min"
    MAX-ACCESS  read-only
    STATUS      current 
    DESCRIPTION
        "AINS state signal quality soak time remaining until transition to IS." 
    ::=  { interfaceDataEntry 8 }

interfaceDataPayload OBJECT-TYPE
    SYNTAX      OtnPayloadType
    MAX-ACCESS  read-only
    STATUS      current 
    DESCRIPTION
        "The PAYLOAD defines the transport service type of the payload,
         which may be transparent at this layer or with protocol-dependent
         behaviour. (Only relevant where TYPE = OTU#)." 
    ::=  { interfaceDataEntry 9 }

interfaceDataParity OBJECT-TYPE
    SYNTAX      FspR7ParityBit
    MAX-ACCESS  read-only
    STATUS      current 
    DESCRIPTION
        "Parity Bit Settings" 
    ::=  { interfaceDataEntry 10 }

opticalIfConfigTable OBJECT-TYPE
    SYNTAX      SEQUENCE OF OpticalIfConfigEntry
    MAX-ACCESS  not-accessible
    STATUS      current 
    DESCRIPTION
        "Contains entries for the configuration of optical interfaces. This table extends
         the entries in the ifTable (RFC 2863)." 
    ::=  { interfaceConfigAndStatus 3 }

opticalIfConfigEntry OBJECT-TYPE
    SYNTAX      OpticalIfConfigEntry
    MAX-ACCESS  not-accessible
    STATUS      current 
    DESCRIPTION
        "Only the gpiTTP and ocTTP optical interfaces will have
         an entry in this table." 
    INDEX       { entityIndex } 
    ::=  { opticalIfConfigTable  1  }

OpticalIfConfigEntry ::=  SEQUENCE
  { opticalIfConfigAlsMode FspR7AlsMode,
    opticalIfConfigErrorForwarding FspR7ErrorFwdMode,
    opticalIfConfigFecType FspR7FecType,
    opticalIfConfigLaserOffDelayFunction EnableState,
    opticalIfConfigForceLaserOn FspR7LaserForcedOperation }


  
opticalIfConfigAlsMode OBJECT-TYPE
    SYNTAX      FspR7AlsMode
    MAX-ACCESS  read-write
    STATUS      current 
    DESCRIPTION
        "A configuration request for the Automatic Laser Shutdown (ALS)
         function. Refer to FspR7AlsMode Textual Convention for details." 
    ::=  { opticalIfConfigEntry 1 }

opticalIfConfigErrorForwarding OBJECT-TYPE
    SYNTAX      FspR7ErrorFwdMode
    MAX-ACCESS  read-write
    STATUS      current 
    DESCRIPTION
        "A configuration request for the error forwarding
         function. Refer to FspR7ErrorFwdMode Textual Convention for details." 
    ::=  { opticalIfConfigEntry 2 }

opticalIfConfigFecType OBJECT-TYPE
    SYNTAX      FspR7FecType
    MAX-ACCESS  read-write
    STATUS      current 
    DESCRIPTION
        "Configuration of FEC type." 
    ::=  { opticalIfConfigEntry 3 }

opticalIfConfigLaserOffDelayFunction OBJECT-TYPE
    SYNTAX      EnableState
    MAX-ACCESS  read-write
    STATUS      current 
    DESCRIPTION
        "A configuration request for the Laser Off Delay function. This function delays
         turning off the laser as a consequent action to a defect." 
    ::=  { opticalIfConfigEntry 4 }

opticalIfConfigForceLaserOn OBJECT-TYPE
    SYNTAX      FspR7LaserForcedOperation
    MAX-ACCESS  read-write
    STATUS      current 
    DESCRIPTION
        "Laser Forced On" 
    ::=  { opticalIfConfigEntry 5 }

opticalIfDataTable OBJECT-TYPE
    SYNTAX      SEQUENCE OF OpticalIfDataEntry
    MAX-ACCESS  not-accessible
    STATUS      current 
    DESCRIPTION
        "Contains entries for optical interfaces.
         This table extends the entries in the ifTable (RFC 2863)." 
    ::=  { interfaceConfigAndStatus 4 }

opticalIfDataEntry OBJECT-TYPE
    SYNTAX      OpticalIfDataEntry
    MAX-ACCESS  not-accessible
    STATUS      current 
    DESCRIPTION
        "." 
    INDEX       { entityIndex } 
    ::=  { opticalIfDataTable  1  }

OpticalIfDataEntry ::=  SEQUENCE
  { opticalIfDataWdmChannel FspR7ChannelIdentifier,
    opticalIfDataWavelength SnmpAdminString,
    opticalIfDataFiberType FspR7OpticalFiberType,
    opticalIfDataLinkLength FspR7OpticalInterfaceReach,
    opticalIfDataAlsHoldoff FspR7AlsHoldoff,
    opticalIfDataLaserOffDelayTime FspR7LaserOffDelayTime,
    opticalIfDataProtectionRole FspR7ProtectionRole }


  
opticalIfDataWdmChannel OBJECT-TYPE
    SYNTAX      FspR7ChannelIdentifier
    MAX-ACCESS  read-only
    STATUS      current 
    DESCRIPTION
        "The WDM channel, as per ADVA grid, of this interface." 
    ::=  { opticalIfDataEntry 1 }

opticalIfDataWavelength OBJECT-TYPE
    SYNTAX      SnmpAdminString
    MAX-ACCESS  read-only
    STATUS      current 
    DESCRIPTION
        "The transmit wavelength of this interface." 
    ::=  { opticalIfDataEntry 2 }

opticalIfDataFiberType OBJECT-TYPE
    SYNTAX      FspR7OpticalFiberType
    MAX-ACCESS  read-only
    STATUS      current 
    DESCRIPTION
        "The fiber type of this interface.
         For interface modules not supporting Fibre Channel
         Transmission, the value will be 'unspecified'." 
    ::=  { opticalIfDataEntry 3 }

opticalIfDataLinkLength OBJECT-TYPE
    SYNTAX      FspR7OpticalInterfaceReach
    MAX-ACCESS  read-only
    STATUS      current 
    DESCRIPTION
        "The link length of this interface in km. This attribute can be
         used, ie, to indicate an intra-office application." 
    ::=  { opticalIfDataEntry 4 }

opticalIfDataAlsHoldoff OBJECT-TYPE
    SYNTAX      FspR7AlsHoldoff
    MAX-ACCESS  read-only
    STATUS      current 
    DESCRIPTION
        "Refer to FspR7AlsHoldoff Textual Convention for details." 
    ::=  { opticalIfDataEntry 5 }

opticalIfDataLaserOffDelayTime OBJECT-TYPE
    SYNTAX      FspR7LaserOffDelayTime
    MAX-ACCESS  read-only
    STATUS      current 
    DESCRIPTION
        "Laser Off Delay function. This function delays turning off the laser
         as a consequent action to a defect." 
    ::=  { opticalIfDataEntry 6 }

opticalIfDataProtectionRole OBJECT-TYPE
    SYNTAX      FspR7ProtectionRole
    MAX-ACCESS  read-only
    STATUS      current 
    DESCRIPTION
        "The Path is Labelled Working or Protection" 
    ::=  { opticalIfDataEntry 7 }

opticalIfDiagTable OBJECT-TYPE
    SYNTAX      SEQUENCE OF OpticalIfDiagEntry
    MAX-ACCESS  not-accessible
    STATUS      current 
    DESCRIPTION
        "Contains diagnostic entries for optical interfaces.
         This table extends the entries in the
         ifTable (RFC 2863)." 
    ::=  { interfaceConfigAndStatus 5 }

opticalIfDiagEntry OBJECT-TYPE
    SYNTAX      OpticalIfDiagEntry
    MAX-ACCESS  not-accessible
    STATUS      current 
    DESCRIPTION
        "" 
    INDEX       { entityIndex } 
    ::=  { opticalIfDiagTable  1  }

OpticalIfDiagEntry ::=  SEQUENCE
  { opticalIfDiagLaserBiasCurrentNormalized Unsigned32,
    opticalIfDiagLaserTemp Integer32,
    opticalIfDiagInputPower Integer32,
    opticalIfDiagOutputPower Integer32,
    opticalIfDiagLaserBiasCurrentLevel Unsigned32 }


  
opticalIfDiagLaserBiasCurrentNormalized OBJECT-TYPE
    SYNTAX      Unsigned32
    UNITS       "%"
    MAX-ACCESS  read-only
    STATUS      current 
    DESCRIPTION
        "Instantaneous Laser Bias Current Normalized" 
    ::=  { opticalIfDiagEntry 1 }

opticalIfDiagLaserTemp OBJECT-TYPE
    SYNTAX      Integer32
    UNITS       "0.1 °C"
    MAX-ACCESS  read-only
    STATUS      current 
    DESCRIPTION
        "The laser temperature, measured with
         a granularity of 0.1 degree Celsius" 
    ::=  { opticalIfDiagEntry 2 }

opticalIfDiagInputPower OBJECT-TYPE
    SYNTAX      Integer32
    UNITS       "0.1 dBm"
    MAX-ACCESS  read-only
    STATUS      current 
    DESCRIPTION
        "The optical input power of a transmitter in dBm,
         measured in the range of -x to +y dBm (TBD).
         It is only valid when there is no loss of signal at the input,
         in which case a value of -65535 is returned.
         A value of -65535 also indicates that OIP is not available.
         When out of range, -65534 indicates that the OIP is outside
         the maximum value and -65533 for outside the minimum value." 
    ::=  { opticalIfDiagEntry 3 }

opticalIfDiagOutputPower OBJECT-TYPE
    SYNTAX      Integer32
    UNITS       "0.1 dBm"
    MAX-ACCESS  read-only
    STATUS      current 
    DESCRIPTION
        "The optical output power of a transmitter in dBm,
         measured in the range of -x to +y dBm.(TBD)
         It is only valid when there the laserState is 'On'.
         If not, a value of -65535 is returned.
         A value of -65535 also indicates that OOP is not available.
         When out of range, -65534 indicates that the OOP is outside
         the maximum value and -65533 for outside the minimum value." 
    ::=  { opticalIfDiagEntry 4 }

opticalIfDiagLaserBiasCurrentLevel OBJECT-TYPE
    SYNTAX      Unsigned32
    UNITS       "0.001 A"
    MAX-ACCESS  read-only
    STATUS      current 
    DESCRIPTION
        "The actual current of the transmitter in mA.
         If the value is -65535, the current is not available." 
    ::=  { opticalIfDiagEntry 5 }

ethernetConfigTable OBJECT-TYPE
    SYNTAX      SEQUENCE OF EthernetConfigEntry
    MAX-ACCESS  not-accessible
    STATUS      current 
    DESCRIPTION
        "Contains entries for the Status information for Ethernet
         interfaces equipped on a Unit. This table extends the
         entries in the ifTable (RFC 2863)." 
    ::=  { interfaceConfigAndStatus 6 }

ethernetConfigEntry OBJECT-TYPE
    SYNTAX      EthernetConfigEntry
    MAX-ACCESS  not-accessible
    STATUS      current 
    DESCRIPTION
        "The objects in this table are used for configuration of the ethernet interface." 
    INDEX       { entityIndex } 
    ::=  { ethernetConfigTable  1  }

EthernetConfigEntry ::=  SEQUENCE
  { ethernetConfigAutoNegotiation EnableState,
    ethernetConfigDuplexMode EthDuplexMode,
    ethernetConfigBitrate FspR7Bitrate,
    ethernetConfigFlowControl FspR7FlowControlMode }


  
ethernetConfigAutoNegotiation OBJECT-TYPE
    SYNTAX      EnableState
    MAX-ACCESS  read-write
    STATUS      current 
    DESCRIPTION
        "The autoneg status of the ethernet layer.
         read-write if FspR7InterfaceType = ifTypeE10or100bt
         read-only if FspR7InterfaceType = ifTypeE100fx" 
    ::=  { ethernetConfigEntry 1 }

ethernetConfigDuplexMode OBJECT-TYPE
    SYNTAX      EthDuplexMode
    MAX-ACCESS  read-write
    STATUS      current 
    DESCRIPTION
        "The duplex configuration of the ethernet layer.
         read-write if FspR7InterfaceType = ifTypeE10or100bt
         read-only if FspR7InterfaceType = ifTypeE100fx" 
    ::=  { ethernetConfigEntry 2 }

ethernetConfigBitrate OBJECT-TYPE
    SYNTAX      FspR7Bitrate
    MAX-ACCESS  read-write
    STATUS      current 
    DESCRIPTION
        "The bite rate configuration of the ethernet layer.
         read-write if FspR7InterfaceType = ifTypeE10or100bt
         read-only if FspR7InterfaceType = ifTypeE100fx" 
    ::=  { ethernetConfigEntry 3 }

ethernetConfigFlowControl OBJECT-TYPE
    SYNTAX      FspR7FlowControlMode
    MAX-ACCESS  read-write
    STATUS      current 
    DESCRIPTION
        "Flow Control mechanism" 
    ::=  { ethernetConfigEntry 4 }

lanIpConfigTable OBJECT-TYPE
    SYNTAX      SEQUENCE OF LanIpConfigEntry
    MAX-ACCESS  not-accessible
    STATUS      current 
    DESCRIPTION
        "" 
    ::=  { interfaceConfigAndStatus 8 }

lanIpConfigEntry OBJECT-TYPE
    SYNTAX      LanIpConfigEntry
    MAX-ACCESS  not-accessible
    STATUS      current 
    DESCRIPTION
        "" 
    INDEX       { entityIndex } 
    ::=  { lanIpConfigTable  1  }

LanIpConfigEntry ::=  SEQUENCE
  { lanIpConfigIpAddr IpAddress,
    lanIpConfigIpAddrMask IpAddress }


  
lanIpConfigIpAddr OBJECT-TYPE
    SYNTAX      IpAddress
    MAX-ACCESS  read-write
    STATUS      current 
    DESCRIPTION
        "IP Address assigned to LAN IP Interface" 
    ::=  { lanIpConfigEntry 1 }

lanIpConfigIpAddrMask OBJECT-TYPE
    SYNTAX      IpAddress
    MAX-ACCESS  read-write
    STATUS      current 
    DESCRIPTION
        "IP MASK assigned to LAN IP Interface" 
    ::=  { lanIpConfigEntry 2 }

ospfConfigTable OBJECT-TYPE
    SYNTAX      SEQUENCE OF OspfConfigEntry
    MAX-ACCESS  not-accessible
    STATUS      current 
    DESCRIPTION
        "" 
    ::=  { interfaceConfigAndStatus 9 }

ospfConfigEntry OBJECT-TYPE
    SYNTAX      OspfConfigEntry
    MAX-ACCESS  not-accessible
    STATUS      current 
    DESCRIPTION
        "" 
    INDEX       { entityIndex } 
    ::=  { ospfConfigTable  1  }

OspfConfigEntry ::=  SEQUENCE
  { ospfConfigOspf EnableState,
    ospfConfigMetric Unsigned32 }


  
ospfConfigOspf OBJECT-TYPE
    SYNTAX      EnableState
    MAX-ACCESS  read-write
    STATUS      current 
    DESCRIPTION
        "OSPF Routing (Dynamic)" 
    ::=  { ospfConfigEntry 1 }

ospfConfigMetric OBJECT-TYPE
    SYNTAX      Unsigned32 (0..65535)
    MAX-ACCESS  read-write
    STATUS      current 
    DESCRIPTION
        "Routing Metric" 
    ::=  { ospfConfigEntry 2 }

ospfDataTable OBJECT-TYPE
    SYNTAX      SEQUENCE OF OspfDataEntry
    MAX-ACCESS  not-accessible
    STATUS      current 
    DESCRIPTION
        "" 
    ::=  { interfaceConfigAndStatus 10 }

ospfDataEntry OBJECT-TYPE
    SYNTAX      OspfDataEntry
    MAX-ACCESS  not-accessible
    STATUS      current 
    DESCRIPTION
        "" 
    INDEX       { entityIndex } 
    ::=  { ospfDataTable  1  }

OspfDataEntry ::=  SEQUENCE
  { ospfDataDesignatedRouter IpAddress,
    ospfDataBkupDesignatedRouter IpAddress }


  
ospfDataDesignatedRouter OBJECT-TYPE
    SYNTAX      IpAddress
    MAX-ACCESS  read-write
    STATUS      current 
    DESCRIPTION
        "IP Address of Designated Router" 
    ::=  { ospfDataEntry 1 }

ospfDataBkupDesignatedRouter OBJECT-TYPE
    SYNTAX      IpAddress
    MAX-ACCESS  read-write
    STATUS      current 
    DESCRIPTION
        "IP Address of BackUp Designated Router" 
    ::=  { ospfDataEntry 2 }

pppfConfigTable OBJECT-TYPE
    SYNTAX      SEQUENCE OF PppfConfigEntry
    MAX-ACCESS  not-accessible
    STATUS      current 
    DESCRIPTION
        "" 
    ::=  { interfaceConfigAndStatus 11 }

pppfConfigEntry OBJECT-TYPE
    SYNTAX      PppfConfigEntry
    MAX-ACCESS  not-accessible
    STATUS      current 
    DESCRIPTION
        "" 
    INDEX       { entityIndex } 
    ::=  { pppfConfigTable  1  }

PppfConfigEntry ::=  SEQUENCE
  { pppfConfigBitrate Unsigned32 }


  
pppfConfigBitrate OBJECT-TYPE
    SYNTAX      Unsigned32 (1..1312)
    UNITS       "Kbit/s"
    MAX-ACCESS  read-write
    STATUS      current 
    DESCRIPTION
        "Provisioned max. bitrate of transmitter in PPP Link established over ECC" 
    ::=  { pppfConfigEntry 1 }

pppDataTable OBJECT-TYPE
    SYNTAX      SEQUENCE OF PppDataEntry
    MAX-ACCESS  not-accessible
    STATUS      current 
    DESCRIPTION
        "" 
    ::=  { interfaceConfigAndStatus 12 }

pppDataEntry OBJECT-TYPE
    SYNTAX      PppDataEntry
    MAX-ACCESS  not-accessible
    STATUS      current 
    DESCRIPTION
        "" 
    INDEX       { entityIndex } 
    ::=  { pppDataTable  1  }

PppDataEntry ::=  SEQUENCE
  { pppDataNearEndIp IpAddress,
    pppDataFarEndIp IpAddress,
    pppDataEccInstance EntityIndex }


  
pppDataNearEndIp OBJECT-TYPE
    SYNTAX      IpAddress
    MAX-ACCESS  read-only
    STATUS      current 
    DESCRIPTION
        "IP Address assigned to PPP Termination Point on Near-End NE. Defaults to System IP address" 
    ::=  { pppDataEntry 1 }

pppDataFarEndIp OBJECT-TYPE
    SYNTAX      IpAddress
    MAX-ACCESS  read-only
    STATUS      current 
    DESCRIPTION
        "IP Address assigned to PPP Termination Point on Far-End NE. Default is set by NE System on LINK establishment if FENDIPACPT = Y" 
    ::=  { pppDataEntry 2 }

pppDataEccInstance OBJECT-TYPE
    SYNTAX      EntityIndex
    MAX-ACCESS  read-only
    STATUS      current 
    DESCRIPTION
        "Address Identifier of ECC Entity." 
    ::=  { pppDataEntry 3 }

crsDcnDataTable OBJECT-TYPE
    SYNTAX      SEQUENCE OF CrsDcnDataEntry
    MAX-ACCESS  not-accessible
    STATUS      current 
    DESCRIPTION
        "" 
    ::=  { interfaceConfigAndStatus 13 }

crsDcnDataEntry OBJECT-TYPE
    SYNTAX      CrsDcnDataEntry
    MAX-ACCESS  not-accessible
    STATUS      current 
    DESCRIPTION
        "" 
    INDEX       { entityIndex } 
    ::=  { crsDcnDataTable  1  }

CrsDcnDataEntry ::=  SEQUENCE
  { crsDcnDataPppInstance EntityIndex,
    crsDcnDataEccInstance EntityIndex }


  
crsDcnDataPppInstance OBJECT-TYPE
    SYNTAX      EntityIndex
    MAX-ACCESS  read-only
    STATUS      current 
    DESCRIPTION
        "Address Identifier of PPPIP LINK Entity." 
    ::=  { crsDcnDataEntry 1 }

crsDcnDataEccInstance OBJECT-TYPE
    SYNTAX      EntityIndex
    MAX-ACCESS  read-only
    STATUS      current 
    DESCRIPTION
        "Address Identifier of ECC Entity." 
    ::=  { crsDcnDataEntry 2 }

eocDataTable OBJECT-TYPE
    SYNTAX      SEQUENCE OF EocDataEntry
    MAX-ACCESS  not-accessible
    STATUS      current 
    DESCRIPTION
        "" 
    ::=  { interfaceConfigAndStatus 14 }

eocDataEntry OBJECT-TYPE
    SYNTAX      EocDataEntry
    MAX-ACCESS  not-accessible
    STATUS      current 
    DESCRIPTION
        "" 
    INDEX       { entityIndex } 
    ::=  { eocDataTable  1  }

EocDataEntry ::=  SEQUENCE
  { eocDataProtAvailability FspR7EocProtAvailability,
    eocDataIpEntity EntityIndex,
    eocDataMaxDataRate Unsigned32,
    eocDataConnectionType FspR7TypeConnection }


  
eocDataProtAvailability OBJECT-TYPE
    SYNTAX      FspR7EocProtAvailability
    MAX-ACCESS  read-only
    STATUS      current 
    DESCRIPTION
        "The availability of protection switching functionality on the EOC." 
    ::=  { eocDataEntry 1 }

eocDataIpEntity OBJECT-TYPE
    SYNTAX      EntityIndex
    MAX-ACCESS  read-only
    STATUS      current 
    DESCRIPTION
        "Address of IP Entity on Module with Router Capability to which the
         EOC is connected." 
    ::=  { eocDataEntry 2 }

eocDataMaxDataRate OBJECT-TYPE
    SYNTAX      Unsigned32
    UNITS       "kbps"
    MAX-ACCESS  read-only
    STATUS      current 
    DESCRIPTION
        "Max data rate of the EOC" 
    ::=  { eocDataEntry 3 }

eocDataConnectionType OBJECT-TYPE
    SYNTAX      FspR7TypeConnection
    MAX-ACCESS  read-only
    STATUS      current 
    DESCRIPTION
        "Uni- or bidirectional traffic." 
    ::=  { eocDataEntry 4 }

opticalIfOlmTable OBJECT-TYPE
    SYNTAX      SEQUENCE OF OpticalIfOlmEntry
    MAX-ACCESS  not-accessible
    STATUS      current 
    DESCRIPTION
        "Contains optical line monitoring entries for optical interfaces.
         This table extends the entries in the
         ifTable (RFC 2863)." 
    ::=  { interfaceConfigAndStatus 15 }

opticalIfOlmEntry OBJECT-TYPE
    SYNTAX      OpticalIfOlmEntry
    MAX-ACCESS  not-accessible
    STATUS      current 
    DESCRIPTION
        "" 
    INDEX       { entityIndex } 
    ::=  { opticalIfOlmTable  1  }

OpticalIfOlmEntry ::=  SEQUENCE
  { opticalIfOlmRxLineAttenuation Integer32,
    opticalIfOlmTxLineAttenuation Integer32,
    opticalIfOlmFarEndSigDegThres Unsigned32 }


  
opticalIfOlmRxLineAttenuation OBJECT-TYPE
    SYNTAX      Integer32
    UNITS       "0.1 dB"
    MAX-ACCESS  read-only
    STATUS      current 
    DESCRIPTION
        "The Attenuation (in 0.1 dB) on line connected to receiver
         of this interface. If there is loss of signal then ine
         attenuation is -65535. The value -255 will be returned if
         the value isn't available." 
    ::=  { opticalIfOlmEntry 1 }

opticalIfOlmTxLineAttenuation OBJECT-TYPE
    SYNTAX      Integer32
    UNITS       "0.1 dB"
    MAX-ACCESS  read-only
    STATUS      current 
    DESCRIPTION
        "The Attenuation (in 0.1 dB) on line connected to
         transmitter of this interface. If there is loss of signal
         then line attenuation is -65535. The value -255 will be
         returned if the value isn't available." 
    ::=  { opticalIfOlmEntry 2 }

opticalIfOlmFarEndSigDegThres OBJECT-TYPE
    SYNTAX      Unsigned32
    UNITS       "0.1 dB"
    MAX-ACCESS  read-only
    STATUS      current 
    DESCRIPTION
        "Far End Signal Degrade Threshold. Read only. Deliverd by a special ADVA propriatery OSC maintanance signaling." 
    ::=  { opticalIfOlmEntry 3 }

otdrConfigTable OBJECT-TYPE
    SYNTAX      SEQUENCE OF OtdrConfigEntry
    MAX-ACCESS  not-accessible
    STATUS      current 
    DESCRIPTION
        "" 
    ::=  { equipmentConfigAndStatus 16 }

otdrConfigEntry OBJECT-TYPE
    SYNTAX      OtdrConfigEntry
    MAX-ACCESS  not-accessible
    STATUS      current 
    DESCRIPTION
        "Configuration of OTDR analysis." 
    INDEX       { entityIndex } 
    ::=  { otdrConfigTable  1  }

OtdrConfigEntry ::=  SEQUENCE
  { otdrConfigTimePeriod FspR7OtdrPeriod }


  
otdrConfigTimePeriod OBJECT-TYPE
    SYNTAX      FspR7OtdrPeriod
    MAX-ACCESS  read-write
    STATUS      current 
    DESCRIPTION
        "NONE - OTDR measurement disabled otherwise the OTDR duration in minutes." 
    ::=  { otdrConfigEntry 1 }

otdrDataTable OBJECT-TYPE
    SYNTAX      SEQUENCE OF OtdrDataEntry
    MAX-ACCESS  not-accessible
    STATUS      current 
    DESCRIPTION
        "" 
    ::=  { equipmentConfigAndStatus 17 }

otdrDataEntry OBJECT-TYPE
    SYNTAX      OtdrDataEntry
    MAX-ACCESS  not-accessible
    STATUS      current 
    DESCRIPTION
        "" 
    INDEX       { entityIndex } 
    ::=  { otdrDataTable  1  }

OtdrDataEntry ::=  SEQUENCE
  { otdrDataRemainingTime Unsigned32 }


  
otdrDataRemainingTime OBJECT-TYPE
    SYNTAX      Unsigned32
    UNITS       "Min"
    MAX-ACCESS  read-only
    STATUS      current 
    DESCRIPTION
        "Time Remaining for Completion of OTDR Measurement. The timer is set by an Operation with parameter 'MEASURE'" 
    ::=  { otdrDataEntry 1 }

edfaConfigTableTable OBJECT-TYPE
    SYNTAX      SEQUENCE OF EdfaConfigTableEntry
    MAX-ACCESS  not-accessible
    STATUS      current 
    DESCRIPTION
        "" 
    ::=  { equipmentConfigAndStatus 18 }

edfaConfigTableEntry OBJECT-TYPE
    SYNTAX      EdfaConfigTableEntry
    MAX-ACCESS  not-accessible
    STATUS      current 
    DESCRIPTION
        "" 
    INDEX       { entityIndex } 
    ::=  { edfaConfigTableTable  1  }

EdfaConfigTableEntry ::=  SEQUENCE
  { edfaConfigTableTilt Integer32,
    edfaConfigTableGain FspR7Gain }


  
edfaConfigTableTilt OBJECT-TYPE
    SYNTAX      Integer32 (-20..0)
    UNITS       "0.1 dB"
    MAX-ACCESS  read-write
    STATUS      current 
    DESCRIPTION
        "Tilt." 
    ::=  { edfaConfigTableEntry 1 }

edfaConfigTableGain OBJECT-TYPE
    SYNTAX      FspR7Gain
    MAX-ACCESS  read-write
    STATUS      current 
    DESCRIPTION
        "Gain." 
    ::=  { edfaConfigTableEntry 2 }

edfaIfDiagnosticsTable OBJECT-TYPE
    SYNTAX      SEQUENCE OF EdfaIfDiagnosticsEntry
    MAX-ACCESS  not-accessible
    STATUS      current 
    DESCRIPTION
        "" 
    ::=  { interfaceConfigAndStatus 16 }

edfaIfDiagnosticsEntry OBJECT-TYPE
    SYNTAX      EdfaIfDiagnosticsEntry
    MAX-ACCESS  not-accessible
    STATUS      current 
    DESCRIPTION
        "" 
    INDEX       { entityIndex } 
    ::=  { edfaIfDiagnosticsTable  1  }

EdfaIfDiagnosticsEntry ::=  SEQUENCE
  { edfaIfDiagnosticsOperatingHours Unsigned32,
    edfaIfDiagnosticsLaserBiasCurrentLevelAverage Unsigned32,
    edfaIfDiagnosticsAttenuation Integer32 }


  
edfaIfDiagnosticsOperatingHours OBJECT-TYPE
    SYNTAX      Unsigned32
    MAX-ACCESS  read-only
    STATUS      current 
    DESCRIPTION
        "Accumulated total of Operating Hours" 
    ::=  { edfaIfDiagnosticsEntry 1 }

edfaIfDiagnosticsLaserBiasCurrentLevelAverage OBJECT-TYPE
    SYNTAX      Unsigned32
    UNITS       "0.001 A"
    MAX-ACCESS  read-only
    STATUS      current 
    DESCRIPTION
        "Accumulated Averaged Laser Bias Current Level." 
    ::=  { edfaIfDiagnosticsEntry 2 }

edfaIfDiagnosticsAttenuation OBJECT-TYPE
    SYNTAX      Integer32
    UNITS       "dB"
    MAX-ACCESS  read-only
    STATUS      current 
    DESCRIPTION
        "The attenuation in dB from the TRMT of the 1st stage to the RCV of the 2nd stage." 
    ::=  { edfaIfDiagnosticsEntry 3 }

opticalFilterIfDataTable OBJECT-TYPE
    SYNTAX      SEQUENCE OF OpticalFilterIfDataEntry
    MAX-ACCESS  not-accessible
    STATUS      current 
    DESCRIPTION
        "" 
    ::=  { interfaceConfigAndStatus 19 }

opticalFilterIfDataEntry OBJECT-TYPE
    SYNTAX      OpticalFilterIfDataEntry
    MAX-ACCESS  not-accessible
    STATUS      current 
    DESCRIPTION
        "" 
    INDEX       { entityIndex } 
    ::=  { opticalFilterIfDataTable  1  }

OpticalFilterIfDataEntry ::=  SEQUENCE
  { opticalFilterIfDataMultiplexLevel FspR7OpticalMultiplexLevel }


  
opticalFilterIfDataMultiplexLevel OBJECT-TYPE
    SYNTAX      FspR7OpticalMultiplexLevel
    MAX-ACCESS  read-only
    STATUS      current 
    DESCRIPTION
        "Optical Multiplex Level" 
    ::=  { opticalFilterIfDataEntry 1 }

ethernetDataTable OBJECT-TYPE
    SYNTAX      SEQUENCE OF EthernetDataEntry
    MAX-ACCESS  not-accessible
    STATUS      current 
    DESCRIPTION
        "" 
    ::=  { interfaceConfigAndStatus 17 }

ethernetDataEntry OBJECT-TYPE
    SYNTAX      EthernetDataEntry
    MAX-ACCESS  not-accessible
    STATUS      current 
    DESCRIPTION
        "" 
    INDEX       { entityIndex } 
    ::=  { ethernetDataTable  1  }

EthernetDataEntry ::=  SEQUENCE
  { ethernetDataMonitoredDuplexMode INTEGER,
    ethernetDataMonitoredBitrate Unsigned32 }


  
ethernetDataMonitoredDuplexMode OBJECT-TYPE
    SYNTAX      INTEGER
                {
                  undefined(0),
                  ethHalfDuplex(1),
                  ethFullDuplex(2)
                }
    MAX-ACCESS  read-only
    STATUS      current 
    DESCRIPTION
        "Monitored Duplex Mode. Available if AUTONEG=ENABLE" 
    ::=  { ethernetDataEntry 1 }

ethernetDataMonitoredBitrate OBJECT-TYPE
    SYNTAX      Unsigned32
    UNITS       "Mbit/s"
    MAX-ACCESS  read-only
    STATUS      current 
    DESCRIPTION
        "Read from card, - relevant to-auto clock" 
    ::=  { ethernetDataEntry 2 }

intraNeConnectionsLastChanged OBJECT-TYPE
    SYNTAX      INTEGER
                {
                  undefined(0),
                  notYetDefined(1)
                }
    MAX-ACCESS  read-only
    STATUS      current 
    DESCRIPTION
        "The Date and Time when the intraNeConnectionsTable was last updated." 
    ::=  { connectionConfigAndStatus 2 }

intraNeConnectionsTable OBJECT-TYPE
    SYNTAX      SEQUENCE OF IntraNeConnectionsEntry
    MAX-ACCESS  not-accessible
    STATUS      current 
    DESCRIPTION
        "Table containing the physical internal NE Connectivity, i.e. optical
         fiber connections between modules in the same NE." 
    ::=  { connectionConfigAndStatus 3 }

intraNeConnectionsEntry OBJECT-TYPE
    SYNTAX      IntraNeConnectionsEntry
    MAX-ACCESS  not-accessible
    STATUS      current 
    DESCRIPTION
        "Entries in the physical internal Connectivity table." 
    INDEX       { entityIndex } 
    ::=  { intraNeConnectionsTable  1  }

IntraNeConnectionsEntry ::=  SEQUENCE
  { intraNeConnectionsType FspR7TypeConnection,
    intraNeConnectionsEndpointA EntityIndex,
    intraNeConnectionsEndpointB EntityIndex }


  
intraNeConnectionsType OBJECT-TYPE
    SYNTAX      FspR7TypeConnection
    MAX-ACCESS  read-only
    STATUS      current 
    DESCRIPTION
        "Ports can transport uni- or bidirectional traffic." 
    ::=  { intraNeConnectionsEntry 1 }

intraNeConnectionsEndpointA OBJECT-TYPE
    SYNTAX      EntityIndex
    MAX-ACCESS  read-only
    STATUS      current 
    DESCRIPTION
        "FROM-end of equipment connection (jumper). FROM direction is significant only for 1WAY connections." 
    ::=  { intraNeConnectionsEntry 2 }

intraNeConnectionsEndpointB OBJECT-TYPE
    SYNTAX      EntityIndex
    MAX-ACCESS  read-only
    STATUS      current 
    DESCRIPTION
        "TO-end of equipment connection (jumper). TO direction is signaificant only for 1WAY" 
    ::=  { intraNeConnectionsEntry 3 }
gfpServiceConfigAndStatus   OBJECT IDENTIFIER ::= { serviceConfigAndStatus 1 }

vc4allocatedTable OBJECT-TYPE
    SYNTAX      SEQUENCE OF Vc4allocatedEntry
    MAX-ACCESS  not-accessible
    STATUS      current 
    DESCRIPTION
        "The higher order VC table for the configuration of an SDH/SONET
         Port. Only VC-4s allocated to a service are present in this table." 
    ::=  { gfpServiceConfigAndStatus 1 }

vc4allocatedEntry OBJECT-TYPE
    SYNTAX      Vc4allocatedEntry
    MAX-ACCESS  not-accessible
    STATUS      current 
    DESCRIPTION
        "An entry in the higher order VC (HO-VC) table. Each entry in
         this table represents a higher order AU (VC)." 
    INDEX       { entityIndex } 
    ::=  { vc4allocatedTable  1  }

Vc4allocatedEntry ::=  SEQUENCE
  { vc4allocatedContainer EntityIndex,
    vc4allocatedClassInstanceNumber Integer32 }


  
vc4allocatedContainer OBJECT-TYPE
    SYNTAX      EntityIndex
    MAX-ACCESS  read-only
    STATUS      current 
    DESCRIPTION
        "The entityIndex of the VC-4 container." 
    ::=  { vc4allocatedEntry 1 }

vc4allocatedClassInstanceNumber OBJECT-TYPE
    SYNTAX      Integer32 (1..2000)
    MAX-ACCESS  read-only
    STATUS      current 
    DESCRIPTION
        "The class instance number of this entity within the module(card)" 
    ::=  { vc4allocatedEntry 2 }

vc3allocatedTable OBJECT-TYPE
    SYNTAX      SEQUENCE OF Vc3allocatedEntry
    MAX-ACCESS  not-accessible
    STATUS      current 
    DESCRIPTION
        "The lower order VC table for the configuration of an SDH/SONET
         Port. Only VC-3s allocated to a service are present in this table." 
    ::=  { gfpServiceConfigAndStatus 2 }

vc3allocatedEntry OBJECT-TYPE
    SYNTAX      Vc3allocatedEntry
    MAX-ACCESS  not-accessible
    STATUS      current 
    DESCRIPTION
        "An entry in the lower order VC (LO-VC) table. Each entry in
         this table represents a lower order path." 
    INDEX       { entityIndex } 
    ::=  { vc3allocatedTable  1  }

Vc3allocatedEntry ::=  SEQUENCE
  { vc3allocatedContainer EntityIndex,
    vc3allocatedClassInstanceNumber Integer32 }


  
vc3allocatedContainer OBJECT-TYPE
    SYNTAX      EntityIndex
    MAX-ACCESS  read-only
    STATUS      current 
    DESCRIPTION
        "The entityIndex of the VC-3 container." 
    ::=  { vc3allocatedEntry 1 }

vc3allocatedClassInstanceNumber OBJECT-TYPE
    SYNTAX      Integer32 (1..2000)
    MAX-ACCESS  read-only
    STATUS      current 
    DESCRIPTION
        "The class instance number of this entity within the module(card)" 
    ::=  { vc3allocatedEntry 2 }

sts1allocatedTable OBJECT-TYPE
    SYNTAX      SEQUENCE OF Sts1allocatedEntry
    MAX-ACCESS  not-accessible
    STATUS      current 
    DESCRIPTION
        "" 
    ::=  { gfpServiceConfigAndStatus 3 }

sts1allocatedEntry OBJECT-TYPE
    SYNTAX      Sts1allocatedEntry
    MAX-ACCESS  not-accessible
    STATUS      current 
    DESCRIPTION
        "" 
    INDEX       { entityIndex } 
    ::=  { sts1allocatedTable  1  }

Sts1allocatedEntry ::=  SEQUENCE
  { sts1allocatedContainer EntityIndex,
    sts1allocatedClassInstanceNumber Integer32 }


  
sts1allocatedContainer OBJECT-TYPE
    SYNTAX      EntityIndex
    MAX-ACCESS  read-only
    STATUS      current 
    DESCRIPTION
        "AID of a logically linked Virtual Channel." 
    ::=  { sts1allocatedEntry 1 }

sts1allocatedClassInstanceNumber OBJECT-TYPE
    SYNTAX      Integer32 (1..2000)
    MAX-ACCESS  read-only
    STATUS      current 
    DESCRIPTION
        "The class instance number of this entity within the module(card)" 
    ::=  { sts1allocatedEntry 2 }

gfpVchConfigTable OBJECT-TYPE
    SYNTAX      SEQUENCE OF GfpVchConfigEntry
    MAX-ACCESS  not-accessible
    STATUS      current 
    DESCRIPTION
        "The GFP Service table configures a Service for a client port." 
    ::=  { gfpServiceConfigAndStatus 4 }

gfpVchConfigEntry OBJECT-TYPE
    SYNTAX      GfpVchConfigEntry
    MAX-ACCESS  not-accessible
    STATUS      current 
    DESCRIPTION
        "Each entry in this table represents a GFP service configuration
         for a client port." 
    INDEX       { entityIndex } 
    ::=  { gfpVchConfigTable  1  }

GfpVchConfigEntry ::=  SEQUENCE
  { gfpVchConfigBundle SonetVcBundleAllocation,
    gfpVchConfigCir Unsigned32 }


  
gfpVchConfigBundle OBJECT-TYPE
    SYNTAX      SonetVcBundleAllocation
    MAX-ACCESS  read-only
    STATUS      current 
    DESCRIPTION
        "Configures the Virtual Containers used in a VCG for a GFP VirtualChannel." 
    ::=  { gfpVchConfigEntry 1 }

gfpVchConfigCir OBJECT-TYPE
    SYNTAX      Unsigned32
    UNITS       "Mbit/s"
    MAX-ACCESS  read-write
    STATUS      current 
    DESCRIPTION
        "Comitted Information Rate of the virtual channel." 
    ::=  { gfpVchConfigEntry 2 }

gfpVchDataTable OBJECT-TYPE
    SYNTAX      SEQUENCE OF GfpVchDataEntry
    MAX-ACCESS  not-accessible
    STATUS      current 
    DESCRIPTION
        "The GFP Service table configures a Service for a client port." 
    ::=  { gfpServiceConfigAndStatus 5 }

gfpVchDataEntry OBJECT-TYPE
    SYNTAX      GfpVchDataEntry
    MAX-ACCESS  not-accessible
    STATUS      current 
    DESCRIPTION
        "Each entry in this table represents a GFP service configuration
         for a client port." 
    INDEX       { entityIndex } 
    ::=  { gfpVchDataTable  1  }

GfpVchDataEntry ::=  SEQUENCE
  { gfpVchDataVcType SonetVcType }


  
gfpVchDataVcType OBJECT-TYPE
    SYNTAX      SonetVcType
    MAX-ACCESS  read-only
    STATUS      current 
    DESCRIPTION
        "Virtual Container Group Type" 
    ::=  { gfpVchDataEntry 1 }

gfpServiceDefTable OBJECT-TYPE
    SYNTAX      SEQUENCE OF GfpServiceDefEntry
    MAX-ACCESS  not-accessible
    STATUS      current 
    DESCRIPTION
        "The GFP Service Default table provides default values for the
         configuration of GFP services." 
    ::=  { gfpServiceConfigAndStatus 6 }

gfpServiceDefEntry OBJECT-TYPE
    SYNTAX      GfpServiceDefEntry
    MAX-ACCESS  not-accessible
    STATUS      current 
    DESCRIPTION
        "An entry in the GFP Service Default table. Each entry in
         this table represents a default service configuration for a
         data rate and protocol. These values may be used as suggested
         values by the management system when defining a new GFP Service.
         There is one entry in this table for each valid data rate
         and service mapping (refer also to Appendix 1)." 
    INDEX       { entityIndex } 
    ::=  { gfpServiceDefTable  1  }

GfpServiceDefEntry ::=  SEQUENCE
  { gfpServiceDefBundleAllocation SonetVcBundleAllocation,
    gfpServiceDefBandwidth Unsigned32,
    gfpServiceDefVcType SonetVcType }


  
gfpServiceDefBundleAllocation OBJECT-TYPE
    SYNTAX      SonetVcBundleAllocation
    MAX-ACCESS  read-only
    STATUS      current 
    DESCRIPTION
        "The default allocation of VCs for the specified datarate and mapping." 
    ::=  { gfpServiceDefEntry 1 }

gfpServiceDefBandwidth OBJECT-TYPE
    SYNTAX      Unsigned32 (0..1000)
    UNITS       "Mbit/s"
    MAX-ACCESS  read-only
    STATUS      current 
    DESCRIPTION
        "The default bandwidth rate throttling of the specified service,
         valid only for mapping: 'gfpframed' and DataRate mb1250 (GbE).
         When not applicable, the value 0 is returned." 
    ::=  { gfpServiceDefEntry 2 }

gfpServiceDefVcType OBJECT-TYPE
    SYNTAX      SonetVcType
    MAX-ACCESS  read-only
    STATUS      current 
    DESCRIPTION
        "The type of VC allocation for the specified DataRate and Mapping
         and used together with BundleSize and Bandwidth:" 
    ::=  { gfpServiceDefEntry 3 }

deployProvShelfTable OBJECT-TYPE
    SYNTAX      SEQUENCE OF DeployProvShelfEntry
    MAX-ACCESS  not-accessible
    STATUS      current 
    DESCRIPTION
        "
         Contains entries for deployProv of shelfs.
        " 
    ::=  { shelfDeployProv 1 }

deployProvShelfEntry OBJECT-TYPE
    SYNTAX      DeployProvShelfEntry
    MAX-ACCESS  not-accessible
    STATUS      current 
    DESCRIPTION
        "
         All shelves which are provisioned(or during deployProv)
         will have an entry in this table.
        " 
    INDEX       { entityIndex } 
    ::=  { deployProvShelfTable  1  }

DeployProvShelfEntry ::=  SEQUENCE
  { deployProvShelfRowStatus RowStatus,
    deployProvShelfForceDestroy FspR7ForcedStatus,
    deployProvShelfType FspR7EquipmentType,
    deployProvShelfAdmin FspR7AdminState,
    deployProvShelfSupply FspR7SupplyType }


  
deployProvShelfRowStatus OBJECT-TYPE
    SYNTAX      RowStatus
    MAX-ACCESS  read-write
    STATUS      current 
    DESCRIPTION
        "
         This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'.
        " 
    ::=  { deployProvShelfEntry 1 }

deployProvShelfForceDestroy OBJECT-TYPE
    SYNTAX      FspR7ForcedStatus
    MAX-ACCESS  read-write
    STATUS      current 
    DESCRIPTION
        "Forced Destroy" 
    ::=  { deployProvShelfEntry 2 }

deployProvShelfType OBJECT-TYPE
    SYNTAX      FspR7EquipmentType
    MAX-ACCESS  read-write
    STATUS      current 
    DESCRIPTION
        "The type of Shelf determines uniquely the number and allowed types of
         the provisionable dependent entities (modules)." 
    ::=  { deployProvShelfEntry 3 }

deployProvShelfAdmin OBJECT-TYPE
    SYNTAX      FspR7AdminState
    MAX-ACCESS  read-write
    STATUS      current 
    DESCRIPTION
        "The Adminstrative State will be displayed in the GUI with full name values;
         it will be displayed differently in TL1 syntax according to TL1 display rules.
         The transaction into the UAS state requires a special destroy/delete function." 
    ::=  { deployProvShelfEntry 4 }

deployProvShelfSupply OBJECT-TYPE
    SYNTAX      FspR7SupplyType
    MAX-ACCESS  read-write
    STATUS      current 
    DESCRIPTION
        "The kind of power supply - provisioned value" 
    ::=  { deployProvShelfEntry 5 }

deployProvShelfCapTable OBJECT-TYPE
    SYNTAX      SEQUENCE OF DeployProvShelfCapEntry
    MAX-ACCESS  not-accessible
    STATUS      current 
    DESCRIPTION
        "
         Contains entries for deployProv of shelfs.
        " 
    ::=  { shelfDeployProv 2 }

deployProvShelfCapEntry OBJECT-TYPE
    SYNTAX      DeployProvShelfCapEntry
    MAX-ACCESS  not-accessible
    STATUS      current 
    DESCRIPTION
        "
         All shelves which are provisioned(or during deployProv)
         will have an entry in this table.
        " 
    INDEX       { entityIndex } 
    ::=  { deployProvShelfCapTable  1  }

DeployProvShelfCapEntry ::=  SEQUENCE
  { deployProvShelfCapRowStatus FspR7RowStatusCaps,
    deployProvShelfCapForceDestroy FspR7ForcedStatusCaps,
    deployProvShelfCapType FspR7EquipmentTypeCaps,
    deployProvShelfCapAdmin FspR7AdminStateCaps,
    deployProvShelfCapSupply FspR7SupplyTypeCaps }


  
deployProvShelfCapRowStatus OBJECT-TYPE
    SYNTAX      FspR7RowStatusCaps
    MAX-ACCESS  read-only
    STATUS      current 
    DESCRIPTION
        "
         This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'.
        " 
    ::=  { deployProvShelfCapEntry 1 }

deployProvShelfCapForceDestroy OBJECT-TYPE
    SYNTAX      FspR7ForcedStatusCaps
    MAX-ACCESS  read-only
    STATUS      current 
    DESCRIPTION
        "Forced Destroy" 
    ::=  { deployProvShelfCapEntry 2 }

deployProvShelfCapType OBJECT-TYPE
    SYNTAX      FspR7EquipmentTypeCaps
    MAX-ACCESS  read-only
    STATUS      current 
    DESCRIPTION
        "The type of Shelf determines uniquely the number and allowed types of
         the provisionable dependent entities (modules)." 
    ::=  { deployProvShelfCapEntry 3 }

deployProvShelfCapAdmin OBJECT-TYPE
    SYNTAX      FspR7AdminStateCaps
    MAX-ACCESS  read-only
    STATUS      current 
    DESCRIPTION
        "The Adminstrative State will be displayed in the GUI with full name values;
         it will be displayed differently in TL1 syntax according to TL1 display rules.
         The transaction into the UAS state requires a special destroy/delete function." 
    ::=  { deployProvShelfCapEntry 4 }

deployProvShelfCapSupply OBJECT-TYPE
    SYNTAX      FspR7SupplyTypeCaps
    MAX-ACCESS  read-only
    STATUS      current 
    DESCRIPTION
        "The kind of power supply - provisioned value" 
    ::=  { deployProvShelfCapEntry 5 }

deployProvShelfDefaultsTable OBJECT-TYPE
    SYNTAX      SEQUENCE OF DeployProvShelfDefaultsEntry
    MAX-ACCESS  not-accessible
    STATUS      current 
    DESCRIPTION
        "
         Contains entries for deployProv of shelfs.
        " 
    ::=  { shelfDeployProv 3 }

deployProvShelfDefaultsEntry OBJECT-TYPE
    SYNTAX      DeployProvShelfDefaultsEntry
    MAX-ACCESS  not-accessible
    STATUS      current 
    DESCRIPTION
        "
         All shelves which are provisioned(or during deployProv)
         will have an entry in this table.
        " 
    INDEX       { entityIndex } 
    ::=  { deployProvShelfDefaultsTable  1  }

DeployProvShelfDefaultsEntry ::=  SEQUENCE
  { deployProvShelfDefaultsRowStatus RowStatus,
    deployProvShelfDefaultsForceDestroy FspR7ForcedStatus,
    deployProvShelfDefaultsType FspR7EquipmentType,
    deployProvShelfDefaultsAdmin FspR7AdminState,
    deployProvShelfDefaultsSupply FspR7SupplyType }


  
deployProvShelfDefaultsRowStatus OBJECT-TYPE
    SYNTAX      RowStatus
    MAX-ACCESS  read-only
    STATUS      current 
    DESCRIPTION
        "
         This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'.
        " 
    ::=  { deployProvShelfDefaultsEntry 1 }

deployProvShelfDefaultsForceDestroy OBJECT-TYPE
    SYNTAX      FspR7ForcedStatus
    MAX-ACCESS  read-only
    STATUS      current 
    DESCRIPTION
        "Forced Destroy" 
    ::=  { deployProvShelfDefaultsEntry 2 }

deployProvShelfDefaultsType OBJECT-TYPE
    SYNTAX      FspR7EquipmentType
    MAX-ACCESS  read-only
    STATUS      current 
    DESCRIPTION
        "The type of Shelf determines uniquely the number and allowed types of
         the provisionable dependent entities (modules)." 
    ::=  { deployProvShelfDefaultsEntry 3 }

deployProvShelfDefaultsAdmin OBJECT-TYPE
    SYNTAX      FspR7AdminState
    MAX-ACCESS  read-only
    STATUS      current 
    DESCRIPTION
        "The Adminstrative State will be displayed in the GUI with full name values;
         it will be displayed differently in TL1 syntax according to TL1 display rules.
         The transaction into the UAS state requires a special destroy/delete function." 
    ::=  { deployProvShelfDefaultsEntry 4 }

deployProvShelfDefaultsSupply OBJECT-TYPE
    SYNTAX      FspR7SupplyType
    MAX-ACCESS  read-only
    STATUS      current 
    DESCRIPTION
        "The kind of power supply - provisioned value" 
    ::=  { deployProvShelfDefaultsEntry 5 }

deployProvModuleTable OBJECT-TYPE
    SYNTAX      SEQUENCE OF DeployProvModuleEntry
    MAX-ACCESS  not-accessible
    STATUS      current 
    DESCRIPTION
        "Contains entries for deployProv of modules." 
    ::=  { moduleDeployProv 1 }

deployProvModuleEntry OBJECT-TYPE
    SYNTAX      DeployProvModuleEntry
    MAX-ACCESS  not-accessible
    STATUS      current 
    DESCRIPTION
        "All modules which are provisioned(or are during deployProv)
         will have an entry in this table." 
    INDEX       { entityIndex } 
    ::=  { deployProvModuleTable  1  }

DeployProvModuleEntry ::=  SEQUENCE
  { deployProvModuleRowStatus RowStatus,
    deployProvModuleForceDestroy FspR7ForcedStatus,
    deployProvModuleType FspR7EquipmentType,
    deployProvModuleMode FspR7TransmissionMode,
    deployProvModuleDeploy FspR7DeploymentScenario,
    deployProvModuleChannel FspR7ChannelIdentifier,
    deployProvModuleReach FspR7OpticalInterfaceReach,
    deployProvModuleBand FspR7OpticalBand,
    deployProvModuleSubBand FspR7OpticalSubBand,
    deployProvModuleGroup FspR7OpticalGroup,
    deployProvModuleFiber FspR7OpticalFiberType,
    deployProvModuleEdfaPwrOut FspR7EdfaOutputPowerRating,
    deployProvModuleAdmin FspR7AdminState,
    deployProvModuleSupply FspR7SupplyType }


  
deployProvModuleRowStatus OBJECT-TYPE
    SYNTAX      RowStatus
    MAX-ACCESS  read-write
    STATUS      current 
    DESCRIPTION
        "RowStatus" 
    ::=  { deployProvModuleEntry 1 }

deployProvModuleForceDestroy OBJECT-TYPE
    SYNTAX      FspR7ForcedStatus
    MAX-ACCESS  read-write
    STATUS      current 
    DESCRIPTION
        "Forced Destroy" 
    ::=  { deployProvModuleEntry 2 }

deployProvModuleType OBJECT-TYPE
    SYNTAX      FspR7EquipmentType
    MAX-ACCESS  read-write
    STATUS      current 
    DESCRIPTION
        "The TYPE of Module." 
    ::=  { deployProvModuleEntry 3 }

deployProvModuleMode OBJECT-TYPE
    SYNTAX      FspR7TransmissionMode
    MAX-ACCESS  read-write
    STATUS      current 
    DESCRIPTION
        "The transmission mode of the module." 
    ::=  { deployProvModuleEntry 4 }

deployProvModuleDeploy OBJECT-TYPE
    SYNTAX      FspR7DeploymentScenario
    MAX-ACCESS  read-write
    STATUS      current 
    DESCRIPTION
        "The deployment scenario of the module." 
    ::=  { deployProvModuleEntry 5 }

deployProvModuleChannel OBJECT-TYPE
    SYNTAX      FspR7ChannelIdentifier
    MAX-ACCESS  read-write
    STATUS      current 
    DESCRIPTION
        "The optical channel." 
    ::=  { deployProvModuleEntry 6 }

deployProvModuleReach OBJECT-TYPE
    SYNTAX      FspR7OpticalInterfaceReach
    MAX-ACCESS  read-write
    STATUS      current 
    DESCRIPTION
        "The optical channel." 
    ::=  { deployProvModuleEntry 7 }

deployProvModuleBand OBJECT-TYPE
    SYNTAX      FspR7OpticalBand
    MAX-ACCESS  read-write
    STATUS      current 
    DESCRIPTION
        "The The optical band of the module." 
    ::=  { deployProvModuleEntry 8 }

deployProvModuleSubBand OBJECT-TYPE
    SYNTAX      FspR7OpticalSubBand
    MAX-ACCESS  read-write
    STATUS      current 
    DESCRIPTION
        "The subband of 16 DWDM channels." 
    ::=  { deployProvModuleEntry 9 }

deployProvModuleGroup OBJECT-TYPE
    SYNTAX      FspR7OpticalGroup
    MAX-ACCESS  read-write
    STATUS      current 
    DESCRIPTION
        "The Group of 4 DWDM channels." 
    ::=  { deployProvModuleEntry 10 }

deployProvModuleFiber OBJECT-TYPE
    SYNTAX      FspR7OpticalFiberType
    MAX-ACCESS  read-write
    STATUS      current 
    DESCRIPTION
        "Fiber type." 
    ::=  { deployProvModuleEntry 11 }

deployProvModuleEdfaPwrOut OBJECT-TYPE
    SYNTAX      FspR7EdfaOutputPowerRating
    MAX-ACCESS  read-write
    STATUS      current 
    DESCRIPTION
        "Optical Output Power Rating - Provision" 
    ::=  { deployProvModuleEntry 12 }

deployProvModuleAdmin OBJECT-TYPE
    SYNTAX      FspR7AdminState
    MAX-ACCESS  read-write
    STATUS      current 
    DESCRIPTION
        "The Adminstrative State." 
    ::=  { deployProvModuleEntry 13 }

deployProvModuleSupply OBJECT-TYPE
    SYNTAX      FspR7SupplyType
    MAX-ACCESS  read-write
    STATUS      current 
    DESCRIPTION
        "The kind of power supply - provisioned value" 
    ::=  { deployProvModuleEntry 14 }

deployProvModuleCapTable OBJECT-TYPE
    SYNTAX      SEQUENCE OF DeployProvModuleCapEntry
    MAX-ACCESS  not-accessible
    STATUS      current 
    DESCRIPTION
        "Contains entries for deployProv of modules." 
    ::=  { moduleDeployProv 2 }

deployProvModuleCapEntry OBJECT-TYPE
    SYNTAX      DeployProvModuleCapEntry
    MAX-ACCESS  not-accessible
    STATUS      current 
    DESCRIPTION
        "All modules which are provisioned(or are during deployProv)
         will have an entry in this table." 
    INDEX       { entityIndex } 
    ::=  { deployProvModuleCapTable  1  }

DeployProvModuleCapEntry ::=  SEQUENCE
  { deployProvModuleCapRowStatus FspR7RowStatusCaps,
    deployProvModuleCapForceDestroy FspR7ForcedStatusCaps,
    deployProvModuleCapType FspR7EquipmentTypeCaps,
    deployProvModuleCapMode FspR7TransmissionModeCaps,
    deployProvModuleCapDeploy FspR7DeploymentScenarioCaps,
    deployProvModuleCapChannel FspR7ChannelIdentifierCaps,
    deployProvModuleCapReach FspR7OpticalInterfaceReachCaps,
    deployProvModuleCapBand FspR7OpticalBandCaps,
    deployProvModuleCapSubBand FspR7OpticalSubBandCaps,
    deployProvModuleCapGroup FspR7OpticalGroupCaps,
    deployProvModuleCapFiber FspR7OpticalFiberTypeCaps,
    deployProvModuleCapEdfaPwrOut FspR7EdfaOutputPowerRatingCaps,
    deployProvModuleCapAdmin FspR7AdminStateCaps,
    deployProvModuleCapSupply FspR7SupplyTypeCaps }


  
deployProvModuleCapRowStatus OBJECT-TYPE
    SYNTAX      FspR7RowStatusCaps
    MAX-ACCESS  read-only
    STATUS      current 
    DESCRIPTION
        "RowStatus" 
    ::=  { deployProvModuleCapEntry 1 }

deployProvModuleCapForceDestroy OBJECT-TYPE
    SYNTAX      FspR7ForcedStatusCaps
    MAX-ACCESS  read-only
    STATUS      current 
    DESCRIPTION
        "Forced Destroy" 
    ::=  { deployProvModuleCapEntry 2 }

deployProvModuleCapType OBJECT-TYPE
    SYNTAX      FspR7EquipmentTypeCaps
    MAX-ACCESS  read-only
    STATUS      current 
    DESCRIPTION
        "The TYPE of Module." 
    ::=  { deployProvModuleCapEntry 3 }

deployProvModuleCapMode OBJECT-TYPE
    SYNTAX      FspR7TransmissionModeCaps
    MAX-ACCESS  read-only
    STATUS      current 
    DESCRIPTION
        "The transmission mode of the module." 
    ::=  { deployProvModuleCapEntry 4 }

deployProvModuleCapDeploy OBJECT-TYPE
    SYNTAX      FspR7DeploymentScenarioCaps
    MAX-ACCESS  read-only
    STATUS      current 
    DESCRIPTION
        "The deployment scenario of the module." 
    ::=  { deployProvModuleCapEntry 5 }

deployProvModuleCapChannel OBJECT-TYPE
    SYNTAX      FspR7ChannelIdentifierCaps
    MAX-ACCESS  read-only
    STATUS      current 
    DESCRIPTION
        "The optical channel." 
    ::=  { deployProvModuleCapEntry 6 }

deployProvModuleCapReach OBJECT-TYPE
    SYNTAX      FspR7OpticalInterfaceReachCaps
    MAX-ACCESS  read-only
    STATUS      current 
    DESCRIPTION
        "The optical channel." 
    ::=  { deployProvModuleCapEntry 7 }

deployProvModuleCapBand OBJECT-TYPE
    SYNTAX      FspR7OpticalBandCaps
    MAX-ACCESS  read-only
    STATUS      current 
    DESCRIPTION
        "The The optical band of the module." 
    ::=  { deployProvModuleCapEntry 8 }

deployProvModuleCapSubBand OBJECT-TYPE
    SYNTAX      FspR7OpticalSubBandCaps
    MAX-ACCESS  read-only
    STATUS      current 
    DESCRIPTION
        "The subband of 16 DWDM channels." 
    ::=  { deployProvModuleCapEntry 9 }

deployProvModuleCapGroup OBJECT-TYPE
    SYNTAX      FspR7OpticalGroupCaps
    MAX-ACCESS  read-only
    STATUS      current 
    DESCRIPTION
        "The Group of 4 DWDM channels." 
    ::=  { deployProvModuleCapEntry 10 }

deployProvModuleCapFiber OBJECT-TYPE
    SYNTAX      FspR7OpticalFiberTypeCaps
    MAX-ACCESS  read-only
    STATUS      current 
    DESCRIPTION
        "Fiber type." 
    ::=  { deployProvModuleCapEntry 11 }

deployProvModuleCapEdfaPwrOut OBJECT-TYPE
    SYNTAX      FspR7EdfaOutputPowerRatingCaps
    MAX-ACCESS  read-only
    STATUS      current 
    DESCRIPTION
        "Optical Output Power Rating - Provision" 
    ::=  { deployProvModuleCapEntry 12 }

deployProvModuleCapAdmin OBJECT-TYPE
    SYNTAX      FspR7AdminStateCaps
    MAX-ACCESS  read-only
    STATUS      current 
    DESCRIPTION
        "The Adminstrative State." 
    ::=  { deployProvModuleCapEntry 13 }

deployProvModuleCapSupply OBJECT-TYPE
    SYNTAX      FspR7SupplyTypeCaps
    MAX-ACCESS  read-only
    STATUS      current 
    DESCRIPTION
        "The kind of power supply - provisioned value" 
    ::=  { deployProvModuleCapEntry 14 }

deployProvModuleDefaultsTable OBJECT-TYPE
    SYNTAX      SEQUENCE OF DeployProvModuleDefaultsEntry
    MAX-ACCESS  not-accessible
    STATUS      current 
    DESCRIPTION
        "Contains entries for deployProv of modules." 
    ::=  { moduleDeployProv 3 }

deployProvModuleDefaultsEntry OBJECT-TYPE
    SYNTAX      DeployProvModuleDefaultsEntry
    MAX-ACCESS  not-accessible
    STATUS      current 
    DESCRIPTION
        "All modules which are provisioned(or are during deployProv)
         will have an entry in this table." 
    INDEX       { entityIndex } 
    ::=  { deployProvModuleDefaultsTable  1  }

DeployProvModuleDefaultsEntry ::=  SEQUENCE
  { deployProvModuleDefaultsRowStatus RowStatus,
    deployProvModuleDefaultsForceDestroy FspR7ForcedStatus,
    deployProvModuleDefaultsType FspR7EquipmentType,
    deployProvModuleDefaultsMode FspR7TransmissionMode,
    deployProvModuleDefaultsDeploy FspR7DeploymentScenario,
    deployProvModuleDefaultsChannel FspR7ChannelIdentifier,
    deployProvModuleDefaultsReach FspR7OpticalInterfaceReach,
    deployProvModuleDefaultsBand FspR7OpticalBand,
    deployProvModuleDefaultsSubBand FspR7OpticalSubBand,
    deployProvModuleDefaultsGroup FspR7OpticalGroup,
    deployProvModuleDefaultsFiber FspR7OpticalFiberType,
    deployProvModuleDefaultsEdfaPwrOut FspR7EdfaOutputPowerRating,
    deployProvModuleDefaultsAdmin FspR7AdminState,
    deployProvModuleDefaultsSupply FspR7SupplyType }


  
deployProvModuleDefaultsRowStatus OBJECT-TYPE
    SYNTAX      RowStatus
    MAX-ACCESS  read-only
    STATUS      current 
    DESCRIPTION
        "RowStatus" 
    ::=  { deployProvModuleDefaultsEntry 1 }

deployProvModuleDefaultsForceDestroy OBJECT-TYPE
    SYNTAX      FspR7ForcedStatus
    MAX-ACCESS  read-only
    STATUS      current 
    DESCRIPTION
        "Forced Destroy" 
    ::=  { deployProvModuleDefaultsEntry 2 }

deployProvModuleDefaultsType OBJECT-TYPE
    SYNTAX      FspR7EquipmentType
    MAX-ACCESS  read-only
    STATUS      current 
    DESCRIPTION
        "The TYPE of Module." 
    ::=  { deployProvModuleDefaultsEntry 3 }

deployProvModuleDefaultsMode OBJECT-TYPE
    SYNTAX      FspR7TransmissionMode
    MAX-ACCESS  read-only
    STATUS      current 
    DESCRIPTION
        "The transmission mode of the module." 
    ::=  { deployProvModuleDefaultsEntry 4 }

deployProvModuleDefaultsDeploy OBJECT-TYPE
    SYNTAX      FspR7DeploymentScenario
    MAX-ACCESS  read-only
    STATUS      current 
    DESCRIPTION
        "The deployment scenario of the module." 
    ::=  { deployProvModuleDefaultsEntry 5 }

deployProvModuleDefaultsChannel OBJECT-TYPE
    SYNTAX      FspR7ChannelIdentifier
    MAX-ACCESS  read-only
    STATUS      current 
    DESCRIPTION
        "The optical channel." 
    ::=  { deployProvModuleDefaultsEntry 6 }

deployProvModuleDefaultsReach OBJECT-TYPE
    SYNTAX      FspR7OpticalInterfaceReach
    MAX-ACCESS  read-only
    STATUS      current 
    DESCRIPTION
        "The optical channel." 
    ::=  { deployProvModuleDefaultsEntry 7 }

deployProvModuleDefaultsBand OBJECT-TYPE
    SYNTAX      FspR7OpticalBand
    MAX-ACCESS  read-only
    STATUS      current 
    DESCRIPTION
        "The The optical band of the module." 
    ::=  { deployProvModuleDefaultsEntry 8 }

deployProvModuleDefaultsSubBand OBJECT-TYPE
    SYNTAX      FspR7OpticalSubBand
    MAX-ACCESS  read-only
    STATUS      current 
    DESCRIPTION
        "The subband of 16 DWDM channels." 
    ::=  { deployProvModuleDefaultsEntry 9 }

deployProvModuleDefaultsGroup OBJECT-TYPE
    SYNTAX      FspR7OpticalGroup
    MAX-ACCESS  read-only
    STATUS      current 
    DESCRIPTION
        "The Group of 4 DWDM channels." 
    ::=  { deployProvModuleDefaultsEntry 10 }

deployProvModuleDefaultsFiber OBJECT-TYPE
    SYNTAX      FspR7OpticalFiberType
    MAX-ACCESS  read-only
    STATUS      current 
    DESCRIPTION
        "Fiber type." 
    ::=  { deployProvModuleDefaultsEntry 11 }

deployProvModuleDefaultsEdfaPwrOut OBJECT-TYPE
    SYNTAX      FspR7EdfaOutputPowerRating
    MAX-ACCESS  read-only
    STATUS      current 
    DESCRIPTION
        "Optical Output Power Rating - Provision" 
    ::=  { deployProvModuleDefaultsEntry 12 }

deployProvModuleDefaultsAdmin OBJECT-TYPE
    SYNTAX      FspR7AdminState
    MAX-ACCESS  read-only
    STATUS      current 
    DESCRIPTION
        "The Adminstrative State." 
    ::=  { deployProvModuleDefaultsEntry 13 }

deployProvModuleDefaultsSupply OBJECT-TYPE
    SYNTAX      FspR7SupplyType
    MAX-ACCESS  read-only
    STATUS      current 
    DESCRIPTION
        "The kind of power supply - provisioned value" 
    ::=  { deployProvModuleDefaultsEntry 14 }

deployProvPlugTable OBJECT-TYPE
    SYNTAX      SEQUENCE OF DeployProvPlugEntry
    MAX-ACCESS  not-accessible
    STATUS      current 
    DESCRIPTION
        "Contains entries for deployProv of plugs." 
    ::=  { plugDeployProv 1 }

deployProvPlugEntry OBJECT-TYPE
    SYNTAX      DeployProvPlugEntry
    MAX-ACCESS  not-accessible
    STATUS      current 
    DESCRIPTION
        "All plugs which are provisioned(or during deployProv)
         will have an entry in this table." 
    INDEX       { entityIndex } 
    ::=  { deployProvPlugTable  1  }

DeployProvPlugEntry ::=  SEQUENCE
  { deployProvPlugRowStatus RowStatus,
    deployProvPlugForceDestroy FspR7ForcedStatus,
    deployProvPlugType FspR7EquipmentType,
    deployProvPlugMaxDataRate FspR7PlugDataRate,
    deployProvPlugChannelId FspR7ChannelIdentifier,
    deployProvPlugThirdPartyUsage EnableState,
    deployProvPlugReach FspR7OpticalInterfaceReach,
    deployProvPlugAdmin FspR7AdminState }


  
deployProvPlugRowStatus OBJECT-TYPE
    SYNTAX      RowStatus
    MAX-ACCESS  read-write
    STATUS      current 
    DESCRIPTION
        "RowStatus" 
    ::=  { deployProvPlugEntry 1 }

deployProvPlugForceDestroy OBJECT-TYPE
    SYNTAX      FspR7ForcedStatus
    MAX-ACCESS  read-write
    STATUS      current 
    DESCRIPTION
        "Forced Destroy" 
    ::=  { deployProvPlugEntry 2 }

deployProvPlugType OBJECT-TYPE
    SYNTAX      FspR7EquipmentType
    MAX-ACCESS  read-write
    STATUS      current 
    DESCRIPTION
        "Allowed Interfacetype may depend additionally on Plug TYPE" 
    ::=  { deployProvPlugEntry 3 }

deployProvPlugMaxDataRate OBJECT-TYPE
    SYNTAX      FspR7PlugDataRate
    MAX-ACCESS  read-write
    STATUS      current 
    DESCRIPTION
        "The maximal data rate of the plug." 
    ::=  { deployProvPlugEntry 4 }

deployProvPlugChannelId OBJECT-TYPE
    SYNTAX      FspR7ChannelIdentifier
    MAX-ACCESS  read-write
    STATUS      current 
    DESCRIPTION
        "The optical channel of the plug." 
    ::=  { deployProvPlugEntry 5 }

deployProvPlugThirdPartyUsage OBJECT-TYPE
    SYNTAX      EnableState
    MAX-ACCESS  read-write
    STATUS      current 
    DESCRIPTION
        "Usage of 3rd Party Plugs" 
    ::=  { deployProvPlugEntry 6 }

deployProvPlugReach OBJECT-TYPE
    SYNTAX      FspR7OpticalInterfaceReach
    MAX-ACCESS  read-write
    STATUS      current 
    DESCRIPTION
        "The optical reach of the plug." 
    ::=  { deployProvPlugEntry 7 }

deployProvPlugAdmin OBJECT-TYPE
    SYNTAX      FspR7AdminState
    MAX-ACCESS  read-write
    STATUS      current 
    DESCRIPTION
        "The Adminstrative State will be displayed in the GUI with full name values;
         it will be differently displayed in TL1 syntax according to TL1 display rules.
         The transaction into the UAS state requires a special destroy/delete function." 
    ::=  { deployProvPlugEntry 8 }

deployProvPlugCapTable OBJECT-TYPE
    SYNTAX      SEQUENCE OF DeployProvPlugCapEntry
    MAX-ACCESS  not-accessible
    STATUS      current 
    DESCRIPTION
        "Contains entries for deployProv of plugs." 
    ::=  { plugDeployProv 2 }

deployProvPlugCapEntry OBJECT-TYPE
    SYNTAX      DeployProvPlugCapEntry
    MAX-ACCESS  not-accessible
    STATUS      current 
    DESCRIPTION
        "All plugs which are provisioned(or during deployProv)
         will have an entry in this table." 
    INDEX       { entityIndex } 
    ::=  { deployProvPlugCapTable  1  }

DeployProvPlugCapEntry ::=  SEQUENCE
  { deployProvPlugCapRowStatus FspR7RowStatusCaps,
    deployProvPlugCapForceDestroy FspR7ForcedStatusCaps,
    deployProvPlugCapType FspR7EquipmentTypeCaps,
    deployProvPlugCapMaxDataRate FspR7PlugDataRateCaps,
    deployProvPlugCapChannelId FspR7ChannelIdentifierCaps,
    deployProvPlugCapThirdPartyUsage EnableStateCaps,
    deployProvPlugCapReach FspR7OpticalInterfaceReachCaps,
    deployProvPlugCapAdmin FspR7AdminStateCaps }


  
deployProvPlugCapRowStatus OBJECT-TYPE
    SYNTAX      FspR7RowStatusCaps
    MAX-ACCESS  read-only
    STATUS      current 
    DESCRIPTION
        "RowStatus" 
    ::=  { deployProvPlugCapEntry 1 }

deployProvPlugCapForceDestroy OBJECT-TYPE
    SYNTAX      FspR7ForcedStatusCaps
    MAX-ACCESS  read-only
    STATUS      current 
    DESCRIPTION
        "Forced Destroy" 
    ::=  { deployProvPlugCapEntry 2 }

deployProvPlugCapType OBJECT-TYPE
    SYNTAX      FspR7EquipmentTypeCaps
    MAX-ACCESS  read-only
    STATUS      current 
    DESCRIPTION
        "Allowed Interfacetype may depend additionally on Plug TYPE" 
    ::=  { deployProvPlugCapEntry 3 }

deployProvPlugCapMaxDataRate OBJECT-TYPE
    SYNTAX      FspR7PlugDataRateCaps
    MAX-ACCESS  read-only
    STATUS      current 
    DESCRIPTION
        "The maximal data rate of the plug." 
    ::=  { deployProvPlugCapEntry 4 }

deployProvPlugCapChannelId OBJECT-TYPE
    SYNTAX      FspR7ChannelIdentifierCaps
    MAX-ACCESS  read-only
    STATUS      current 
    DESCRIPTION
        "The optical channel of the plug." 
    ::=  { deployProvPlugCapEntry 5 }

deployProvPlugCapThirdPartyUsage OBJECT-TYPE
    SYNTAX      EnableStateCaps
    MAX-ACCESS  read-only
    STATUS      current 
    DESCRIPTION
        "Usage of 3rd Party Plugs" 
    ::=  { deployProvPlugCapEntry 6 }

deployProvPlugCapReach OBJECT-TYPE
    SYNTAX      FspR7OpticalInterfaceReachCaps
    MAX-ACCESS  read-only
    STATUS      current 
    DESCRIPTION
        "The optical reach of the plug." 
    ::=  { deployProvPlugCapEntry 7 }

deployProvPlugCapAdmin OBJECT-TYPE
    SYNTAX      FspR7AdminStateCaps
    MAX-ACCESS  read-only
    STATUS      current 
    DESCRIPTION
        "The Adminstrative State will be displayed in the GUI with full name values;
         it will be differently displayed in TL1 syntax according to TL1 display rules.
         The transaction into the UAS state requires a special destroy/delete function." 
    ::=  { deployProvPlugCapEntry 8 }

deployProvPlugDefaultsTable OBJECT-TYPE
    SYNTAX      SEQUENCE OF DeployProvPlugDefaultsEntry
    MAX-ACCESS  not-accessible
    STATUS      current 
    DESCRIPTION
        "Contains entries for deployProv of plugs." 
    ::=  { plugDeployProv 3 }

deployProvPlugDefaultsEntry OBJECT-TYPE
    SYNTAX      DeployProvPlugDefaultsEntry
    MAX-ACCESS  not-accessible
    STATUS      current 
    DESCRIPTION
        "All plugs which are provisioned(or during deployProv)
         will have an entry in this table." 
    INDEX       { entityIndex } 
    ::=  { deployProvPlugDefaultsTable  1  }

DeployProvPlugDefaultsEntry ::=  SEQUENCE
  { deployProvPlugDefaultsRowStatus RowStatus,
    deployProvPlugDefaultsForceDestroy FspR7ForcedStatus,
    deployProvPlugDefaultsType FspR7EquipmentType,
    deployProvPlugDefaultsMaxDataRate FspR7PlugDataRate,
    deployProvPlugDefaultsChannelId FspR7ChannelIdentifier,
    deployProvPlugDefaultsThirdPartyUsage EnableState,
    deployProvPlugDefaultsReach FspR7OpticalInterfaceReach,
    deployProvPlugDefaultsAdmin FspR7AdminState }


  
deployProvPlugDefaultsRowStatus OBJECT-TYPE
    SYNTAX      RowStatus
    MAX-ACCESS  read-only
    STATUS      current 
    DESCRIPTION
        "RowStatus" 
    ::=  { deployProvPlugDefaultsEntry 1 }

deployProvPlugDefaultsForceDestroy OBJECT-TYPE
    SYNTAX      FspR7ForcedStatus
    MAX-ACCESS  read-only
    STATUS      current 
    DESCRIPTION
        "Forced Destroy" 
    ::=  { deployProvPlugDefaultsEntry 2 }

deployProvPlugDefaultsType OBJECT-TYPE
    SYNTAX      FspR7EquipmentType
    MAX-ACCESS  read-only
    STATUS      current 
    DESCRIPTION
        "Allowed Interfacetype may depend additionally on Plug TYPE" 
    ::=  { deployProvPlugDefaultsEntry 3 }

deployProvPlugDefaultsMaxDataRate OBJECT-TYPE
    SYNTAX      FspR7PlugDataRate
    MAX-ACCESS  read-only
    STATUS      current 
    DESCRIPTION
        "The maximal data rate of the plug." 
    ::=  { deployProvPlugDefaultsEntry 4 }

deployProvPlugDefaultsChannelId OBJECT-TYPE
    SYNTAX      FspR7ChannelIdentifier
    MAX-ACCESS  read-only
    STATUS      current 
    DESCRIPTION
        "The optical channel of the plug." 
    ::=  { deployProvPlugDefaultsEntry 5 }

deployProvPlugDefaultsThirdPartyUsage OBJECT-TYPE
    SYNTAX      EnableState
    MAX-ACCESS  read-only
    STATUS      current 
    DESCRIPTION
        "Usage of 3rd Party Plugs" 
    ::=  { deployProvPlugDefaultsEntry 6 }

deployProvPlugDefaultsReach OBJECT-TYPE
    SYNTAX      FspR7OpticalInterfaceReach
    MAX-ACCESS  read-only
    STATUS      current 
    DESCRIPTION
        "The optical reach of the plug." 
    ::=  { deployProvPlugDefaultsEntry 7 }

deployProvPlugDefaultsAdmin OBJECT-TYPE
    SYNTAX      FspR7AdminState
    MAX-ACCESS  read-only
    STATUS      current 
    DESCRIPTION
        "The Adminstrative State will be displayed in the GUI with full name values;
         it will be differently displayed in TL1 syntax according to TL1 display rules.
         The transaction into the UAS state requires a special destroy/delete function." 
    ::=  { deployProvPlugDefaultsEntry 8 }

deployProvIfTable OBJECT-TYPE
    SYNTAX      SEQUENCE OF DeployProvIfEntry
    MAX-ACCESS  not-accessible
    STATUS      current 
    DESCRIPTION
        "Contains entries for deployProv of interfaces." 
    ::=  { facilityDeployProv 1 }

deployProvIfEntry OBJECT-TYPE
    SYNTAX      DeployProvIfEntry
    MAX-ACCESS  not-accessible
    STATUS      current 
    DESCRIPTION
        "All interfaces which are provisioned(or during deployProv) will have an entry
         in this table." 
    INDEX       { entityIndex } 
    ::=  { deployProvIfTable  1  }

DeployProvIfEntry ::=  SEQUENCE
  { deployProvIfRowStatus RowStatus,
    deployProvIfForceDestroy FspR7ForcedStatus,
    deployProvIfType FspR7InterfaceType,
    deployProvIfPayload OtnPayloadType,
    deployProvIfBehaviour FspR7PortBehaviour,
    deployProvIfTerminationLevel OhTerminationLevel,
    deployProvIfAlsMode FspR7AlsMode,
    deployProvIfErrorForwarding FspR7ErrorFwdMode,
    deployProvIfLaserOffDelayFunction EnableState,
    deployProvIfFecType FspR7FecType,
    deployProvIfTimingSource SonetTimingSource,
    deployProvIfTcmALevel OtnTcmLevel,
    deployProvIfTcmBLevel OtnTcmLevel,
    deployProvIfSigDegThresSonetLine FspR7BERThreshold,
    deployProvIfSigDegThresSdhMs Unsigned32,
    deployProvIfSignalDegradePeriod Unsigned32,
    deployProvIfAutonegotiation EnableState,
    deployProvIfBitrate FspR7Bitrate,
    deployProvIfDuplex EthDuplexMode,
    deployProvIfFlowControl FspR7FlowControlMode,
    deployProvIfOtnStuffing EnableState,
    deployProvIfSigDegThresOtu Integer32,
    deployProvIfSigDegPeriodOtu Unsigned32,
    deployProvIfSigDegThresOdu Integer32,
    deployProvIfSigDegPeriodOdu Unsigned32,
    deployProvIfSigDegThresOduTcmA Integer32,
    deployProvIfSigDegPeriodOduTcmA Unsigned32,
    deployProvIfSigDegThresOduTcmB Integer32,
    deployProvIfSigDegPeriodOduTcmB Unsigned32,
    deployProvIfTilt Integer32,
    deployProvIfGain FspR7Gain,
    deployProvIfAdmin FspR7AdminState,
    deployProvIfAttenuationGradient Unsigned32,
    deployProvIfSigDegThresReceiver Unsigned32,
    deployProvIfTcmCLevel OtnTcmLevel,
    deployProvIfSigDegThresOduTcmC Integer32,
    deployProvIfSigDegPeriodOduTcmC Unsigned32,
    deployProvIfDisparityCorrection EnableState,
    deployProvIfIpAddr IpAddress,
    deployProvIfIpMask IpAddress,
    deployProvIfOspf EnableState,
    deployProvIfMetric Unsigned32,
    deployProvIfAreaId IpAddress }


  
deployProvIfRowStatus OBJECT-TYPE
    SYNTAX      RowStatus
    MAX-ACCESS  read-write
    STATUS      current 
    DESCRIPTION
        "RowStatus" 
    ::=  { deployProvIfEntry 1 }

deployProvIfForceDestroy OBJECT-TYPE
    SYNTAX      FspR7ForcedStatus
    MAX-ACCESS  read-write
    STATUS      current 
    DESCRIPTION
        "Forced Destroy" 
    ::=  { deployProvIfEntry 2 }

deployProvIfType OBJECT-TYPE
    SYNTAX      FspR7InterfaceType
    MAX-ACCESS  read-write
    STATUS      current 
    DESCRIPTION
        "The TYPE defines the transport service type as wrapper with wrapper layer
         termination OR else as payload" 
    ::=  { deployProvIfEntry 3 }

deployProvIfPayload OBJECT-TYPE
    SYNTAX      OtnPayloadType
    MAX-ACCESS  read-write
    STATUS      current 
    DESCRIPTION
        "The payload of the interface (inside a transport overhead).
         Relevant e. g. for OTN cards which wrap a payload into an OTU1/2 wrapper." 
    ::=  { deployProvIfEntry 4 }

deployProvIfBehaviour OBJECT-TYPE
    SYNTAX      FspR7PortBehaviour
    MAX-ACCESS  read-write
    STATUS      current 
    DESCRIPTION
        "The configured behaviour of the interface. If configured as
         a network interface, the interface will use a WDM laser." 
    ::=  { deployProvIfEntry 5 }

deployProvIfTerminationLevel OBJECT-TYPE
    SYNTAX      OhTerminationLevel
    MAX-ACCESS  read-write
    STATUS      current 
    DESCRIPTION
        "Signal Tremination Level of Intrusive Access to Header Information.
         Not used in 7.0, monitoring is one layer higher than TERM level,
         if applicable. All conditions detected on monitoring layer will not
         be reported (severity degradated to NR)." 
    ::=  { deployProvIfEntry 6 }

deployProvIfAlsMode OBJECT-TYPE
    SYNTAX      FspR7AlsMode
    MAX-ACCESS  read-write
    STATUS      current 
    DESCRIPTION
        "A configuration request for the Automatic Laser Shutdown (ALS)
         function. Refer to FspR7AlsMode Textual Convention for details." 
    ::=  { deployProvIfEntry 7 }

deployProvIfErrorForwarding OBJECT-TYPE
    SYNTAX      FspR7ErrorFwdMode
    MAX-ACCESS  read-write
    STATUS      current 
    DESCRIPTION
        "A configuration request for the error forwarding
         function. Refer to FspR7ErrorFwdMode Textual Convention for details." 
    ::=  { deployProvIfEntry 8 }

deployProvIfLaserOffDelayFunction OBJECT-TYPE
    SYNTAX      EnableState
    MAX-ACCESS  read-write
    STATUS      current 
    DESCRIPTION
        "A configuration request for the Laser Off Delay function. This function
         delays turning off the laser as a consequent action to a defect." 
    ::=  { deployProvIfEntry 9 }

deployProvIfFecType OBJECT-TYPE
    SYNTAX      FspR7FecType
    MAX-ACCESS  read-write
    STATUS      current 
    DESCRIPTION
        "Configuration of FEC type." 
    ::=  { deployProvIfEntry 10 }

deployProvIfTimingSource OBJECT-TYPE
    SYNTAX      SonetTimingSource
    MAX-ACCESS  read-write
    STATUS      current 
    DESCRIPTION
        "The timing source for this interface.
         - internal: used in stand-alone, point-to-point topologies
         stand-alone (dedicated fiber operation)
         - loopTiming: e.g. used in point-to-point via SONET network and
         feeder topologies.
         The default is internal(1)." 
    ::=  { deployProvIfEntry 11 }

deployProvIfTcmALevel OBJECT-TYPE
    SYNTAX      OtnTcmLevel
    MAX-ACCESS  read-write
    STATUS      current 
    DESCRIPTION
        "Configuration of TCMA level." 
    ::=  { deployProvIfEntry 12 }

deployProvIfTcmBLevel OBJECT-TYPE
    SYNTAX      OtnTcmLevel
    MAX-ACCESS  read-write
    STATUS      current 
    DESCRIPTION
        "Configuration of TCMB level." 
    ::=  { deployProvIfEntry 13 }

deployProvIfSigDegThresSonetLine OBJECT-TYPE
    SYNTAX      FspR7BERThreshold
    MAX-ACCESS  read-write
    STATUS      current 
    DESCRIPTION
        "Bit-Error-Based Degradation Definition for SONET (standard integration period)" 
    ::=  { deployProvIfEntry 14 }

deployProvIfSigDegThresSdhMs OBJECT-TYPE
    SYNTAX      Unsigned32 (1..100)
    UNITS       "%"
    MAX-ACCESS  read-write
    STATUS      current 
    DESCRIPTION
        "Block-Error-Based Degradation Definition for SDH (standard integration period).
         Defined as percentage Background Block Errors (30% default) evaluated
         over a defined period (SDPER-RS)." 
    ::=  { deployProvIfEntry 15 }

deployProvIfSignalDegradePeriod OBJECT-TYPE
    SYNTAX      Unsigned32 (2..10)
    UNITS       "s"
    MAX-ACCESS  read-write
    STATUS      current 
    DESCRIPTION
        "The measurement period in seconds used together with
         the deployProvIfSigDegThresSdhRegSect based on the
         block error counting method.
         The valid range is 2..10,
         The default being 7." 
    ::=  { deployProvIfEntry 16 }

deployProvIfAutonegotiation OBJECT-TYPE
    SYNTAX      EnableState
    MAX-ACCESS  read-write
    STATUS      current 
    DESCRIPTION
        "Autonegotiation of the data rate" 
    ::=  { deployProvIfEntry 17 }

deployProvIfBitrate OBJECT-TYPE
    SYNTAX      FspR7Bitrate
    MAX-ACCESS  read-write
    STATUS      current 
    DESCRIPTION
        "Provisioned data rate" 
    ::=  { deployProvIfEntry 18 }

deployProvIfDuplex OBJECT-TYPE
    SYNTAX      EthDuplexMode
    MAX-ACCESS  read-write
    STATUS      current 
    DESCRIPTION
        "Duplex Mode Provision." 
    ::=  { deployProvIfEntry 19 }

deployProvIfFlowControl OBJECT-TYPE
    SYNTAX      FspR7FlowControlMode
    MAX-ACCESS  read-write
    STATUS      current 
    DESCRIPTION
        "Flow Control mechanism" 
    ::=  { deployProvIfEntry 20 }

deployProvIfOtnStuffing OBJECT-TYPE
    SYNTAX      EnableState
    MAX-ACCESS  read-write
    STATUS      current 
    DESCRIPTION
        "Indicates if bit/byte stuffing is used in the transport signal." 
    ::=  { deployProvIfEntry 21 }

deployProvIfSigDegThresOtu OBJECT-TYPE
    SYNTAX      Integer32 (1..100)
    UNITS       "%"
    MAX-ACCESS  read-write
    STATUS      current 
    DESCRIPTION
        "Background-Block-Error-Based Signal Degradation Definition for OTU" 
    ::=  { deployProvIfEntry 22 }

deployProvIfSigDegPeriodOtu OBJECT-TYPE
    SYNTAX      Unsigned32 (2..10)
    UNITS       "s"
    MAX-ACCESS  read-write
    STATUS      current 
    DESCRIPTION
        "Integration Period for Signal degrade (standard integration period?)" 
    ::=  { deployProvIfEntry 23 }

deployProvIfSigDegThresOdu OBJECT-TYPE
    SYNTAX      Integer32 (1..100)
    UNITS       "%"
    MAX-ACCESS  read-write
    STATUS      current 
    DESCRIPTION
        "Background-Block-Error-Based Signal Degradation Definition for ODU" 
    ::=  { deployProvIfEntry 24 }

deployProvIfSigDegPeriodOdu OBJECT-TYPE
    SYNTAX      Unsigned32 (2..10)
    UNITS       "s"
    MAX-ACCESS  read-write
    STATUS      current 
    DESCRIPTION
        "Integration Period for Signal degrade (standard integration period?)" 
    ::=  { deployProvIfEntry 25 }

deployProvIfSigDegThresOduTcmA OBJECT-TYPE
    SYNTAX      Integer32 (1..100)
    UNITS       "%"
    MAX-ACCESS  read-write
    STATUS      current 
    DESCRIPTION
        "Background-Block-Error-Based Signal Degradation Definition for TCM-A" 
    ::=  { deployProvIfEntry 26 }

deployProvIfSigDegPeriodOduTcmA OBJECT-TYPE
    SYNTAX      Unsigned32 (2..10)
    UNITS       "s"
    MAX-ACCESS  read-write
    STATUS      current 
    DESCRIPTION
        "Integration Period for Signal degrade (standard integration period?)" 
    ::=  { deployProvIfEntry 27 }

deployProvIfSigDegThresOduTcmB OBJECT-TYPE
    SYNTAX      Integer32 (1..100)
    UNITS       "%"
    MAX-ACCESS  read-write
    STATUS      current 
    DESCRIPTION
        "Background-Block-Error-Based Signal Degradation Definition for TCM-B" 
    ::=  { deployProvIfEntry 28 }

deployProvIfSigDegPeriodOduTcmB OBJECT-TYPE
    SYNTAX      Unsigned32 (2..10)
    UNITS       "s"
    MAX-ACCESS  read-write
    STATUS      current 
    DESCRIPTION
        "Integration Period of TCMB Signal Segrade (standard integration period?)" 
    ::=  { deployProvIfEntry 29 }

deployProvIfTilt OBJECT-TYPE
    SYNTAX      Integer32 (-20..0)
    UNITS       "0.1 dB"
    MAX-ACCESS  read-write
    STATUS      current 
    DESCRIPTION
        "Tilt." 
    ::=  { deployProvIfEntry 30 }

deployProvIfGain OBJECT-TYPE
    SYNTAX      FspR7Gain
    MAX-ACCESS  read-write
    STATUS      current 
    DESCRIPTION
        "Gain." 
    ::=  { deployProvIfEntry 31 }

deployProvIfAdmin OBJECT-TYPE
    SYNTAX      FspR7AdminState
    MAX-ACCESS  read-write
    STATUS      current 
    DESCRIPTION
        "The Adminstrative State." 
    ::=  { deployProvIfEntry 32 }

deployProvIfAttenuationGradient OBJECT-TYPE
    SYNTAX      Unsigned32 (5..30)
    UNITS       "0.1 dB/min"
    MAX-ACCESS  read-write
    STATUS      current 
    DESCRIPTION
        "Attenuation Gradient Threshold on Receive Fiber. Applies to both TRMT and RCV directions; but threshold violation is reported for each direction separately by the 'tapping' alarms: INTRUDE-RCV and INTRUDE-TRMT." 
    ::=  { deployProvIfEntry 33 }

deployProvIfSigDegThresReceiver OBJECT-TYPE
    SYNTAX      Unsigned32
    UNITS       "0.1 dB"
    MAX-ACCESS  read-write
    STATUS      current 
    DESCRIPTION
        "Signal Degrade Threshold on Receiver. Reported as ATTRMT-SDHT to far end." 
    ::=  { deployProvIfEntry 34 }

deployProvIfTcmCLevel OBJECT-TYPE
    SYNTAX      OtnTcmLevel
    MAX-ACCESS  read-write
    STATUS      current 
    DESCRIPTION
        "Activation of Tandem Connection Monitoring Instance C" 
    ::=  { deployProvIfEntry 35 }

deployProvIfSigDegThresOduTcmC OBJECT-TYPE
    SYNTAX      Integer32 (1..100)
    UNITS       "%"
    MAX-ACCESS  read-write
    STATUS      current 
    DESCRIPTION
        "Background-Block-Error-Based Signal Degradation Definition for TCM-C" 
    ::=  { deployProvIfEntry 36 }

deployProvIfSigDegPeriodOduTcmC OBJECT-TYPE
    SYNTAX      Unsigned32 (2..10)
    UNITS       "s"
    MAX-ACCESS  read-write
    STATUS      current 
    DESCRIPTION
        "Integration Period of TCMC Signal Segrade (standard integration period?)" 
    ::=  { deployProvIfEntry 37 }

deployProvIfDisparityCorrection OBJECT-TYPE
    SYNTAX      EnableState
    MAX-ACCESS  read-write
    STATUS      current 
    DESCRIPTION
        "Disparity correction" 
    ::=  { deployProvIfEntry 38 }

deployProvIfIpAddr OBJECT-TYPE
    SYNTAX      IpAddress
    MAX-ACCESS  read-write
    STATUS      current 
    DESCRIPTION
        "IP Address assigned to LAN IP Interface" 
    ::=  { deployProvIfEntry 39 }

deployProvIfIpMask OBJECT-TYPE
    SYNTAX      IpAddress
    MAX-ACCESS  read-write
    STATUS      current 
    DESCRIPTION
        "IP MASK assigned to LAN IP Interface" 
    ::=  { deployProvIfEntry 40 }

deployProvIfOspf OBJECT-TYPE
    SYNTAX      EnableState
    MAX-ACCESS  read-write
    STATUS      current 
    DESCRIPTION
        "OSPF Routing (Dynamic)" 
    ::=  { deployProvIfEntry 41 }

deployProvIfMetric OBJECT-TYPE
    SYNTAX      Unsigned32 (0..65535)
    MAX-ACCESS  read-write
    STATUS      current 
    DESCRIPTION
        "Routing Metric" 
    ::=  { deployProvIfEntry 42 }

deployProvIfAreaId OBJECT-TYPE
    SYNTAX      IpAddress
    MAX-ACCESS  read-write
    STATUS      current 
    DESCRIPTION
        "OSPF Area ID for IP Interface" 
    ::=  { deployProvIfEntry 43 }

deployProvIfCapTable OBJECT-TYPE
    SYNTAX      SEQUENCE OF DeployProvIfCapEntry
    MAX-ACCESS  not-accessible
    STATUS      current 
    DESCRIPTION
        "Contains entries for deployProv of interfaces." 
    ::=  { facilityDeployProv 2 }

deployProvIfCapEntry OBJECT-TYPE
    SYNTAX      DeployProvIfCapEntry
    MAX-ACCESS  not-accessible
    STATUS      current 
    DESCRIPTION
        "All interfaces which are provisioned(or during deployProv) will have an entry
         in this table." 
    INDEX       { entityIndex } 
    ::=  { deployProvIfCapTable  1  }

DeployProvIfCapEntry ::=  SEQUENCE
  { deployProvIfCapRowStatus FspR7RowStatusCaps,
    deployProvIfCapForceDestroy FspR7ForcedStatusCaps,
    deployProvIfCapType FspR7InterfaceTypeCaps,
    deployProvIfCapPayload OtnPayloadTypeCaps,
    deployProvIfCapBehaviour FspR7PortBehaviourCaps,
    deployProvIfCapTerminationLevel OhTerminationLevelCaps,
    deployProvIfCapAlsMode FspR7AlsModeCaps,
    deployProvIfCapErrorForwarding FspR7ErrorFwdModeCaps,
    deployProvIfCapLaserOffDelayFunction EnableStateCaps,
    deployProvIfCapFecType FspR7FecTypeCaps,
    deployProvIfCapTimingSource SonetTimingSourceCaps,
    deployProvIfCapTcmALevel OtnTcmLevelCaps,
    deployProvIfCapTcmBLevel OtnTcmLevelCaps,
    deployProvIfCapSigDegThresSonetLine FspR7BERThresholdCaps,
    deployProvIfCapSigDegThresSdhMs FspR7Unsigned32Caps,
    deployProvIfCapSignalDegradePeriod FspR7Unsigned32Caps,
    deployProvIfCapAutonegotiation EnableStateCaps,
    deployProvIfCapBitrate FspR7BitrateCaps,
    deployProvIfCapDuplex EthDuplexModeCaps,
    deployProvIfCapFlowControl FspR7FlowControlModeCaps,
    deployProvIfCapOtnStuffing EnableStateCaps,
    deployProvIfCapSigDegThresOtu FspR7Interger32Caps,
    deployProvIfCapSigDegPeriodOtu FspR7Unsigned32Caps,
    deployProvIfCapSigDegThresOdu FspR7Interger32Caps,
    deployProvIfCapSigDegPeriodOdu FspR7Unsigned32Caps,
    deployProvIfCapSigDegThresOduTcmA FspR7Interger32Caps,
    deployProvIfCapSigDegPeriodOduTcmA FspR7Unsigned32Caps,
    deployProvIfCapSigDegThresOduTcmB FspR7Interger32Caps,
    deployProvIfCapSigDegPeriodOduTcmB FspR7Unsigned32Caps,
    deployProvIfCapTilt FspR7Interger32Caps,
    deployProvIfCapGain FspR7GainCaps,
    deployProvIfCapAdmin FspR7AdminStateCaps,
    deployProvIfCapAttenuationGradient FspR7Unsigned32Caps,
    deployProvIfCapSigDegThresReceiver FspR7Unsigned32Caps,
    deployProvIfCapTcmCLevel OtnTcmLevelCaps,
    deployProvIfCapSigDegThresOduTcmC FspR7Interger32Caps,
    deployProvIfCapSigDegPeriodOduTcmC FspR7Unsigned32Caps,
    deployProvIfCapDisparityCorrection EnableStateCaps,
    deployProvIfCapIpAddr FspR7YesNo,
    deployProvIfCapIpMask FspR7YesNo,
    deployProvIfCapOspf EnableStateCaps,
    deployProvIfCapMetric FspR7Unsigned32Caps,
    deployProvIfCapAreaId FspR7YesNo }


  
deployProvIfCapRowStatus OBJECT-TYPE
    SYNTAX      FspR7RowStatusCaps
    MAX-ACCESS  read-only
    STATUS      current 
    DESCRIPTION
        "RowStatus" 
    ::=  { deployProvIfCapEntry 1 }

deployProvIfCapForceDestroy OBJECT-TYPE
    SYNTAX      FspR7ForcedStatusCaps
    MAX-ACCESS  read-only
    STATUS      current 
    DESCRIPTION
        "Forced Destroy" 
    ::=  { deployProvIfCapEntry 2 }

deployProvIfCapType OBJECT-TYPE
    SYNTAX      FspR7InterfaceTypeCaps
    MAX-ACCESS  read-only
    STATUS      current 
    DESCRIPTION
        "The TYPE defines the transport service type as wrapper with wrapper layer
         termination OR else as payload" 
    ::=  { deployProvIfCapEntry 3 }

deployProvIfCapPayload OBJECT-TYPE
    SYNTAX      OtnPayloadTypeCaps
    MAX-ACCESS  read-only
    STATUS      current 
    DESCRIPTION
        "The payload of the interface (inside a transport overhead).
         Relevant e. g. for OTN cards which wrap a payload into an OTU1/2 wrapper." 
    ::=  { deployProvIfCapEntry 4 }

deployProvIfCapBehaviour OBJECT-TYPE
    SYNTAX      FspR7PortBehaviourCaps
    MAX-ACCESS  read-only
    STATUS      current 
    DESCRIPTION
        "The configured behaviour of the interface. If configured as
         a network interface, the interface will use a WDM laser." 
    ::=  { deployProvIfCapEntry 5 }

deployProvIfCapTerminationLevel OBJECT-TYPE
    SYNTAX      OhTerminationLevelCaps
    MAX-ACCESS  read-only
    STATUS      current 
    DESCRIPTION
        "Signal Tremination Level of Intrusive Access to Header Information.
         Not used in 7.0, monitoring is one layer higher than TERM level,
         if applicable. All conditions detected on monitoring layer will not
         be reported (severity degradated to NR)." 
    ::=  { deployProvIfCapEntry 6 }

deployProvIfCapAlsMode OBJECT-TYPE
    SYNTAX      FspR7AlsModeCaps
    MAX-ACCESS  read-only
    STATUS      current 
    DESCRIPTION
        "A configuration request for the Automatic Laser Shutdown (ALS)
         function. Refer to FspR7AlsMode Textual Convention for details." 
    ::=  { deployProvIfCapEntry 7 }

deployProvIfCapErrorForwarding OBJECT-TYPE
    SYNTAX      FspR7ErrorFwdModeCaps
    MAX-ACCESS  read-only
    STATUS      current 
    DESCRIPTION
        "A configuration request for the error forwarding
         function. Refer to FspR7ErrorFwdMode Textual Convention for details." 
    ::=  { deployProvIfCapEntry 8 }

deployProvIfCapLaserOffDelayFunction OBJECT-TYPE
    SYNTAX      EnableStateCaps
    MAX-ACCESS  read-only
    STATUS      current 
    DESCRIPTION
        "A configuration request for the Laser Off Delay function. This function
         delays turning off the laser as a consequent action to a defect." 
    ::=  { deployProvIfCapEntry 9 }

deployProvIfCapFecType OBJECT-TYPE
    SYNTAX      FspR7FecTypeCaps
    MAX-ACCESS  read-only
    STATUS      current 
    DESCRIPTION
        "Configuration of FEC type." 
    ::=  { deployProvIfCapEntry 10 }

deployProvIfCapTimingSource OBJECT-TYPE
    SYNTAX      SonetTimingSourceCaps
    MAX-ACCESS  read-only
    STATUS      current 
    DESCRIPTION
        "The timing source for this interface.
         - internal: used in stand-alone, point-to-point topologies
         stand-alone (dedicated fiber operation)
         - loopTiming: e.g. used in point-to-point via SONET network and
         feeder topologies.
         The default is internal(1)." 
    ::=  { deployProvIfCapEntry 11 }

deployProvIfCapTcmALevel OBJECT-TYPE
    SYNTAX      OtnTcmLevelCaps
    MAX-ACCESS  read-only
    STATUS      current 
    DESCRIPTION
        "Configuration of TCMA level." 
    ::=  { deployProvIfCapEntry 12 }

deployProvIfCapTcmBLevel OBJECT-TYPE
    SYNTAX      OtnTcmLevelCaps
    MAX-ACCESS  read-only
    STATUS      current 
    DESCRIPTION
        "Configuration of TCMB level." 
    ::=  { deployProvIfCapEntry 13 }

deployProvIfCapSigDegThresSonetLine OBJECT-TYPE
    SYNTAX      FspR7BERThresholdCaps
    MAX-ACCESS  read-only
    STATUS      current 
    DESCRIPTION
        "Bit-Error-Based Degradation Definition for SONET (standard integration period)" 
    ::=  { deployProvIfCapEntry 14 }

deployProvIfCapSigDegThresSdhMs OBJECT-TYPE
    SYNTAX      FspR7Unsigned32Caps
    UNITS       "%"
    MAX-ACCESS  read-only
    STATUS      current 
    DESCRIPTION
        "Block-Error-Based Degradation Definition for SDH (standard integration period).
         Defined as percentage Background Block Errors (30% default) evaluated
         over a defined period (SDPER-RS)." 
    ::=  { deployProvIfCapEntry 15 }

deployProvIfCapSignalDegradePeriod OBJECT-TYPE
    SYNTAX      FspR7Unsigned32Caps
    UNITS       "s"
    MAX-ACCESS  read-only
    STATUS      current 
    DESCRIPTION
        "The measurement period in seconds used together with
         the deployProvIfSigDegThresSdhRegSect based on the
         block error counting method.
         The valid range is 2..10,
         The default being 7." 
    ::=  { deployProvIfCapEntry 16 }

deployProvIfCapAutonegotiation OBJECT-TYPE
    SYNTAX      EnableStateCaps
    MAX-ACCESS  read-only
    STATUS      current 
    DESCRIPTION
        "Autonegotiation of the data rate" 
    ::=  { deployProvIfCapEntry 17 }

deployProvIfCapBitrate OBJECT-TYPE
    SYNTAX      FspR7BitrateCaps
    MAX-ACCESS  read-only
    STATUS      current 
    DESCRIPTION
        "Provisioned data rate" 
    ::=  { deployProvIfCapEntry 18 }

deployProvIfCapDuplex OBJECT-TYPE
    SYNTAX      EthDuplexModeCaps
    MAX-ACCESS  read-only
    STATUS      current 
    DESCRIPTION
        "Duplex Mode Provision." 
    ::=  { deployProvIfCapEntry 19 }

deployProvIfCapFlowControl OBJECT-TYPE
    SYNTAX      FspR7FlowControlModeCaps
    MAX-ACCESS  read-only
    STATUS      current 
    DESCRIPTION
        "Flow Control mechanism" 
    ::=  { deployProvIfCapEntry 20 }

deployProvIfCapOtnStuffing OBJECT-TYPE
    SYNTAX      EnableStateCaps
    MAX-ACCESS  read-only
    STATUS      current 
    DESCRIPTION
        "Indicates if bit/byte stuffing is used in the transport signal." 
    ::=  { deployProvIfCapEntry 21 }

deployProvIfCapSigDegThresOtu OBJECT-TYPE
    SYNTAX      FspR7Interger32Caps
    UNITS       "%"
    MAX-ACCESS  read-only
    STATUS      current 
    DESCRIPTION
        "Background-Block-Error-Based Signal Degradation Definition for OTU" 
    ::=  { deployProvIfCapEntry 22 }

deployProvIfCapSigDegPeriodOtu OBJECT-TYPE
    SYNTAX      FspR7Unsigned32Caps
    UNITS       "s"
    MAX-ACCESS  read-only
    STATUS      current 
    DESCRIPTION
        "Integration Period for Signal degrade (standard integration period?)" 
    ::=  { deployProvIfCapEntry 23 }

deployProvIfCapSigDegThresOdu OBJECT-TYPE
    SYNTAX      FspR7Interger32Caps
    UNITS       "%"
    MAX-ACCESS  read-only
    STATUS      current 
    DESCRIPTION
        "Background-Block-Error-Based Signal Degradation Definition for ODU" 
    ::=  { deployProvIfCapEntry 24 }

deployProvIfCapSigDegPeriodOdu OBJECT-TYPE
    SYNTAX      FspR7Unsigned32Caps
    UNITS       "s"
    MAX-ACCESS  read-only
    STATUS      current 
    DESCRIPTION
        "Integration Period for Signal degrade (standard integration period?)" 
    ::=  { deployProvIfCapEntry 25 }

deployProvIfCapSigDegThresOduTcmA OBJECT-TYPE
    SYNTAX      FspR7Interger32Caps
    UNITS       "%"
    MAX-ACCESS  read-only
    STATUS      current 
    DESCRIPTION
        "Background-Block-Error-Based Signal Degradation Definition for TCM-A" 
    ::=  { deployProvIfCapEntry 26 }

deployProvIfCapSigDegPeriodOduTcmA OBJECT-TYPE
    SYNTAX      FspR7Unsigned32Caps
    UNITS       "s"
    MAX-ACCESS  read-only
    STATUS      current 
    DESCRIPTION
        "Integration Period for Signal degrade (standard integration period?)" 
    ::=  { deployProvIfCapEntry 27 }

deployProvIfCapSigDegThresOduTcmB OBJECT-TYPE
    SYNTAX      FspR7Interger32Caps
    UNITS       "%"
    MAX-ACCESS  read-only
    STATUS      current 
    DESCRIPTION
        "Background-Block-Error-Based Signal Degradation Definition for TCM-B" 
    ::=  { deployProvIfCapEntry 28 }

deployProvIfCapSigDegPeriodOduTcmB OBJECT-TYPE
    SYNTAX      FspR7Unsigned32Caps
    UNITS       "s"
    MAX-ACCESS  read-only
    STATUS      current 
    DESCRIPTION
        "Integration Period of TCMB Signal Segrade (standard integration period?)" 
    ::=  { deployProvIfCapEntry 29 }

deployProvIfCapTilt OBJECT-TYPE
    SYNTAX      FspR7Interger32Caps
    UNITS       "0.1 dB"
    MAX-ACCESS  read-only
    STATUS      current 
    DESCRIPTION
        "Tilt." 
    ::=  { deployProvIfCapEntry 30 }

deployProvIfCapGain OBJECT-TYPE
    SYNTAX      FspR7GainCaps
    MAX-ACCESS  read-only
    STATUS      current 
    DESCRIPTION
        "Gain." 
    ::=  { deployProvIfCapEntry 31 }

deployProvIfCapAdmin OBJECT-TYPE
    SYNTAX      FspR7AdminStateCaps
    MAX-ACCESS  read-only
    STATUS      current 
    DESCRIPTION
        "The Adminstrative State." 
    ::=  { deployProvIfCapEntry 32 }

deployProvIfCapAttenuationGradient OBJECT-TYPE
    SYNTAX      FspR7Unsigned32Caps
    UNITS       "0.1 dB/min"
    MAX-ACCESS  read-only
    STATUS      current 
    DESCRIPTION
        "Attenuation Gradient Threshold on Receive Fiber. Applies to both TRMT and RCV directions; but threshold violation is reported for each direction separately by the 'tapping' alarms: INTRUDE-RCV and INTRUDE-TRMT." 
    ::=  { deployProvIfCapEntry 33 }

deployProvIfCapSigDegThresReceiver OBJECT-TYPE
    SYNTAX      FspR7Unsigned32Caps
    UNITS       "0.1 dB"
    MAX-ACCESS  read-only
    STATUS      current 
    DESCRIPTION
        "Signal Degrade Threshold on Receiver. Reported as ATTRMT-SDHT to far end." 
    ::=  { deployProvIfCapEntry 34 }

deployProvIfCapTcmCLevel OBJECT-TYPE
    SYNTAX      OtnTcmLevelCaps
    MAX-ACCESS  read-only
    STATUS      current 
    DESCRIPTION
        "Activation of Tandem Connection Monitoring Instance C" 
    ::=  { deployProvIfCapEntry 35 }

deployProvIfCapSigDegThresOduTcmC OBJECT-TYPE
    SYNTAX      FspR7Interger32Caps
    UNITS       "%"
    MAX-ACCESS  read-only
    STATUS      current 
    DESCRIPTION
        "Background-Block-Error-Based Signal Degradation Definition for TCM-C" 
    ::=  { deployProvIfCapEntry 36 }

deployProvIfCapSigDegPeriodOduTcmC OBJECT-TYPE
    SYNTAX      FspR7Unsigned32Caps
    UNITS       "s"
    MAX-ACCESS  read-only
    STATUS      current 
    DESCRIPTION
        "Integration Period of TCMC Signal Segrade (standard integration period?)" 
    ::=  { deployProvIfCapEntry 37 }

deployProvIfCapDisparityCorrection OBJECT-TYPE
    SYNTAX      EnableStateCaps
    MAX-ACCESS  read-only
    STATUS      current 
    DESCRIPTION
        "Disparity correction" 
    ::=  { deployProvIfCapEntry 38 }

deployProvIfCapIpAddr OBJECT-TYPE
    SYNTAX      FspR7YesNo
    MAX-ACCESS  read-only
    STATUS      current 
    DESCRIPTION
        "IP Address assigned to LAN IP Interface" 
    ::=  { deployProvIfCapEntry 39 }

deployProvIfCapIpMask OBJECT-TYPE
    SYNTAX      FspR7YesNo
    MAX-ACCESS  read-only
    STATUS      current 
    DESCRIPTION
        "IP MASK assigned to LAN IP Interface" 
    ::=  { deployProvIfCapEntry 40 }

deployProvIfCapOspf OBJECT-TYPE
    SYNTAX      EnableStateCaps
    MAX-ACCESS  read-only
    STATUS      current 
    DESCRIPTION
        "OSPF Routing (Dynamic)" 
    ::=  { deployProvIfCapEntry 41 }

deployProvIfCapMetric OBJECT-TYPE
    SYNTAX      FspR7Unsigned32Caps
    MAX-ACCESS  read-only
    STATUS      current 
    DESCRIPTION
        "Routing Metric" 
    ::=  { deployProvIfCapEntry 42 }

deployProvIfCapAreaId OBJECT-TYPE
    SYNTAX      FspR7YesNo
    MAX-ACCESS  read-only
    STATUS      current 
    DESCRIPTION
        "OSPF Area ID for IP Interface" 
    ::=  { deployProvIfCapEntry 43 }

deployProvIfDefaultsTable OBJECT-TYPE
    SYNTAX      SEQUENCE OF DeployProvIfDefaultsEntry
    MAX-ACCESS  not-accessible
    STATUS      current 
    DESCRIPTION
        "Contains entries for deployProv of interfaces." 
    ::=  { facilityDeployProv 3 }

deployProvIfDefaultsEntry OBJECT-TYPE
    SYNTAX      DeployProvIfDefaultsEntry
    MAX-ACCESS  not-accessible
    STATUS      current 
    DESCRIPTION
        "All interfaces which are provisioned(or during deployProv) will have an entry
         in this table." 
    INDEX       { entityIndex } 
    ::=  { deployProvIfDefaultsTable  1  }

DeployProvIfDefaultsEntry ::=  SEQUENCE
  { deployProvIfDefaultsRowStatus RowStatus,
    deployProvIfDefaultsForceDestroy FspR7ForcedStatus,
    deployProvIfDefaultsType FspR7InterfaceType,
    deployProvIfDefaultsPayload OtnPayloadType,
    deployProvIfDefaultsBehaviour FspR7PortBehaviour,
    deployProvIfDefaultsTerminationLevel OhTerminationLevel,
    deployProvIfDefaultsAlsMode FspR7AlsMode,
    deployProvIfDefaultsErrorForwarding FspR7ErrorFwdMode,
    deployProvIfDefaultsLaserOffDelayFunction EnableState,
    deployProvIfDefaultsFecType FspR7FecType,
    deployProvIfDefaultsTimingSource SonetTimingSource,
    deployProvIfDefaultsTcmALevel OtnTcmLevel,
    deployProvIfDefaultsTcmBLevel OtnTcmLevel,
    deployProvIfDefaultsSigDegThresSonetLine FspR7BERThreshold,
    deployProvIfDefaultsSigDegThresSdhMs Unsigned32,
    deployProvIfDefaultsSignalDegradePeriod Unsigned32,
    deployProvIfDefaultsAutonegotiation EnableState,
    deployProvIfDefaultsBitrate FspR7Bitrate,
    deployProvIfDefaultsDuplex EthDuplexMode,
    deployProvIfDefaultsFlowControl FspR7FlowControlMode,
    deployProvIfDefaultsOtnStuffing EnableState,
    deployProvIfDefaultsSigDegThresOtu Integer32,
    deployProvIfDefaultsSigDegPeriodOtu Unsigned32,
    deployProvIfDefaultsSigDegThresOdu Integer32,
    deployProvIfDefaultsSigDegPeriodOdu Unsigned32,
    deployProvIfDefaultsSigDegThresOduTcmA Integer32,
    deployProvIfDefaultsSigDegPeriodOduTcmA Unsigned32,
    deployProvIfDefaultsSigDegThresOduTcmB Integer32,
    deployProvIfDefaultsSigDegPeriodOduTcmB Unsigned32,
    deployProvIfDefaultsTilt Integer32,
    deployProvIfDefaultsGain FspR7Gain,
    deployProvIfDefaultsAdmin FspR7AdminState,
    deployProvIfDefaultsAttenuationGradient Unsigned32,
    deployProvIfDefaultsSigDegThresReceiver Unsigned32,
    deployProvIfDefaultsTcmCLevel OtnTcmLevel,
    deployProvIfDefaultsSigDegThresOduTcmC Integer32,
    deployProvIfDefaultsSigDegPeriodOduTcmC Unsigned32,
    deployProvIfDefaultsDisparityCorrection EnableState,
    deployProvIfDefaultsIpAddr IpAddress,
    deployProvIfDefaultsIpMask IpAddress,
    deployProvIfDefaultsOspf EnableState,
    deployProvIfDefaultsMetric Unsigned32,
    deployProvIfDefaultsAreaId IpAddress }


  
deployProvIfDefaultsRowStatus OBJECT-TYPE
    SYNTAX      RowStatus
    MAX-ACCESS  read-only
    STATUS      current 
    DESCRIPTION
        "RowStatus" 
    ::=  { deployProvIfDefaultsEntry 1 }

deployProvIfDefaultsForceDestroy OBJECT-TYPE
    SYNTAX      FspR7ForcedStatus
    MAX-ACCESS  read-only
    STATUS      current 
    DESCRIPTION
        "Forced Destroy" 
    ::=  { deployProvIfDefaultsEntry 2 }

deployProvIfDefaultsType OBJECT-TYPE
    SYNTAX      FspR7InterfaceType
    MAX-ACCESS  read-only
    STATUS      current 
    DESCRIPTION
        "The TYPE defines the transport service type as wrapper with wrapper layer
         termination OR else as payload" 
    ::=  { deployProvIfDefaultsEntry 3 }

deployProvIfDefaultsPayload OBJECT-TYPE
    SYNTAX      OtnPayloadType
    MAX-ACCESS  read-only
    STATUS      current 
    DESCRIPTION
        "The payload of the interface (inside a transport overhead).
         Relevant e. g. for OTN cards which wrap a payload into an OTU1/2 wrapper." 
    ::=  { deployProvIfDefaultsEntry 4 }

deployProvIfDefaultsBehaviour OBJECT-TYPE
    SYNTAX      FspR7PortBehaviour
    MAX-ACCESS  read-only
    STATUS      current 
    DESCRIPTION
        "The configured behaviour of the interface. If configured as
         a network interface, the interface will use a WDM laser." 
    ::=  { deployProvIfDefaultsEntry 5 }

deployProvIfDefaultsTerminationLevel OBJECT-TYPE
    SYNTAX      OhTerminationLevel
    MAX-ACCESS  read-only
    STATUS      current 
    DESCRIPTION
        "Signal Tremination Level of Intrusive Access to Header Information.
         Not used in 7.0, monitoring is one layer higher than TERM level,
         if applicable. All conditions detected on monitoring layer will not
         be reported (severity degradated to NR)." 
    ::=  { deployProvIfDefaultsEntry 6 }

deployProvIfDefaultsAlsMode OBJECT-TYPE
    SYNTAX      FspR7AlsMode
    MAX-ACCESS  read-only
    STATUS      current 
    DESCRIPTION
        "A configuration request for the Automatic Laser Shutdown (ALS)
         function. Refer to FspR7AlsMode Textual Convention for details." 
    ::=  { deployProvIfDefaultsEntry 7 }

deployProvIfDefaultsErrorForwarding OBJECT-TYPE
    SYNTAX      FspR7ErrorFwdMode
    MAX-ACCESS  read-only
    STATUS      current 
    DESCRIPTION
        "A configuration request for the error forwarding
         function. Refer to FspR7ErrorFwdMode Textual Convention for details." 
    ::=  { deployProvIfDefaultsEntry 8 }

deployProvIfDefaultsLaserOffDelayFunction OBJECT-TYPE
    SYNTAX      EnableState
    MAX-ACCESS  read-only
    STATUS      current 
    DESCRIPTION
        "A configuration request for the Laser Off Delay function. This function
         delays turning off the laser as a consequent action to a defect." 
    ::=  { deployProvIfDefaultsEntry 9 }

deployProvIfDefaultsFecType OBJECT-TYPE
    SYNTAX      FspR7FecType
    MAX-ACCESS  read-only
    STATUS      current 
    DESCRIPTION
        "Configuration of FEC type." 
    ::=  { deployProvIfDefaultsEntry 10 }

deployProvIfDefaultsTimingSource OBJECT-TYPE
    SYNTAX      SonetTimingSource
    MAX-ACCESS  read-only
    STATUS      current 
    DESCRIPTION
        "The timing source for this interface.
         - internal: used in stand-alone, point-to-point topologies
         stand-alone (dedicated fiber operation)
         - loopTiming: e.g. used in point-to-point via SONET network and
         feeder topologies.
         The default is internal(1)." 
    ::=  { deployProvIfDefaultsEntry 11 }

deployProvIfDefaultsTcmALevel OBJECT-TYPE
    SYNTAX      OtnTcmLevel
    MAX-ACCESS  read-only
    STATUS      current 
    DESCRIPTION
        "Configuration of TCMA level." 
    ::=  { deployProvIfDefaultsEntry 12 }

deployProvIfDefaultsTcmBLevel OBJECT-TYPE
    SYNTAX      OtnTcmLevel
    MAX-ACCESS  read-only
    STATUS      current 
    DESCRIPTION
        "Configuration of TCMB level." 
    ::=  { deployProvIfDefaultsEntry 13 }

deployProvIfDefaultsSigDegThresSonetLine OBJECT-TYPE
    SYNTAX      FspR7BERThreshold
    MAX-ACCESS  read-only
    STATUS      current 
    DESCRIPTION
        "Bit-Error-Based Degradation Definition for SONET (standard integration period)" 
    ::=  { deployProvIfDefaultsEntry 14 }

deployProvIfDefaultsSigDegThresSdhMs OBJECT-TYPE
    SYNTAX      Unsigned32 (1..100)
    UNITS       "%"
    MAX-ACCESS  read-only
    STATUS      current 
    DESCRIPTION
        "Block-Error-Based Degradation Definition for SDH (standard integration period).
         Defined as percentage Background Block Errors (30% default) evaluated
         over a defined period (SDPER-RS)." 
    ::=  { deployProvIfDefaultsEntry 15 }

deployProvIfDefaultsSignalDegradePeriod OBJECT-TYPE
    SYNTAX      Unsigned32 (2..10)
    UNITS       "s"
    MAX-ACCESS  read-only
    STATUS      current 
    DESCRIPTION
        "The measurement period in seconds used together with
         the deployProvIfSigDegThresSdhRegSect based on the
         block error counting method.
         The valid range is 2..10,
         The default being 7." 
    ::=  { deployProvIfDefaultsEntry 16 }

deployProvIfDefaultsAutonegotiation OBJECT-TYPE
    SYNTAX      EnableState
    MAX-ACCESS  read-only
    STATUS      current 
    DESCRIPTION
        "Autonegotiation of the data rate" 
    ::=  { deployProvIfDefaultsEntry 17 }

deployProvIfDefaultsBitrate OBJECT-TYPE
    SYNTAX      FspR7Bitrate
    MAX-ACCESS  read-only
    STATUS      current 
    DESCRIPTION
        "Provisioned data rate" 
    ::=  { deployProvIfDefaultsEntry 18 }

deployProvIfDefaultsDuplex OBJECT-TYPE
    SYNTAX      EthDuplexMode
    MAX-ACCESS  read-only
    STATUS      current 
    DESCRIPTION
        "Duplex Mode Provision." 
    ::=  { deployProvIfDefaultsEntry 19 }

deployProvIfDefaultsFlowControl OBJECT-TYPE
    SYNTAX      FspR7FlowControlMode
    MAX-ACCESS  read-only
    STATUS      current 
    DESCRIPTION
        "Flow Control mechanism" 
    ::=  { deployProvIfDefaultsEntry 20 }

deployProvIfDefaultsOtnStuffing OBJECT-TYPE
    SYNTAX      EnableState
    MAX-ACCESS  read-only
    STATUS      current 
    DESCRIPTION
        "Indicates if bit/byte stuffing is used in the transport signal." 
    ::=  { deployProvIfDefaultsEntry 21 }

deployProvIfDefaultsSigDegThresOtu OBJECT-TYPE
    SYNTAX      Integer32 (1..100)
    UNITS       "%"
    MAX-ACCESS  read-only
    STATUS      current 
    DESCRIPTION
        "Background-Block-Error-Based Signal Degradation Definition for OTU" 
    ::=  { deployProvIfDefaultsEntry 22 }

deployProvIfDefaultsSigDegPeriodOtu OBJECT-TYPE
    SYNTAX      Unsigned32 (2..10)
    UNITS       "s"
    MAX-ACCESS  read-only
    STATUS      current 
    DESCRIPTION
        "Integration Period for Signal degrade (standard integration period?)" 
    ::=  { deployProvIfDefaultsEntry 23 }

deployProvIfDefaultsSigDegThresOdu OBJECT-TYPE
    SYNTAX      Integer32 (1..100)
    UNITS       "%"
    MAX-ACCESS  read-only
    STATUS      current 
    DESCRIPTION
        "Background-Block-Error-Based Signal Degradation Definition for ODU" 
    ::=  { deployProvIfDefaultsEntry 24 }

deployProvIfDefaultsSigDegPeriodOdu OBJECT-TYPE
    SYNTAX      Unsigned32 (2..10)
    UNITS       "s"
    MAX-ACCESS  read-only
    STATUS      current 
    DESCRIPTION
        "Integration Period for Signal degrade (standard integration period?)" 
    ::=  { deployProvIfDefaultsEntry 25 }

deployProvIfDefaultsSigDegThresOduTcmA OBJECT-TYPE
    SYNTAX      Integer32 (1..100)
    UNITS       "%"
    MAX-ACCESS  read-only
    STATUS      current 
    DESCRIPTION
        "Background-Block-Error-Based Signal Degradation Definition for TCM-A" 
    ::=  { deployProvIfDefaultsEntry 26 }

deployProvIfDefaultsSigDegPeriodOduTcmA OBJECT-TYPE
    SYNTAX      Unsigned32 (2..10)
    UNITS       "s"
    MAX-ACCESS  read-only
    STATUS      current 
    DESCRIPTION
        "Integration Period for Signal degrade (standard integration period?)" 
    ::=  { deployProvIfDefaultsEntry 27 }

deployProvIfDefaultsSigDegThresOduTcmB OBJECT-TYPE
    SYNTAX      Integer32 (1..100)
    UNITS       "%"
    MAX-ACCESS  read-only
    STATUS      current 
    DESCRIPTION
        "Background-Block-Error-Based Signal Degradation Definition for TCM-B" 
    ::=  { deployProvIfDefaultsEntry 28 }

deployProvIfDefaultsSigDegPeriodOduTcmB OBJECT-TYPE
    SYNTAX      Unsigned32 (2..10)
    UNITS       "s"
    MAX-ACCESS  read-only
    STATUS      current 
    DESCRIPTION
        "Integration Period of TCMB Signal Segrade (standard integration period?)" 
    ::=  { deployProvIfDefaultsEntry 29 }

deployProvIfDefaultsTilt OBJECT-TYPE
    SYNTAX      Integer32 (-20..0)
    UNITS       "0.1 dB"
    MAX-ACCESS  read-only
    STATUS      current 
    DESCRIPTION
        "Tilt." 
    ::=  { deployProvIfDefaultsEntry 30 }

deployProvIfDefaultsGain OBJECT-TYPE
    SYNTAX      FspR7Gain
    MAX-ACCESS  read-only
    STATUS      current 
    DESCRIPTION
        "Gain." 
    ::=  { deployProvIfDefaultsEntry 31 }

deployProvIfDefaultsAdmin OBJECT-TYPE
    SYNTAX      FspR7AdminState
    MAX-ACCESS  read-only
    STATUS      current 
    DESCRIPTION
        "The Adminstrative State." 
    ::=  { deployProvIfDefaultsEntry 32 }

deployProvIfDefaultsAttenuationGradient OBJECT-TYPE
    SYNTAX      Unsigned32 (5..30)
    UNITS       "0.1 dB/min"
    MAX-ACCESS  read-only
    STATUS      current 
    DESCRIPTION
        "Attenuation Gradient Threshold on Receive Fiber. Applies to both TRMT and RCV directions; but threshold violation is reported for each direction separately by the 'tapping' alarms: INTRUDE-RCV and INTRUDE-TRMT." 
    ::=  { deployProvIfDefaultsEntry 33 }

deployProvIfDefaultsSigDegThresReceiver OBJECT-TYPE
    SYNTAX      Unsigned32
    UNITS       "0.1 dB"
    MAX-ACCESS  read-only
    STATUS      current 
    DESCRIPTION
        "Signal Degrade Threshold on Receiver. Reported as ATTRMT-SDHT to far end." 
    ::=  { deployProvIfDefaultsEntry 34 }

deployProvIfDefaultsTcmCLevel OBJECT-TYPE
    SYNTAX      OtnTcmLevel
    MAX-ACCESS  read-only
    STATUS      current 
    DESCRIPTION
        "Activation of Tandem Connection Monitoring Instance C" 
    ::=  { deployProvIfDefaultsEntry 35 }

deployProvIfDefaultsSigDegThresOduTcmC OBJECT-TYPE
    SYNTAX      Integer32 (1..100)
    UNITS       "%"
    MAX-ACCESS  read-only
    STATUS      current 
    DESCRIPTION
        "Background-Block-Error-Based Signal Degradation Definition for TCM-C" 
    ::=  { deployProvIfDefaultsEntry 36 }

deployProvIfDefaultsSigDegPeriodOduTcmC OBJECT-TYPE
    SYNTAX      Unsigned32 (2..10)
    UNITS       "s"
    MAX-ACCESS  read-only
    STATUS      current 
    DESCRIPTION
        "Integration Period of TCMC Signal Segrade (standard integration period?)" 
    ::=  { deployProvIfDefaultsEntry 37 }

deployProvIfDefaultsDisparityCorrection OBJECT-TYPE
    SYNTAX      EnableState
    MAX-ACCESS  read-only
    STATUS      current 
    DESCRIPTION
        "Disparity correction" 
    ::=  { deployProvIfDefaultsEntry 38 }

deployProvIfDefaultsIpAddr OBJECT-TYPE
    SYNTAX      IpAddress
    MAX-ACCESS  read-only
    STATUS      current 
    DESCRIPTION
        "IP Address assigned to LAN IP Interface" 
    ::=  { deployProvIfDefaultsEntry 39 }

deployProvIfDefaultsIpMask OBJECT-TYPE
    SYNTAX      IpAddress
    MAX-ACCESS  read-only
    STATUS      current 
    DESCRIPTION
        "IP MASK assigned to LAN IP Interface" 
    ::=  { deployProvIfDefaultsEntry 40 }

deployProvIfDefaultsOspf OBJECT-TYPE
    SYNTAX      EnableState
    MAX-ACCESS  read-only
    STATUS      current 
    DESCRIPTION
        "OSPF Routing (Dynamic)" 
    ::=  { deployProvIfDefaultsEntry 41 }

deployProvIfDefaultsMetric OBJECT-TYPE
    SYNTAX      Unsigned32 (0..65535)
    MAX-ACCESS  read-only
    STATUS      current 
    DESCRIPTION
        "Routing Metric" 
    ::=  { deployProvIfDefaultsEntry 42 }

deployProvIfDefaultsAreaId OBJECT-TYPE
    SYNTAX      IpAddress
    MAX-ACCESS  read-only
    STATUS      current 
    DESCRIPTION
        "OSPF Area ID for IP Interface" 
    ::=  { deployProvIfDefaultsEntry 43 }

deployProvVchChannelTable OBJECT-TYPE
    SYNTAX      SEQUENCE OF DeployProvVchChannelEntry
    MAX-ACCESS  not-accessible
    STATUS      current 
    DESCRIPTION
        "
         Contains entries for provisioning of interfaces.
        " 
    ::=  { facilityDeployProv 4 }

deployProvVchChannelEntry OBJECT-TYPE
    SYNTAX      DeployProvVchChannelEntry
    MAX-ACCESS  not-accessible
    STATUS      current 
    DESCRIPTION
        "
         All interfaces which are provisioned(or are during provisioning) will have an entry
         in this table.
        " 
    INDEX       { entityIndex } 
    ::=  { deployProvVchChannelTable  1  }

DeployProvVchChannelEntry ::=  SEQUENCE
  { deployProvVchChannelRowStatus RowStatus,
    deployProvVchChannelForceDestroy FspR7ForcedStatus,
    deployProvVchChannelType FspR7InterfaceType,
    deployProvVchChannelVcgType SonetVcType,
    deployProvVchChannelBundle SonetVcBundleAllocation,
    deployProvVchChannelCir Unsigned32,
    deployProvVchChannelAdmin FspR7AdminState,
    deployProvVchChannelSigDegThresOdu Integer32,
    deployProvVchChannelSigDegPeriodOdu Unsigned32 }


  
deployProvVchChannelRowStatus OBJECT-TYPE
    SYNTAX      RowStatus
    MAX-ACCESS  read-write
    STATUS      current 
    DESCRIPTION
        "RowStatus" 
    ::=  { deployProvVchChannelEntry 1 }

deployProvVchChannelForceDestroy OBJECT-TYPE
    SYNTAX      FspR7ForcedStatus
    MAX-ACCESS  read-write
    STATUS      current 
    DESCRIPTION
        "Forced Destroy" 
    ::=  { deployProvVchChannelEntry 2 }

deployProvVchChannelType OBJECT-TYPE
    SYNTAX      FspR7InterfaceType
    MAX-ACCESS  read-write
    STATUS      current 
    DESCRIPTION
        "The TYPE defines the transport service type as wrapper with wrapper layer termination OR else as payload" 
    ::=  { deployProvVchChannelEntry 3 }

deployProvVchChannelVcgType OBJECT-TYPE
    SYNTAX      SonetVcType
    MAX-ACCESS  read-write
    STATUS      current 
    DESCRIPTION
        "Virtual Container Group Type" 
    ::=  { deployProvVchChannelEntry 4 }

deployProvVchChannelBundle OBJECT-TYPE
    SYNTAX      SonetVcBundleAllocation
    MAX-ACCESS  read-write
    STATUS      current 
    DESCRIPTION
        "List of VC4/VC3/STS1 containers used in the BUNDLE" 
    ::=  { deployProvVchChannelEntry 5 }

deployProvVchChannelCir OBJECT-TYPE
    SYNTAX      Unsigned32
    UNITS       "Mbit/s"
    MAX-ACCESS  read-write
    STATUS      current 
    DESCRIPTION
        "CIR (Comitted Information Rate ) is used on Ethernet Interfaces with a policing function" 
    ::=  { deployProvVchChannelEntry 6 }

deployProvVchChannelAdmin OBJECT-TYPE
    SYNTAX      FspR7AdminState
    MAX-ACCESS  read-write
    STATUS      current 
    DESCRIPTION
        "The Adminstrative State will be displayed in the GUI with full
         name values; it will be differently displayed in TL1 syntax according
         to TL1 display rules. The transaction into the UAS state requires
         a special destroy/delete function." 
    ::=  { deployProvVchChannelEntry 7 }

deployProvVchChannelSigDegThresOdu OBJECT-TYPE
    SYNTAX      Integer32 (1..100)
    UNITS       "%"
    MAX-ACCESS  read-write
    STATUS      current 
    DESCRIPTION
        "Background-Block-Error-Based Signal Degradation Definition for ODU" 
    ::=  { deployProvVchChannelEntry 8 }

deployProvVchChannelSigDegPeriodOdu OBJECT-TYPE
    SYNTAX      Unsigned32 (2..10)
    UNITS       "s"
    MAX-ACCESS  read-write
    STATUS      current 
    DESCRIPTION
        "Integration Period for Signal degrade (standard integration period?)" 
    ::=  { deployProvVchChannelEntry 9 }

deployProvVchChannelCapTable OBJECT-TYPE
    SYNTAX      SEQUENCE OF DeployProvVchChannelCapEntry
    MAX-ACCESS  not-accessible
    STATUS      current 
    DESCRIPTION
        "
         Contains entries for provisioning of interfaces.
        " 
    ::=  { facilityDeployProv 5 }

deployProvVchChannelCapEntry OBJECT-TYPE
    SYNTAX      DeployProvVchChannelCapEntry
    MAX-ACCESS  not-accessible
    STATUS      current 
    DESCRIPTION
        "
         All interfaces which are provisioned(or are during provisioning) will have an entry
         in this table.
        " 
    INDEX       { entityIndex } 
    ::=  { deployProvVchChannelCapTable  1  }

DeployProvVchChannelCapEntry ::=  SEQUENCE
  { deployProvVchChannelCapRowStatus FspR7RowStatusCaps,
    deployProvVchChannelCapForceDestroy FspR7ForcedStatusCaps,
    deployProvVchChannelCapType FspR7InterfaceTypeCaps,
    deployProvVchChannelCapVcgType SonetVcTypeCaps,
    deployProvVchChannelCapBundle SonetVcBundleAllocationCaps,
    deployProvVchChannelCapCir FspR7Unsigned32Caps,
    deployProvVchChannelCapAdmin FspR7AdminStateCaps,
    deployProvVchChannelCapSigDegThresOdu FspR7Interger32Caps,
    deployProvVchChannelCapSigDegPeriodOdu FspR7Unsigned32Caps }


  
deployProvVchChannelCapRowStatus OBJECT-TYPE
    SYNTAX      FspR7RowStatusCaps
    MAX-ACCESS  read-only
    STATUS      current 
    DESCRIPTION
        "RowStatus" 
    ::=  { deployProvVchChannelCapEntry 1 }

deployProvVchChannelCapForceDestroy OBJECT-TYPE
    SYNTAX      FspR7ForcedStatusCaps
    MAX-ACCESS  read-only
    STATUS      current 
    DESCRIPTION
        "Forced Destroy" 
    ::=  { deployProvVchChannelCapEntry 2 }

deployProvVchChannelCapType OBJECT-TYPE
    SYNTAX      FspR7InterfaceTypeCaps
    MAX-ACCESS  read-only
    STATUS      current 
    DESCRIPTION
        "The TYPE defines the transport service type as wrapper with wrapper layer termination OR else as payload" 
    ::=  { deployProvVchChannelCapEntry 3 }

deployProvVchChannelCapVcgType OBJECT-TYPE
    SYNTAX      SonetVcTypeCaps
    MAX-ACCESS  read-only
    STATUS      current 
    DESCRIPTION
        "Virtual Container Group Type" 
    ::=  { deployProvVchChannelCapEntry 4 }

deployProvVchChannelCapBundle OBJECT-TYPE
    SYNTAX      SonetVcBundleAllocationCaps
    MAX-ACCESS  read-only
    STATUS      current 
    DESCRIPTION
        "List of VC4/VC3/STS1 containers used in the BUNDLE" 
    ::=  { deployProvVchChannelCapEntry 5 }

deployProvVchChannelCapCir OBJECT-TYPE
    SYNTAX      FspR7Unsigned32Caps
    UNITS       "Mbit/s"
    MAX-ACCESS  read-only
    STATUS      current 
    DESCRIPTION
        "CIR (Comitted Information Rate ) is used on Ethernet Interfaces with a policing function" 
    ::=  { deployProvVchChannelCapEntry 6 }

deployProvVchChannelCapAdmin OBJECT-TYPE
    SYNTAX      FspR7AdminStateCaps
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvVchChannelCapEntry 7 }

deployProvVchChannelCapSigDegThresOdu OBJECT-TYPE
    SYNTAX      FspR7Interger32Caps
    UNITS       "%"
    MAX-ACCESS  read-only
    STATUS      current 
    DESCRIPTION
        "Background-Block-Error-Based Signal Degradation Definition for ODU" 
    ::=  { deployProvVchChannelCapEntry 8 }

deployProvVchChannelCapSigDegPeriodOdu OBJECT-TYPE
    SYNTAX      FspR7Unsigned32Caps
    UNITS       "s"
    MAX-ACCESS  read-only
    STATUS      current 
    DESCRIPTION
        "Integration Period for Signal degrade (standard integration period?)" 
    ::=  { deployProvVchChannelCapEntry 9 }

deployProvVchChannelDefaultsTable OBJECT-TYPE
    SYNTAX      SEQUENCE OF DeployProvVchChannelDefaultsEntry
    MAX-ACCESS  not-accessible
    STATUS      current 
    DESCRIPTION
        "
         Contains entries for provisioning of interfaces.
        " 
    ::=  { facilityDeployProv 6 }

deployProvVchChannelDefaultsEntry OBJECT-TYPE
    SYNTAX      DeployProvVchChannelDefaultsEntry
    MAX-ACCESS  not-accessible
    STATUS      current 
    DESCRIPTION
        "
         All interfaces which are provisioned(or are during provisioning) will have an entry
         in this table.
        " 
    INDEX       { entityIndex } 
    ::=  { deployProvVchChannelDefaultsTable  1  }

DeployProvVchChannelDefaultsEntry ::=  SEQUENCE
  { deployProvVchChannelDefaultsRowStatus RowStatus,
    deployProvVchChannelDefaultsForceDestroy FspR7ForcedStatus,
    deployProvVchChannelDefaultsType FspR7InterfaceType,
    deployProvVchChannelDefaultsVcgType SonetVcType,
    deployProvVchChannelDefaultsBundle SonetVcBundleAllocation,
    deployProvVchChannelDefaultsCir Unsigned32,
    deployProvVchChannelDefaultsAdmin FspR7AdminState,
    deployProvVchChannelDefaultsSigDegThresOdu Integer32,
    deployProvVchChannelDefaultsSigDegPeriodOdu Unsigned32 }


  
deployProvVchChannelDefaultsRowStatus OBJECT-TYPE
    SYNTAX      RowStatus
    MAX-ACCESS  read-only
    STATUS      current 
    DESCRIPTION
        "RowStatus" 
    ::=  { deployProvVchChannelDefaultsEntry 1 }

deployProvVchChannelDefaultsForceDestroy OBJECT-TYPE
    SYNTAX      FspR7ForcedStatus
    MAX-ACCESS  read-only
    STATUS      current 
    DESCRIPTION
        "Forced Destroy" 
    ::=  { deployProvVchChannelDefaultsEntry 2 }

deployProvVchChannelDefaultsType OBJECT-TYPE
    SYNTAX      FspR7InterfaceType
    MAX-ACCESS  read-only
    STATUS      current 
    DESCRIPTION
        "The TYPE defines the transport service type as wrapper with wrapper layer termination OR else as payload" 
    ::=  { deployProvVchChannelDefaultsEntry 3 }

deployProvVchChannelDefaultsVcgType OBJECT-TYPE
    SYNTAX      SonetVcType
    MAX-ACCESS  read-only
    STATUS      current 
    DESCRIPTION
        "Virtual Container Group Type" 
    ::=  { deployProvVchChannelDefaultsEntry 4 }

deployProvVchChannelDefaultsBundle OBJECT-TYPE
    SYNTAX      SonetVcBundleAllocation
    MAX-ACCESS  read-only
    STATUS      current 
    DESCRIPTION
        "List of VC4/VC3/STS1 containers used in the BUNDLE" 
    ::=  { deployProvVchChannelDefaultsEntry 5 }

deployProvVchChannelDefaultsCir OBJECT-TYPE
    SYNTAX      Unsigned32
    UNITS       "Mbit/s"
    MAX-ACCESS  read-only
    STATUS      current 
    DESCRIPTION
        "CIR (Comitted Information Rate ) is used on Ethernet Interfaces with a policing function" 
    ::=  { deployProvVchChannelDefaultsEntry 6 }

deployProvVchChannelDefaultsAdmin OBJECT-TYPE
    SYNTAX      FspR7AdminState
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvVchChannelDefaultsEntry 7 }

deployProvVchChannelDefaultsSigDegThresOdu OBJECT-TYPE
    SYNTAX      Integer32 (1..100)
    UNITS       "%"
    MAX-ACCESS  read-only
    STATUS      current 
    DESCRIPTION
        "Background-Block-Error-Based Signal Degradation Definition for ODU" 
    ::=  { deployProvVchChannelDefaultsEntry 8 }

deployProvVchChannelDefaultsSigDegPeriodOdu OBJECT-TYPE
    SYNTAX      Unsigned32 (2..10)
    UNITS       "s"
    MAX-ACCESS  read-only
    STATUS      current 
    DESCRIPTION
        "Integration Period for Signal degrade (standard integration period?)" 
    ::=  { deployProvVchChannelDefaultsEntry 9 }

deployProvApsTable OBJECT-TYPE
    SYNTAX      SEQUENCE OF DeployProvApsEntry
    MAX-ACCESS  not-accessible
    STATUS      current 
    DESCRIPTION
        "Contains entries for deployProv of protection groups." 
    ::=  { facilityDeployProv 7 }

deployProvApsEntry OBJECT-TYPE
    SYNTAX      DeployProvApsEntry
    MAX-ACCESS  not-accessible
    STATUS      current 
    DESCRIPTION
        "All protection groups which have been provisioned(or are during provisioning)
         will have an entry in this table." 
    INDEX       { entityIndex } 
    ::=  { deployProvApsTable  1  }

DeployProvApsEntry ::=  SEQUENCE
  { deployProvApsRowStatus RowStatus,
    deployProvApsForceDestroy FspR7ForcedStatus,
    deployProvApsSDswitching EnableState,
    deployProvApsHoldOffTime ApsHoldoffTime,
    deployProvApsProtectionMech ProtectionMech,
    deployProvApsWorkingAid EntityIndex,
    deployProvApsProtectionAid EntityIndex,
    deployProvApsSignalDegradeSwitching EnableState,
    deployProvApsSignalFailureSwitching EnableState,
    deployProvApsFarEndIp IpAddress,
    deployProvApsPeerAid EntityIndex }


  
deployProvApsRowStatus OBJECT-TYPE
    SYNTAX      RowStatus
    MAX-ACCESS  read-write
    STATUS      current 
    DESCRIPTION
        "RowStatus" 
    ::=  { deployProvApsEntry 1 }

deployProvApsForceDestroy OBJECT-TYPE
    SYNTAX      FspR7ForcedStatus
    MAX-ACCESS  read-write
    STATUS      current 
    DESCRIPTION
        "Forced Destroy" 
    ::=  { deployProvApsEntry 2 }

deployProvApsSDswitching OBJECT-TYPE
    SYNTAX      EnableState
    MAX-ACCESS  read-write
    STATUS      current 
    DESCRIPTION
        "This state controls whether the switch criteria for the
         APS group will include the Signal
         Degrade alarm." 
    ::=  { deployProvApsEntry 3 }

deployProvApsHoldOffTime OBJECT-TYPE
    SYNTAX      ApsHoldoffTime
    MAX-ACCESS  read-write
    STATUS      current 
    DESCRIPTION
        "This value controls the switch delay (0 to 10 seconds in
         100ms steps) for the protection group. Changing the hold-off
         time when the timer is active will not affect the active
         timer. The change will take effect the next time the timer
         is active." 
    ::=  { deployProvApsEntry 4 }

deployProvApsProtectionMech OBJECT-TYPE
    SYNTAX      ProtectionMech
    MAX-ACCESS  read-write
    STATUS      current 
    DESCRIPTION
        "The protection type of this protection group." 
    ::=  { deployProvApsEntry 5 }

deployProvApsWorkingAid OBJECT-TYPE
    SYNTAX      EntityIndex
    MAX-ACCESS  read-write
    STATUS      current 
    DESCRIPTION
        "AID of working port involved in the protection group." 
    ::=  { deployProvApsEntry 6 }

deployProvApsProtectionAid OBJECT-TYPE
    SYNTAX      EntityIndex
    MAX-ACCESS  read-write
    STATUS      current 
    DESCRIPTION
        "AID of protection port involved in the protection group." 
    ::=  { deployProvApsEntry 7 }

deployProvApsSignalDegradeSwitching OBJECT-TYPE
    SYNTAX      EnableState
    MAX-ACCESS  read-write
    STATUS      current 
    DESCRIPTION
        "Switch Trigger Additionally on Signal Degrade Link Detection" 
    ::=  { deployProvApsEntry 8 }

deployProvApsSignalFailureSwitching OBJECT-TYPE
    SYNTAX      EnableState
    MAX-ACCESS  read-write
    STATUS      current 
    DESCRIPTION
        "Switch Trigger on Signal Failure Link Detection" 
    ::=  { deployProvApsEntry 9 }

deployProvApsFarEndIp OBJECT-TYPE
    SYNTAX      IpAddress
    MAX-ACCESS  read-write
    STATUS      current 
    DESCRIPTION
        "IP Address assigned to PPP Termination Point on Far-End NE. Default is set by NE System on LINK establishment if FENDIPACPT = Y" 
    ::=  { deployProvApsEntry 10 }

deployProvApsPeerAid OBJECT-TYPE
    SYNTAX      EntityIndex
    MAX-ACCESS  read-write
    STATUS      current 
    DESCRIPTION
        "AID of Protection Partner involved in the protection group." 
    ::=  { deployProvApsEntry 11 }

deployProvApsCapTable OBJECT-TYPE
    SYNTAX      SEQUENCE OF DeployProvApsCapEntry
    MAX-ACCESS  not-accessible
    STATUS      current 
    DESCRIPTION
        "Contains entries for deployProv of protection groups." 
    ::=  { facilityDeployProv 8 }

deployProvApsCapEntry OBJECT-TYPE
    SYNTAX      DeployProvApsCapEntry
    MAX-ACCESS  not-accessible
    STATUS      current 
    DESCRIPTION
        "All protection groups which have been provisioned(or are during provisioning)
         will have an entry in this table." 
    INDEX       { entityIndex } 
    ::=  { deployProvApsCapTable  1  }

DeployProvApsCapEntry ::=  SEQUENCE
  { deployProvApsCapRowStatus FspR7RowStatusCaps,
    deployProvApsCapForceDestroy FspR7ForcedStatusCaps,
    deployProvApsCapSDswitching EnableStateCaps,
    deployProvApsCapHoldOffTime ApsHoldoffTimeCaps,
    deployProvApsCapProtectionMech ProtectionMechCaps,
    deployProvApsCapWorkingAid Integer32,
    deployProvApsCapProtectionAid Integer32,
    deployProvApsCapSignalDegradeSwitching EnableStateCaps,
    deployProvApsCapSignalFailureSwitching EnableStateCaps,
    deployProvApsCapFarEndIp FspR7YesNo,
    deployProvApsCapPeerAid Integer32 }


  
deployProvApsCapRowStatus OBJECT-TYPE
    SYNTAX      FspR7RowStatusCaps
    MAX-ACCESS  read-only
    STATUS      current 
    DESCRIPTION
        "RowStatus" 
    ::=  { deployProvApsCapEntry 1 }

deployProvApsCapForceDestroy OBJECT-TYPE
    SYNTAX      FspR7ForcedStatusCaps
    MAX-ACCESS  read-only
    STATUS      current 
    DESCRIPTION
        "Forced Destroy" 
    ::=  { deployProvApsCapEntry 2 }

deployProvApsCapSDswitching OBJECT-TYPE
    SYNTAX      EnableStateCaps
    MAX-ACCESS  read-only
    STATUS      current 
    DESCRIPTION
        "This state controls whether the switch criteria for the
         APS group will include the Signal
         Degrade alarm." 
    ::=  { deployProvApsCapEntry 3 }

deployProvApsCapHoldOffTime OBJECT-TYPE
    SYNTAX      ApsHoldoffTimeCaps
    MAX-ACCESS  read-only
    STATUS      current 
    DESCRIPTION
        "This value controls the switch delay (0 to 10 seconds in
         100ms steps) for the protection group. Changing the hold-off
         time when the timer is active will not affect the active
         timer. The change will take effect the next time the timer
         is active." 
    ::=  { deployProvApsCapEntry 4 }

deployProvApsCapProtectionMech OBJECT-TYPE
    SYNTAX      ProtectionMechCaps
    MAX-ACCESS  read-only
    STATUS      current 
    DESCRIPTION
        "The protection type of this protection group." 
    ::=  { deployProvApsCapEntry 5 }

deployProvApsCapWorkingAid OBJECT-TYPE
    SYNTAX      Integer32
    MAX-ACCESS  read-only
    STATUS      current 
    DESCRIPTION
        "AID of working port involved in the protection group." 
    ::=  { deployProvApsCapEntry 6 }

deployProvApsCapProtectionAid OBJECT-TYPE
    SYNTAX      Integer32
    MAX-ACCESS  read-only
    STATUS      current 
    DESCRIPTION
        "AID of protection port involved in the protection group." 
    ::=  { deployProvApsCapEntry 7 }

deployProvApsCapSignalDegradeSwitching OBJECT-TYPE
    SYNTAX      EnableStateCaps
    MAX-ACCESS  read-only
    STATUS      current 
    DESCRIPTION
        "Switch Trigger Additionally on Signal Degrade Link Detection" 
    ::=  { deployProvApsCapEntry 8 }

deployProvApsCapSignalFailureSwitching OBJECT-TYPE
    SYNTAX      EnableStateCaps
    MAX-ACCESS  read-only
    STATUS      current 
    DESCRIPTION
        "Switch Trigger on Signal Failure Link Detection" 
    ::=  { deployProvApsCapEntry 9 }

deployProvApsCapFarEndIp OBJECT-TYPE
    SYNTAX      FspR7YesNo
    MAX-ACCESS  read-only
    STATUS      current 
    DESCRIPTION
        "IP Address assigned to PPP Termination Point on Far-End NE. Default is set by NE System on LINK establishment if FENDIPACPT = Y" 
    ::=  { deployProvApsCapEntry 10 }

deployProvApsCapPeerAid OBJECT-TYPE
    SYNTAX      Integer32
    MAX-ACCESS  read-only
    STATUS      current 
    DESCRIPTION
        "AID of Protection Partner involved in the protection group." 
    ::=  { deployProvApsCapEntry 11 }

deployProvApsDefaultsTable OBJECT-TYPE
    SYNTAX      SEQUENCE OF DeployProvApsDefaultsEntry
    MAX-ACCESS  not-accessible
    STATUS      current 
    DESCRIPTION
        "Contains entries for deployProv of protection groups." 
    ::=  { facilityDeployProv 9 }

deployProvApsDefaultsEntry OBJECT-TYPE
    SYNTAX      DeployProvApsDefaultsEntry
    MAX-ACCESS  not-accessible
    STATUS      current 
    DESCRIPTION
        "All protection groups which have been provisioned(or are during provisioning)
         will have an entry in this table." 
    INDEX       { entityIndex } 
    ::=  { deployProvApsDefaultsTable  1  }

DeployProvApsDefaultsEntry ::=  SEQUENCE
  { deployProvApsDefaultsRowStatus RowStatus,
    deployProvApsDefaultsForceDestroy FspR7ForcedStatus,
    deployProvApsDefaultsSDswitching EnableState,
    deployProvApsDefaultsHoldOffTime ApsHoldoffTime,
    deployProvApsDefaultsProtectionMech ProtectionMech,
    deployProvApsDefaultsWorkingAid EntityIndex,
    deployProvApsDefaultsProtectionAid EntityIndex,
    deployProvApsDefaultsSignalDegradeSwitching EnableState,
    deployProvApsDefaultsSignalFailureSwitching EnableState,
    deployProvApsDefaultsFarEndIp IpAddress,
    deployProvApsDefaultsPeerAid EntityIndex }


  
deployProvApsDefaultsRowStatus OBJECT-TYPE
    SYNTAX      RowStatus
    MAX-ACCESS  read-only
    STATUS      current 
    DESCRIPTION
        "RowStatus" 
    ::=  { deployProvApsDefaultsEntry 1 }

deployProvApsDefaultsForceDestroy OBJECT-TYPE
    SYNTAX      FspR7ForcedStatus
    MAX-ACCESS  read-only
    STATUS      current 
    DESCRIPTION
        "Forced Destroy" 
    ::=  { deployProvApsDefaultsEntry 2 }

deployProvApsDefaultsSDswitching OBJECT-TYPE
    SYNTAX      EnableState
    MAX-ACCESS  read-only
    STATUS      current 
    DESCRIPTION
        "This state controls whether the switch criteria for the
         APS group will include the Signal
         Degrade alarm." 
    ::=  { deployProvApsDefaultsEntry 3 }

deployProvApsDefaultsHoldOffTime OBJECT-TYPE
    SYNTAX      ApsHoldoffTime
    MAX-ACCESS  read-only
    STATUS      current 
    DESCRIPTION
        "This value controls the switch delay (0 to 10 seconds in
         100ms steps) for the protection group. Changing the hold-off
         time when the timer is active will not affect the active
         timer. The change will take effect the next time the timer
         is active." 
    ::=  { deployProvApsDefaultsEntry 4 }

deployProvApsDefaultsProtectionMech OBJECT-TYPE
    SYNTAX      ProtectionMech
    MAX-ACCESS  read-only
    STATUS      current 
    DESCRIPTION
        "The protection type of this protection group." 
    ::=  { deployProvApsDefaultsEntry 5 }

deployProvApsDefaultsWorkingAid OBJECT-TYPE
    SYNTAX      EntityIndex
    MAX-ACCESS  read-only
    STATUS      current 
    DESCRIPTION
        "AID of working port involved in the protection group." 
    ::=  { deployProvApsDefaultsEntry 6 }

deployProvApsDefaultsProtectionAid OBJECT-TYPE
    SYNTAX      EntityIndex
    MAX-ACCESS  read-only
    STATUS      current 
    DESCRIPTION
        "AID of protection port involved in the protection group." 
    ::=  { deployProvApsDefaultsEntry 7 }

deployProvApsDefaultsSignalDegradeSwitching OBJECT-TYPE
    SYNTAX      EnableState
    MAX-ACCESS  read-only
    STATUS      current 
    DESCRIPTION
        "Switch Trigger Additionally on Signal Degrade Link Detection" 
    ::=  { deployProvApsDefaultsEntry 8 }

deployProvApsDefaultsSignalFailureSwitching OBJECT-TYPE
    SYNTAX      EnableState
    MAX-ACCESS  read-only
    STATUS      current 
    DESCRIPTION
        "Switch Trigger on Signal Failure Link Detection" 
    ::=  { deployProvApsDefaultsEntry 9 }

deployProvApsDefaultsFarEndIp OBJECT-TYPE
    SYNTAX      IpAddress
    MAX-ACCESS  read-only
    STATUS      current 
    DESCRIPTION
        "IP Address assigned to PPP Termination Point on Far-End NE. Default is set by NE System on LINK establishment if FENDIPACPT = Y" 
    ::=  { deployProvApsDefaultsEntry 10 }

deployProvApsDefaultsPeerAid OBJECT-TYPE
    SYNTAX      EntityIndex
    MAX-ACCESS  read-only
    STATUS      current 
    DESCRIPTION
        "AID of Protection Partner involved in the protection group." 
    ::=  { deployProvApsDefaultsEntry 11 }

deployProvApsWorkingAidCapsTable OBJECT-TYPE
    SYNTAX      SEQUENCE OF DeployProvApsWorkingAidCapsEntry
    MAX-ACCESS  not-accessible
    STATUS      current 
    DESCRIPTION
        "" 
    ::=  { facilityDeployProv 10 }

deployProvApsWorkingAidCapsEntry OBJECT-TYPE
    SYNTAX      DeployProvApsWorkingAidCapsEntry
    MAX-ACCESS  not-accessible
    STATUS      current 
    DESCRIPTION
        "" 
    INDEX       { entityIndex,deployProvApsWorkingAidCapsIndex } 
    ::=  { deployProvApsWorkingAidCapsTable  1  }

DeployProvApsWorkingAidCapsEntry ::=  SEQUENCE
  { deployProvApsWorkingAidCapsIndex EntityIndex }


  
deployProvApsWorkingAidCapsIndex OBJECT-TYPE
    SYNTAX      EntityIndex
    MAX-ACCESS  read-only
    STATUS      current 
    DESCRIPTION
        "AID of working port involved in the protection group." 
    ::=  { deployProvApsWorkingAidCapsEntry 1 }

deployProvApsProtectingAidCapsTable OBJECT-TYPE
    SYNTAX      SEQUENCE OF DeployProvApsProtectingAidCapsEntry
    MAX-ACCESS  not-accessible
    STATUS      current 
    DESCRIPTION
        "" 
    ::=  { facilityDeployProv 11 }

deployProvApsProtectingAidCapsEntry OBJECT-TYPE
    SYNTAX      DeployProvApsProtectingAidCapsEntry
    MAX-ACCESS  not-accessible
    STATUS      current 
    DESCRIPTION
        "" 
    INDEX       { entityIndex,deployProvApsProtectingAidCapsIndex } 
    ::=  { deployProvApsProtectingAidCapsTable  1  }

DeployProvApsProtectingAidCapsEntry ::=  SEQUENCE
  { deployProvApsProtectingAidCapsIndex EntityIndex }


  
deployProvApsProtectingAidCapsIndex OBJECT-TYPE
    SYNTAX      EntityIndex
    MAX-ACCESS  read-only
    STATUS      current 
    DESCRIPTION
        "AID of protection port involved in the protection group." 
    ::=  { deployProvApsProtectingAidCapsEntry 1 }

deployProvDcnTable OBJECT-TYPE
    SYNTAX      SEQUENCE OF DeployProvDcnEntry
    MAX-ACCESS  not-accessible
    STATUS      current 
    DESCRIPTION
        "
         Contains entries for provisioning dcnChannel.
        " 
    ::=  { facilityDeployProv 12 }

deployProvDcnEntry OBJECT-TYPE
    SYNTAX      DeployProvDcnEntry
    MAX-ACCESS  not-accessible
    STATUS      current 
    DESCRIPTION
        "
         All dcnChannel which are provisioned(or are during provisioning) will have an entry
         in this table.
        " 
    INDEX       { entityIndex } 
    ::=  { deployProvDcnTable  1  }

DeployProvDcnEntry ::=  SEQUENCE
  { deployProvDcnRowStatus RowStatus,
    deployProvDcnForceDestroy FspR7ForcedStatus,
    deployProvDcnType FspR7InterfaceType,
    deployProvDcnAdmin FspR7AdminState }


  
deployProvDcnRowStatus OBJECT-TYPE
    SYNTAX      RowStatus
    MAX-ACCESS  read-write
    STATUS      current 
    DESCRIPTION
        "RowStatus" 
    ::=  { deployProvDcnEntry 1 }

deployProvDcnForceDestroy OBJECT-TYPE
    SYNTAX      FspR7ForcedStatus
    MAX-ACCESS  read-write
    STATUS      current 
    DESCRIPTION
        "Forced Destroy" 
    ::=  { deployProvDcnEntry 2 }

deployProvDcnType OBJECT-TYPE
    SYNTAX      FspR7InterfaceType
    MAX-ACCESS  read-write
    STATUS      current 
    DESCRIPTION
        "The TYPE defines the transport service type as wrapper with wrapper layer termination OR else as payload" 
    ::=  { deployProvDcnEntry 3 }

deployProvDcnAdmin OBJECT-TYPE
    SYNTAX      FspR7AdminState
    MAX-ACCESS  read-write
    STATUS      current 
    DESCRIPTION
        "The Adminstrative State will be displayed in the GUI with full
         name values; it will be differently displayed in TL1 syntax according
         to TL1 display rules. The transaction into the UAS state requires
         a special destroy/delete function." 
    ::=  { deployProvDcnEntry 4 }

deployProvDcnCapTable OBJECT-TYPE
    SYNTAX      SEQUENCE OF DeployProvDcnCapEntry
    MAX-ACCESS  not-accessible
    STATUS      current 
    DESCRIPTION
        "
         Contains entries for provisioning dcnChannel.
        " 
    ::=  { facilityDeployProv 13 }

deployProvDcnCapEntry OBJECT-TYPE
    SYNTAX      DeployProvDcnCapEntry
    MAX-ACCESS  not-accessible
    STATUS      current 
    DESCRIPTION
        "
         All dcnChannel which are provisioned(or are during provisioning) will have an entry
         in this table.
        " 
    INDEX       { entityIndex } 
    ::=  { deployProvDcnCapTable  1  }

DeployProvDcnCapEntry ::=  SEQUENCE
  { deployProvDcnCapRowStatus FspR7RowStatusCaps,
    deployProvDcnCapForceDestroy FspR7ForcedStatusCaps,
    deployProvDcnCapType FspR7InterfaceTypeCaps,
    deployProvDcnCapAdmin FspR7AdminStateCaps }


  
deployProvDcnCapRowStatus OBJECT-TYPE
    SYNTAX      FspR7RowStatusCaps
    MAX-ACCESS  read-only
    STATUS      current 
    DESCRIPTION
        "RowStatus" 
    ::=  { deployProvDcnCapEntry 1 }

deployProvDcnCapForceDestroy OBJECT-TYPE
    SYNTAX      FspR7ForcedStatusCaps
    MAX-ACCESS  read-only
    STATUS      current 
    DESCRIPTION
        "Forced Destroy" 
    ::=  { deployProvDcnCapEntry 2 }

deployProvDcnCapType OBJECT-TYPE
    SYNTAX      FspR7InterfaceTypeCaps
    MAX-ACCESS  read-only
    STATUS      current 
    DESCRIPTION
        "The TYPE defines the transport service type as wrapper with wrapper layer termination OR else as payload" 
    ::=  { deployProvDcnCapEntry 3 }

deployProvDcnCapAdmin OBJECT-TYPE
    SYNTAX      FspR7AdminStateCaps
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvDcnCapEntry 4 }

deployProvDcnDefaultsTable OBJECT-TYPE
    SYNTAX      SEQUENCE OF DeployProvDcnDefaultsEntry
    MAX-ACCESS  not-accessible
    STATUS      current 
    DESCRIPTION
        "
         Contains entries for provisioning dcnChannel.
        " 
    ::=  { facilityDeployProv 14 }

deployProvDcnDefaultsEntry OBJECT-TYPE
    SYNTAX      DeployProvDcnDefaultsEntry
    MAX-ACCESS  not-accessible
    STATUS      current 
    DESCRIPTION
        "
         All dcnChannel which are provisioned(or are during provisioning) will have an entry
         in this table.
        " 
    INDEX       { entityIndex } 
    ::=  { deployProvDcnDefaultsTable  1  }

DeployProvDcnDefaultsEntry ::=  SEQUENCE
  { deployProvDcnDefaultsRowStatus RowStatus,
    deployProvDcnDefaultsForceDestroy FspR7ForcedStatus,
    deployProvDcnDefaultsType FspR7InterfaceType,
    deployProvDcnDefaultsAdmin FspR7AdminState }


  
deployProvDcnDefaultsRowStatus OBJECT-TYPE
    SYNTAX      RowStatus
    MAX-ACCESS  read-only
    STATUS      current 
    DESCRIPTION
        "RowStatus" 
    ::=  { deployProvDcnDefaultsEntry 1 }

deployProvDcnDefaultsForceDestroy OBJECT-TYPE
    SYNTAX      FspR7ForcedStatus
    MAX-ACCESS  read-only
    STATUS      current 
    DESCRIPTION
        "Forced Destroy" 
    ::=  { deployProvDcnDefaultsEntry 2 }

deployProvDcnDefaultsType OBJECT-TYPE
    SYNTAX      FspR7InterfaceType
    MAX-ACCESS  read-only
    STATUS      current 
    DESCRIPTION
        "The TYPE defines the transport service type as wrapper with wrapper layer termination OR else as payload" 
    ::=  { deployProvDcnDefaultsEntry 3 }

deployProvDcnDefaultsAdmin OBJECT-TYPE
    SYNTAX      FspR7AdminState
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvDcnDefaultsEntry 4 }

deployProvPppIpTable OBJECT-TYPE
    SYNTAX      SEQUENCE OF DeployProvPppIpEntry
    MAX-ACCESS  not-accessible
    STATUS      current 
    DESCRIPTION
        "
         Contains entries for provisioning PppIp.
        " 
    ::=  { facilityDeployProv 15 }

deployProvPppIpEntry OBJECT-TYPE
    SYNTAX      DeployProvPppIpEntry
    MAX-ACCESS  not-accessible
    STATUS      current 
    DESCRIPTION
        "
         All PppIp which are provisioned(or are during provisioning) will have an entry
         in this table.
        " 
    INDEX       { entityIndex } 
    ::=  { deployProvPppIpTable  1  }

DeployProvPppIpEntry ::=  SEQUENCE
  { deployProvPppIpRowStatus RowStatus,
    deployProvPppIpForceDestroy FspR7ForcedStatus,
    deployProvPppIpType FspR7InterfaceType,
    deployProvPppIpNearEndIp IpAddress,
    deployProvPppIpFarEndIp IpAddress,
    deployProvPppIpBitrate Unsigned32,
    deployProvPppIpOspf EnableState,
    deployProvPppIpMetric Unsigned32,
    deployProvPppIpDefaultGateway FspR7NoYes,
    deployProvPppIpProxyArp FspR7NoYes,
    deployProvPppIpAdmin FspR7AdminState,
    deployProvPppIpAreaId IpAddress,
    deployProvPppIpBaud FspR7Baund,
    deployProvPppIpFlowControl FspR7FlowControlMode }


  
deployProvPppIpRowStatus OBJECT-TYPE
    SYNTAX      RowStatus
    MAX-ACCESS  read-write
    STATUS      current 
    DESCRIPTION
        "RowStatus" 
    ::=  { deployProvPppIpEntry 1 }

deployProvPppIpForceDestroy OBJECT-TYPE
    SYNTAX      FspR7ForcedStatus
    MAX-ACCESS  read-write
    STATUS      current 
    DESCRIPTION
        "Forced Destroy" 
    ::=  { deployProvPppIpEntry 2 }

deployProvPppIpType OBJECT-TYPE
    SYNTAX      FspR7InterfaceType
    MAX-ACCESS  read-write
    STATUS      current 
    DESCRIPTION
        "The TYPE defines the transport service type as wrapper with wrapper layer termination OR else as payload" 
    ::=  { deployProvPppIpEntry 3 }

deployProvPppIpNearEndIp OBJECT-TYPE
    SYNTAX      IpAddress
    MAX-ACCESS  read-write
    STATUS      current 
    DESCRIPTION
        "IP Address assigned to PPP Termination Point on Near-End NE. Defaults to System IP address" 
    ::=  { deployProvPppIpEntry 4 }

deployProvPppIpFarEndIp OBJECT-TYPE
    SYNTAX      IpAddress
    MAX-ACCESS  read-write
    STATUS      current 
    DESCRIPTION
        "IP Address assigned to PPP Termination Point on Far-End NE. Default is set by NE System on LINK establishment if FENDIPACPT = Y" 
    ::=  { deployProvPppIpEntry 5 }

deployProvPppIpBitrate OBJECT-TYPE
    SYNTAX      Unsigned32 (1..1312)
    UNITS       "Kbit/s"
    MAX-ACCESS  read-write
    STATUS      current 
    DESCRIPTION
        "Provisioned max. bitrate of transmitter in PPP Link established over ECC" 
    ::=  { deployProvPppIpEntry 6 }

deployProvPppIpOspf OBJECT-TYPE
    SYNTAX      EnableState
    MAX-ACCESS  read-write
    STATUS      current 
    DESCRIPTION
        "OSPF Routing (Dynamic)" 
    ::=  { deployProvPppIpEntry 7 }

deployProvPppIpMetric OBJECT-TYPE
    SYNTAX      Unsigned32 (0..65535)
    MAX-ACCESS  read-write
    STATUS      current 
    DESCRIPTION
        "Routing Metric" 
    ::=  { deployProvPppIpEntry 8 }

deployProvPppIpDefaultGateway OBJECT-TYPE
    SYNTAX      FspR7NoYes
    MAX-ACCESS  read-write
    STATUS      current 
    DESCRIPTION
        "If Y then a default router entry with thid PPPIP as gateway will be set in the routing table if no default router is present yet. It can be enabled on multiple PPPIP instances. But this were an unlogical configuration." 
    ::=  { deployProvPppIpEntry 9 }

deployProvPppIpProxyArp OBJECT-TYPE
    SYNTAX      FspR7NoYes
    MAX-ACCESS  read-write
    STATUS      current 
    DESCRIPTION
        "If enabled then ARP requests for FENDIP (coming in on another interface in the same subnet as FENDIP) will be replied too." 
    ::=  { deployProvPppIpEntry 10 }

deployProvPppIpAdmin OBJECT-TYPE
    SYNTAX      FspR7AdminState
    MAX-ACCESS  read-write
    STATUS      current 
    DESCRIPTION
        "The Adminstrative State will be displayed in the GUI with full
         name values; it will be differently displayed in TL1 syntax according
         to TL1 display rules. The transaction into the UAS state requires
         a special destroy/delete function." 
    ::=  { deployProvPppIpEntry 11 }

deployProvPppIpAreaId OBJECT-TYPE
    SYNTAX      IpAddress
    MAX-ACCESS  read-write
    STATUS      current 
    DESCRIPTION
        "OSPF Area ID for IP Interface" 
    ::=  { deployProvPppIpEntry 12 }

deployProvPppIpBaud OBJECT-TYPE
    SYNTAX      FspR7Baund
    MAX-ACCESS  read-write
    STATUS      current 
    DESCRIPTION
        "Baud rate of the serial interface" 
    ::=  { deployProvPppIpEntry 13 }

deployProvPppIpFlowControl OBJECT-TYPE
    SYNTAX      FspR7FlowControlMode
    MAX-ACCESS  read-write
    STATUS      current 
    DESCRIPTION
        "Flow Control mechanism" 
    ::=  { deployProvPppIpEntry 14 }

deployProvPppIpCapTable OBJECT-TYPE
    SYNTAX      SEQUENCE OF DeployProvPppIpCapEntry
    MAX-ACCESS  not-accessible
    STATUS      current 
    DESCRIPTION
        "
         Contains entries for provisioning PppIp.
        " 
    ::=  { facilityDeployProv 16 }

deployProvPppIpCapEntry OBJECT-TYPE
    SYNTAX      DeployProvPppIpCapEntry
    MAX-ACCESS  not-accessible
    STATUS      current 
    DESCRIPTION
        "
         All PppIp which are provisioned(or are during provisioning) will have an entry
         in this table.
        " 
    INDEX       { entityIndex } 
    ::=  { deployProvPppIpCapTable  1  }

DeployProvPppIpCapEntry ::=  SEQUENCE
  { deployProvPppIpCapRowStatus FspR7RowStatusCaps,
    deployProvPppIpCapForceDestroy FspR7ForcedStatusCaps,
    deployProvPppIpCapType FspR7InterfaceTypeCaps,
    deployProvPppIpCapNearEndIp FspR7YesNo,
    deployProvPppIpCapFarEndIp FspR7YesNo,
    deployProvPppIpCapBitrate FspR7Unsigned32Caps,
    deployProvPppIpCapOspf EnableStateCaps,
    deployProvPppIpCapMetric FspR7Unsigned32Caps,
    deployProvPppIpCapDefaultGateway FspR7NoYesCaps,
    deployProvPppIpCapProxyArp FspR7NoYesCaps,
    deployProvPppIpCapAdmin FspR7AdminStateCaps,
    deployProvPppIpCapAreaId FspR7YesNo,
    deployProvPppIpCapBaud FspR7BaundCaps,
    deployProvPppIpCapFlowControl FspR7FlowControlModeCaps }


  
deployProvPppIpCapRowStatus OBJECT-TYPE
    SYNTAX      FspR7RowStatusCaps
    MAX-ACCESS  read-only
    STATUS      current 
    DESCRIPTION
        "RowStatus" 
    ::=  { deployProvPppIpCapEntry 1 }

deployProvPppIpCapForceDestroy OBJECT-TYPE
    SYNTAX      FspR7ForcedStatusCaps
    MAX-ACCESS  read-only
    STATUS      current 
    DESCRIPTION
        "Forced Destroy" 
    ::=  { deployProvPppIpCapEntry 2 }

deployProvPppIpCapType OBJECT-TYPE
    SYNTAX      FspR7InterfaceTypeCaps
    MAX-ACCESS  read-only
    STATUS      current 
    DESCRIPTION
        "The TYPE defines the transport service type as wrapper with wrapper layer termination OR else as payload" 
    ::=  { deployProvPppIpCapEntry 3 }

deployProvPppIpCapNearEndIp OBJECT-TYPE
    SYNTAX      FspR7YesNo
    MAX-ACCESS  read-only
    STATUS      current 
    DESCRIPTION
        "IP Address assigned to PPP Termination Point on Near-End NE. Defaults to System IP address" 
    ::=  { deployProvPppIpCapEntry 4 }

deployProvPppIpCapFarEndIp OBJECT-TYPE
    SYNTAX      FspR7YesNo
    MAX-ACCESS  read-only
    STATUS      current 
    DESCRIPTION
        "IP Address assigned to PPP Termination Point on Far-End NE. Default is set by NE System on LINK establishment if FENDIPACPT = Y" 
    ::=  { deployProvPppIpCapEntry 5 }

deployProvPppIpCapBitrate OBJECT-TYPE
    SYNTAX      FspR7Unsigned32Caps
    UNITS       "Kbit/s"
    MAX-ACCESS  read-only
    STATUS      current 
    DESCRIPTION
        "Provisioned max. bitrate of transmitter in PPP Link established over ECC" 
    ::=  { deployProvPppIpCapEntry 6 }

deployProvPppIpCapOspf OBJECT-TYPE
    SYNTAX      EnableStateCaps
    MAX-ACCESS  read-only
    STATUS      current 
    DESCRIPTION
        "OSPF Routing (Dynamic)" 
    ::=  { deployProvPppIpCapEntry 7 }

deployProvPppIpCapMetric OBJECT-TYPE
    SYNTAX      FspR7Unsigned32Caps
    MAX-ACCESS  read-only
    STATUS      current 
    DESCRIPTION
        "Routing Metric" 
    ::=  { deployProvPppIpCapEntry 8 }

deployProvPppIpCapDefaultGateway OBJECT-TYPE
    SYNTAX      FspR7NoYesCaps
    MAX-ACCESS  read-only
    STATUS      current 
    DESCRIPTION
        "If Y then a default router entry with thid PPPIP as gateway will be set in the routing table if no default router is present yet. It can be enabled on multiple PPPIP instances. But this were an unlogical configuration." 
    ::=  { deployProvPppIpCapEntry 9 }

deployProvPppIpCapProxyArp OBJECT-TYPE
    SYNTAX      FspR7NoYesCaps
    MAX-ACCESS  read-only
    STATUS      current 
    DESCRIPTION
        "If enabled then ARP requests for FENDIP (coming in on another interface in the same subnet as FENDIP) will be replied too." 
    ::=  { deployProvPppIpCapEntry 10 }

deployProvPppIpCapAdmin OBJECT-TYPE
    SYNTAX      FspR7AdminStateCaps
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvPppIpCapEntry 11 }

deployProvPppIpCapAreaId OBJECT-TYPE
    SYNTAX      FspR7YesNo
    MAX-ACCESS  read-only
    STATUS      current 
    DESCRIPTION
        "OSPF Area ID for IP Interface" 
    ::=  { deployProvPppIpCapEntry 12 }

deployProvPppIpCapBaud OBJECT-TYPE
    SYNTAX      FspR7BaundCaps
    MAX-ACCESS  read-only
    STATUS      current 
    DESCRIPTION
        "Baud rate of the serial interface" 
    ::=  { deployProvPppIpCapEntry 13 }

deployProvPppIpCapFlowControl OBJECT-TYPE
    SYNTAX      FspR7FlowControlModeCaps
    MAX-ACCESS  read-only
    STATUS      current 
    DESCRIPTION
        "Flow Control mechanism" 
    ::=  { deployProvPppIpCapEntry 14 }

deployProvPppIpDefaultsTable OBJECT-TYPE
    SYNTAX      SEQUENCE OF DeployProvPppIpDefaultsEntry
    MAX-ACCESS  not-accessible
    STATUS      current 
    DESCRIPTION
        "
         Contains entries for provisioning PppIp.
        " 
    ::=  { facilityDeployProv 17 }

deployProvPppIpDefaultsEntry OBJECT-TYPE
    SYNTAX      DeployProvPppIpDefaultsEntry
    MAX-ACCESS  not-accessible
    STATUS      current 
    DESCRIPTION
        "
         All PppIp which are provisioned(or are during provisioning) will have an entry
         in this table.
        " 
    INDEX       { entityIndex } 
    ::=  { deployProvPppIpDefaultsTable  1  }

DeployProvPppIpDefaultsEntry ::=  SEQUENCE
  { deployProvPppIpDefaultsRowStatus RowStatus,
    deployProvPppIpDefaultsForceDestroy FspR7ForcedStatus,
    deployProvPppIpDefaultsType FspR7InterfaceType,
    deployProvPppIpDefaultsNearEndIp IpAddress,
    deployProvPppIpDefaultsFarEndIp IpAddress,
    deployProvPppIpDefaultsBitrate Unsigned32,
    deployProvPppIpDefaultsOspf EnableState,
    deployProvPppIpDefaultsMetric Unsigned32,
    deployProvPppIpDefaultsDefaultGateway FspR7NoYes,
    deployProvPppIpDefaultsProxyArp FspR7NoYes,
    deployProvPppIpDefaultsAdmin FspR7AdminState,
    deployProvPppIpDefaultsAreaId IpAddress,
    deployProvPppIpDefaultsBaud FspR7Baund,
    deployProvPppIpDefaultsFlowControl FspR7FlowControlMode }


  
deployProvPppIpDefaultsRowStatus OBJECT-TYPE
    SYNTAX      RowStatus
    MAX-ACCESS  read-only
    STATUS      current 
    DESCRIPTION
        "RowStatus" 
    ::=  { deployProvPppIpDefaultsEntry 1 }

deployProvPppIpDefaultsForceDestroy OBJECT-TYPE
    SYNTAX      FspR7ForcedStatus
    MAX-ACCESS  read-only
    STATUS      current 
    DESCRIPTION
        "Forced Destroy" 
    ::=  { deployProvPppIpDefaultsEntry 2 }

deployProvPppIpDefaultsType OBJECT-TYPE
    SYNTAX      FspR7InterfaceType
    MAX-ACCESS  read-only
    STATUS      current 
    DESCRIPTION
        "The TYPE defines the transport service type as wrapper with wrapper layer termination OR else as payload" 
    ::=  { deployProvPppIpDefaultsEntry 3 }

deployProvPppIpDefaultsNearEndIp OBJECT-TYPE
    SYNTAX      IpAddress
    MAX-ACCESS  read-only
    STATUS      current 
    DESCRIPTION
        "IP Address assigned to PPP Termination Point on Near-End NE. Defaults to System IP address" 
    ::=  { deployProvPppIpDefaultsEntry 4 }

deployProvPppIpDefaultsFarEndIp OBJECT-TYPE
    SYNTAX      IpAddress
    MAX-ACCESS  read-only
    STATUS      current 
    DESCRIPTION
        "IP Address assigned to PPP Termination Point on Far-End NE. Default is set by NE System on LINK establishment if FENDIPACPT = Y" 
    ::=  { deployProvPppIpDefaultsEntry 5 }

deployProvPppIpDefaultsBitrate OBJECT-TYPE
    SYNTAX      Unsigned32 (1..1312)
    UNITS       "Kbit/s"
    MAX-ACCESS  read-only
    STATUS      current 
    DESCRIPTION
        "Provisioned max. bitrate of transmitter in PPP Link established over ECC" 
    ::=  { deployProvPppIpDefaultsEntry 6 }

deployProvPppIpDefaultsOspf OBJECT-TYPE
    SYNTAX      EnableState
    MAX-ACCESS  read-only
    STATUS      current 
    DESCRIPTION
        "OSPF Routing (Dynamic)" 
    ::=  { deployProvPppIpDefaultsEntry 7 }

deployProvPppIpDefaultsMetric OBJECT-TYPE
    SYNTAX      Unsigned32 (0..65535)
    MAX-ACCESS  read-only
    STATUS      current 
    DESCRIPTION
        "Routing Metric" 
    ::=  { deployProvPppIpDefaultsEntry 8 }

deployProvPppIpDefaultsDefaultGateway OBJECT-TYPE
    SYNTAX      FspR7NoYes
    MAX-ACCESS  read-only
    STATUS      current 
    DESCRIPTION
        "If Y then a default router entry with thid PPPIP as gateway will be set in the routing table if no default router is present yet. It can be enabled on multiple PPPIP instances. But this were an unlogical configuration." 
    ::=  { deployProvPppIpDefaultsEntry 9 }

deployProvPppIpDefaultsProxyArp OBJECT-TYPE
    SYNTAX      FspR7NoYes
    MAX-ACCESS  read-only
    STATUS      current 
    DESCRIPTION
        "If enabled then ARP requests for FENDIP (coming in on another interface in the same subnet as FENDIP) will be replied too." 
    ::=  { deployProvPppIpDefaultsEntry 10 }

deployProvPppIpDefaultsAdmin OBJECT-TYPE
    SYNTAX      FspR7AdminState
    MAX-ACCESS  read-only
    STATUS      current 
    DESCRIPTION
        "The Adminstrative State will be displayed in the GUI with full
         name values; it will be differently displayed in TL1 syntax according
         to TL1 display rules. The transaction into the UAS state requires
         a special destroy/delete function." 
    ::=  { deployProvPppIpDefaultsEntry 11 }

deployProvPppIpDefaultsAreaId OBJECT-TYPE
    SYNTAX      IpAddress
    MAX-ACCESS  read-only
    STATUS      current 
    DESCRIPTION
        "OSPF Area ID for IP Interface" 
    ::=  { deployProvPppIpDefaultsEntry 12 }

deployProvPppIpDefaultsBaud OBJECT-TYPE
    SYNTAX      FspR7Baund
    MAX-ACCESS  read-only
    STATUS      current 
    DESCRIPTION
        "Baud rate of the serial interface" 
    ::=  { deployProvPppIpDefaultsEntry 13 }

deployProvPppIpDefaultsFlowControl OBJECT-TYPE
    SYNTAX      FspR7FlowControlMode
    MAX-ACCESS  read-only
    STATUS      current 
    DESCRIPTION
        "Flow Control mechanism" 
    ::=  { deployProvPppIpDefaultsEntry 14 }

deployProvCrsDcnTable OBJECT-TYPE
    SYNTAX      SEQUENCE OF DeployProvCrsDcnEntry
    MAX-ACCESS  not-accessible
    STATUS      current 
    DESCRIPTION
        "
         Contains entries for provisioning CrsDcn.
        " 
    ::=  { facilityDeployProv 18 }

deployProvCrsDcnEntry OBJECT-TYPE
    SYNTAX      DeployProvCrsDcnEntry
    MAX-ACCESS  not-accessible
    STATUS      current 
    DESCRIPTION
        "
         All CrsDcn which are provisioned(or are during provisioning) will have an entry
         in this table.
        " 
    INDEX       { entityIndex } 
    ::=  { deployProvCrsDcnTable  1  }

DeployProvCrsDcnEntry ::=  SEQUENCE
  { deployProvCrsDcnRowStatus RowStatus,
    deployProvCrsDcnForceDestroy FspR7ForcedStatus,
    deployProvCrsDcnType FspR7TypeConnection,
    deployProvCrsDcnLink EntityIndex,
    deployProvCrsDcnEcc EntityIndex }


  
deployProvCrsDcnRowStatus OBJECT-TYPE
    SYNTAX      RowStatus
    MAX-ACCESS  read-write
    STATUS      current 
    DESCRIPTION
        "RowStatus" 
    ::=  { deployProvCrsDcnEntry 1 }

deployProvCrsDcnForceDestroy OBJECT-TYPE
    SYNTAX      FspR7ForcedStatus
    MAX-ACCESS  read-write
    STATUS      current 
    DESCRIPTION
        "Forced Destroy" 
    ::=  { deployProvCrsDcnEntry 2 }

deployProvCrsDcnType OBJECT-TYPE
    SYNTAX      FspR7TypeConnection
    MAX-ACCESS  read-write
    STATUS      current 
    DESCRIPTION
        "Type of Cross-Connect" 
    ::=  { deployProvCrsDcnEntry 3 }

deployProvCrsDcnLink OBJECT-TYPE
    SYNTAX      EntityIndex
    MAX-ACCESS  read-write
    STATUS      current 
    DESCRIPTION
        "Address Identifier of PPPIP LINK Entity." 
    ::=  { deployProvCrsDcnEntry 4 }

deployProvCrsDcnEcc OBJECT-TYPE
    SYNTAX      EntityIndex
    MAX-ACCESS  read-write
    STATUS      current 
    DESCRIPTION
        "Address Identifier of ECC Entity." 
    ::=  { deployProvCrsDcnEntry 5 }

deployProvCrsDcnCapTable OBJECT-TYPE
    SYNTAX      SEQUENCE OF DeployProvCrsDcnCapEntry
    MAX-ACCESS  not-accessible
    STATUS      current 
    DESCRIPTION
        "
         Contains entries for provisioning CrsDcn.
        " 
    ::=  { facilityDeployProv 19 }

deployProvCrsDcnCapEntry OBJECT-TYPE
    SYNTAX      DeployProvCrsDcnCapEntry
    MAX-ACCESS  not-accessible
    STATUS      current 
    DESCRIPTION
        "
         All CrsDcn which are provisioned(or are during provisioning) will have an entry
         in this table.
        " 
    INDEX       { entityIndex } 
    ::=  { deployProvCrsDcnCapTable  1  }

DeployProvCrsDcnCapEntry ::=  SEQUENCE
  { deployProvCrsDcnCapRowStatus FspR7RowStatusCaps,
    deployProvCrsDcnCapForceDestroy FspR7ForcedStatusCaps,
    deployProvCrsDcnCapType FspR7TypeConnectionCaps,
    deployProvCrsDcnCapLink Integer32,
    deployProvCrsDcnCapEcc Integer32 }


  
deployProvCrsDcnCapRowStatus OBJECT-TYPE
    SYNTAX      FspR7RowStatusCaps
    MAX-ACCESS  read-only
    STATUS      current 
    DESCRIPTION
        "RowStatus" 
    ::=  { deployProvCrsDcnCapEntry 1 }

deployProvCrsDcnCapForceDestroy OBJECT-TYPE
    SYNTAX      FspR7ForcedStatusCaps
    MAX-ACCESS  read-only
    STATUS      current 
    DESCRIPTION
        "Forced Destroy" 
    ::=  { deployProvCrsDcnCapEntry 2 }

deployProvCrsDcnCapType OBJECT-TYPE
    SYNTAX      FspR7TypeConnectionCaps
    MAX-ACCESS  read-only
    STATUS      current 
    DESCRIPTION
        "Type of Cross-Connect" 
    ::=  { deployProvCrsDcnCapEntry 3 }

deployProvCrsDcnCapLink OBJECT-TYPE
    SYNTAX      Integer32
    MAX-ACCESS  read-only
    STATUS      current 
    DESCRIPTION
        "Address Identifier of PPPIP LINK Entity." 
    ::=  { deployProvCrsDcnCapEntry 4 }

deployProvCrsDcnCapEcc OBJECT-TYPE
    SYNTAX      Integer32
    MAX-ACCESS  read-only
    STATUS      current 
    DESCRIPTION
        "Address Identifier of ECC Entity." 
    ::=  { deployProvCrsDcnCapEntry 5 }

deployProvCrsDcnDefaultsTable OBJECT-TYPE
    SYNTAX      SEQUENCE OF DeployProvCrsDcnDefaultsEntry
    MAX-ACCESS  not-accessible
    STATUS      current 
    DESCRIPTION
        "
         Contains entries for provisioning CrsDcn.
        " 
    ::=  { facilityDeployProv 20 }

deployProvCrsDcnDefaultsEntry OBJECT-TYPE
    SYNTAX      DeployProvCrsDcnDefaultsEntry
    MAX-ACCESS  not-accessible
    STATUS      current 
    DESCRIPTION
        "
         All CrsDcn which are provisioned(or are during provisioning) will have an entry
         in this table.
        " 
    INDEX       { entityIndex } 
    ::=  { deployProvCrsDcnDefaultsTable  1  }

DeployProvCrsDcnDefaultsEntry ::=  SEQUENCE
  { deployProvCrsDcnDefaultsRowStatus RowStatus,
    deployProvCrsDcnDefaultsForceDestroy FspR7ForcedStatus,
    deployProvCrsDcnDefaultsType FspR7TypeConnection,
    deployProvCrsDcnDefaultsLink EntityIndex,
    deployProvCrsDcnDefaultsEcc EntityIndex }


  
deployProvCrsDcnDefaultsRowStatus OBJECT-TYPE
    SYNTAX      RowStatus
    MAX-ACCESS  read-only
    STATUS      current 
    DESCRIPTION
        "RowStatus" 
    ::=  { deployProvCrsDcnDefaultsEntry 1 }

deployProvCrsDcnDefaultsForceDestroy OBJECT-TYPE
    SYNTAX      FspR7ForcedStatus
    MAX-ACCESS  read-only
    STATUS      current 
    DESCRIPTION
        "Forced Destroy" 
    ::=  { deployProvCrsDcnDefaultsEntry 2 }

deployProvCrsDcnDefaultsType OBJECT-TYPE
    SYNTAX      FspR7TypeConnection
    MAX-ACCESS  read-only
    STATUS      current 
    DESCRIPTION
        "Type of Cross-Connect" 
    ::=  { deployProvCrsDcnDefaultsEntry 3 }

deployProvCrsDcnDefaultsLink OBJECT-TYPE
    SYNTAX      EntityIndex
    MAX-ACCESS  read-only
    STATUS      current 
    DESCRIPTION
        "Address Identifier of PPPIP LINK Entity." 
    ::=  { deployProvCrsDcnDefaultsEntry 4 }

deployProvCrsDcnDefaultsEcc OBJECT-TYPE
    SYNTAX      EntityIndex
    MAX-ACCESS  read-only
    STATUS      current 
    DESCRIPTION
        "Address Identifier of ECC Entity." 
    ::=  { deployProvCrsDcnDefaultsEntry 5 }

deployProvCrsDcnLinkAidCapsTable OBJECT-TYPE
    SYNTAX      SEQUENCE OF DeployProvCrsDcnLinkAidCapsEntry
    MAX-ACCESS  not-accessible
    STATUS      current 
    DESCRIPTION
        "" 
    ::=  { facilityDeployProv 21 }

deployProvCrsDcnLinkAidCapsEntry OBJECT-TYPE
    SYNTAX      DeployProvCrsDcnLinkAidCapsEntry
    MAX-ACCESS  not-accessible
    STATUS      current 
    DESCRIPTION
        "" 
    INDEX       { entityIndex,deployProvCrsDcnLinkAidCapsIndex } 
    ::=  { deployProvCrsDcnLinkAidCapsTable  1  }

DeployProvCrsDcnLinkAidCapsEntry ::=  SEQUENCE
  { deployProvCrsDcnLinkAidCapsIndex EntityIndex }


  
deployProvCrsDcnLinkAidCapsIndex OBJECT-TYPE
    SYNTAX      EntityIndex
    MAX-ACCESS  read-only
    STATUS      current 
    DESCRIPTION
        "Address Identifier of PPPIP LINK Entity." 
    ::=  { deployProvCrsDcnLinkAidCapsEntry 1 }

deployProvCrsDcnEccAidCapsTable OBJECT-TYPE
    SYNTAX      SEQUENCE OF DeployProvCrsDcnEccAidCapsEntry
    MAX-ACCESS  not-accessible
    STATUS      current 
    DESCRIPTION
        "" 
    ::=  { facilityDeployProv 22 }

deployProvCrsDcnEccAidCapsEntry OBJECT-TYPE
    SYNTAX      DeployProvCrsDcnEccAidCapsEntry
    MAX-ACCESS  not-accessible
    STATUS      current 
    DESCRIPTION
        "" 
    INDEX       { entityIndex,deployProvCrsDcnLinkAidCapsIndex } 
    ::=  { deployProvCrsDcnEccAidCapsTable  1  }

DeployProvCrsDcnEccAidCapsEntry ::=  SEQUENCE
  { deployProvCrsDcnEccAidCapsIndex EntityIndex }


  
deployProvCrsDcnEccAidCapsIndex OBJECT-TYPE
    SYNTAX      EntityIndex
    MAX-ACCESS  read-only
    STATUS      current 
    DESCRIPTION
        "Address Identifier of ECC Entity." 
    ::=  { deployProvCrsDcnEccAidCapsEntry 1 }

deployProvApsPeerAidCapsTable OBJECT-TYPE
    SYNTAX      SEQUENCE OF DeployProvApsPeerAidCapsEntry
    MAX-ACCESS  not-accessible
    STATUS      current 
    DESCRIPTION
        "" 
    ::=  { facilityDeployProv 23 }

deployProvApsPeerAidCapsEntry OBJECT-TYPE
    SYNTAX      DeployProvApsPeerAidCapsEntry
    MAX-ACCESS  not-accessible
    STATUS      current 
    DESCRIPTION
        "" 
    INDEX       { entityIndex,deployProvApsWorkingAidCapsIndex } 
    ::=  { deployProvApsPeerAidCapsTable  1  }

DeployProvApsPeerAidCapsEntry ::=  SEQUENCE
  { deployProvApsPeerAidCapsIndex EntityIndex }


  
deployProvApsPeerAidCapsIndex OBJECT-TYPE
    SYNTAX      EntityIndex
    MAX-ACCESS  read-only
    STATUS      current 
    DESCRIPTION
        "AID of Protection Partner involved in the protection group." 
    ::=  { deployProvApsPeerAidCapsEntry 1 }

thresholdOtuTable OBJECT-TYPE
    SYNTAX      SEQUENCE OF ThresholdOtuEntry
    MAX-ACCESS  not-accessible
    STATUS      current 
    DESCRIPTION
        "" 
    ::=  { performanceAdmin 1 }

thresholdOtuEntry OBJECT-TYPE
    SYNTAX      ThresholdOtuEntry
    MAX-ACCESS  not-accessible
    STATUS      current 
    DESCRIPTION
        "" 
    INDEX       { entityIndex } 
    ::=  { thresholdOtuTable  1  }

ThresholdOtuEntry ::=  SEQUENCE
  { thresholdOtuESHighThres15min Unsigned32,
    thresholdOtuESHighThres1day Unsigned32,
    thresholdOtuSESHighThres15min Unsigned32,
    thresholdOtuSESHighThres1day Unsigned32,
    thresholdOtuBbeHighThres15min Unsigned32,
    thresholdOtuBbeHighThres1day Unsigned32,
    thresholdOtuUASHighThres15min Unsigned32,
    thresholdOtuUASHighThres1day Unsigned32 }


  
thresholdOtuESHighThres15min OBJECT-TYPE
    SYNTAX      Unsigned32 (0..900)
    MAX-ACCESS  read-write
    STATUS      current 
    DESCRIPTION
        "Errored Seconds OTU Section Monitoring" 
    ::=  { thresholdOtuEntry 1 }

thresholdOtuESHighThres1day OBJECT-TYPE
    SYNTAX      Unsigned32 (0..86400)
    MAX-ACCESS  read-write
    STATUS      current 
    DESCRIPTION
        "Errored Seconds OTU Section Monitoring" 
    ::=  { thresholdOtuEntry 2 }

thresholdOtuSESHighThres15min OBJECT-TYPE
    SYNTAX      Unsigned32 (0..900)
    MAX-ACCESS  read-write
    STATUS      current 
    DESCRIPTION
        "Errored Seconds OTU Section Monitoring" 
    ::=  { thresholdOtuEntry 3 }

thresholdOtuSESHighThres1day OBJECT-TYPE
    SYNTAX      Unsigned32 (0..86400)
    MAX-ACCESS  read-write
    STATUS      current 
    DESCRIPTION
        "Errored Seconds OTU Section Monitoring" 
    ::=  { thresholdOtuEntry 4 }

thresholdOtuBbeHighThres15min OBJECT-TYPE
    SYNTAX      Unsigned32 (0..900)
    MAX-ACCESS  read-write
    STATUS      current 
    DESCRIPTION
        "Threshold: Background Block Errors OTU Section Monitoring" 
    ::=  { thresholdOtuEntry 5 }

thresholdOtuBbeHighThres1day OBJECT-TYPE
    SYNTAX      Unsigned32 (0..86400)
    MAX-ACCESS  read-write
    STATUS      current 
    DESCRIPTION
        "Threshold: Background Block Errors OTU Section Monitoring" 
    ::=  { thresholdOtuEntry 6 }

thresholdOtuUASHighThres15min OBJECT-TYPE
    SYNTAX      Unsigned32 (0..900)
    MAX-ACCESS  read-write
    STATUS      current 
    DESCRIPTION
        "Unavailable Seconds OTU Section Monitoring" 
    ::=  { thresholdOtuEntry 7 }

thresholdOtuUASHighThres1day OBJECT-TYPE
    SYNTAX      Unsigned32 (0..86400)
    MAX-ACCESS  read-write
    STATUS      current 
    DESCRIPTION
        "Unavailable Seconds OTU Section Monitoring" 
    ::=  { thresholdOtuEntry 8 }

thresholdOduTable OBJECT-TYPE
    SYNTAX      SEQUENCE OF ThresholdOduEntry
    MAX-ACCESS  not-accessible
    STATUS      current 
    DESCRIPTION
        "" 
    ::=  { performanceAdmin 2 }

thresholdOduEntry OBJECT-TYPE
    SYNTAX      ThresholdOduEntry
    MAX-ACCESS  not-accessible
    STATUS      current 
    DESCRIPTION
        "" 
    INDEX       { entityIndex } 
    ::=  { thresholdOduTable  1  }

ThresholdOduEntry ::=  SEQUENCE
  { thresholdOduESHighThres15min Unsigned32,
    thresholdOduESHighThres1day Unsigned32,
    thresholdOduSESHighThres15min Unsigned32,
    thresholdOduSESHighThres1day Unsigned32,
    thresholdOduBbeHighThres15min Unsigned32,
    thresholdOduBbeHighThres1day Unsigned32,
    thresholdOduUASHighThres15min Unsigned32,
    thresholdOduUASHighThres1day Unsigned32 }


  
thresholdOduESHighThres15min OBJECT-TYPE
    SYNTAX      Unsigned32 (0..900)
    MAX-ACCESS  read-write
    STATUS      current 
    DESCRIPTION
        "Errored Seconds ODU Path Monitoring" 
    ::=  { thresholdOduEntry 1 }

thresholdOduESHighThres1day OBJECT-TYPE
    SYNTAX      Unsigned32 (0..86400)
    MAX-ACCESS  read-write
    STATUS      current 
    DESCRIPTION
        "Errored Seconds ODU Path Monitoring" 
    ::=  { thresholdOduEntry 2 }

thresholdOduSESHighThres15min OBJECT-TYPE
    SYNTAX      Unsigned32 (0..900)
    MAX-ACCESS  read-write
    STATUS      current 
    DESCRIPTION
        "Severely Errored Seconds ODU Path Monitoring" 
    ::=  { thresholdOduEntry 3 }

thresholdOduSESHighThres1day OBJECT-TYPE
    SYNTAX      Unsigned32 (0..86400)
    MAX-ACCESS  read-write
    STATUS      current 
    DESCRIPTION
        "Severely Errored Seconds ODU Path Monitoring" 
    ::=  { thresholdOduEntry 4 }

thresholdOduBbeHighThres15min OBJECT-TYPE
    SYNTAX      Unsigned32 (0..900)
    MAX-ACCESS  read-write
    STATUS      current 
    DESCRIPTION
        "Threshold: Background Block Erros ODU Path Monitoring" 
    ::=  { thresholdOduEntry 5 }

thresholdOduBbeHighThres1day OBJECT-TYPE
    SYNTAX      Unsigned32 (0..86400)
    MAX-ACCESS  read-write
    STATUS      current 
    DESCRIPTION
        "Threshold: Background Block Erros ODU Path Monitoring" 
    ::=  { thresholdOduEntry 6 }

thresholdOduUASHighThres15min OBJECT-TYPE
    SYNTAX      Unsigned32 (0..900)
    MAX-ACCESS  read-write
    STATUS      current 
    DESCRIPTION
        "Unavailable Seconds ODU Path Monitoring" 
    ::=  { thresholdOduEntry 7 }

thresholdOduUASHighThres1day OBJECT-TYPE
    SYNTAX      Unsigned32 (0..86400)
    MAX-ACCESS  read-write
    STATUS      current 
    DESCRIPTION
        "Unavailable Seconds ODU Path Monitoring" 
    ::=  { thresholdOduEntry 8 }

thresholdOduTcmATable OBJECT-TYPE
    SYNTAX      SEQUENCE OF ThresholdOduTcmAEntry
    MAX-ACCESS  not-accessible
    STATUS      current 
    DESCRIPTION
        "" 
    ::=  { performanceAdmin 3 }

thresholdOduTcmAEntry OBJECT-TYPE
    SYNTAX      ThresholdOduTcmAEntry
    MAX-ACCESS  not-accessible
    STATUS      current 
    DESCRIPTION
        "" 
    INDEX       { entityIndex } 
    ::=  { thresholdOduTcmATable  1  }

ThresholdOduTcmAEntry ::=  SEQUENCE
  { thresholdOduTcmAESHighThres15min Unsigned32,
    thresholdOduTcmAESHighThres1day Unsigned32,
    thresholdOduTcmASESHighThres15min Unsigned32,
    thresholdOduTcmASESHighThres1day Unsigned32,
    thresholdOduTcmABbeHighThres15min Unsigned32,
    thresholdOduTcmABbeHighThres1day Unsigned32,
    thresholdOduTcmAUASHighThres15min Unsigned32,
    thresholdOduTcmAUASHighThres1day Unsigned32 }


  
thresholdOduTcmAESHighThres15min OBJECT-TYPE
    SYNTAX      Unsigned32 (0..900)
    MAX-ACCESS  read-write
    STATUS      current 
    DESCRIPTION
        "Errored Seconds ODU Tandem Connection Monitoring" 
    ::=  { thresholdOduTcmAEntry 1 }

thresholdOduTcmAESHighThres1day OBJECT-TYPE
    SYNTAX      Unsigned32 (0..86400)
    MAX-ACCESS  read-write
    STATUS      current 
    DESCRIPTION
        "Errored Seconds ODU Tandem Connection Monitoring" 
    ::=  { thresholdOduTcmAEntry 2 }

thresholdOduTcmASESHighThres15min OBJECT-TYPE
    SYNTAX      Unsigned32 (0..900)
    MAX-ACCESS  read-write
    STATUS      current 
    DESCRIPTION
        "Severely Errored Seconds ODU Tandem Connection Monitoring" 
    ::=  { thresholdOduTcmAEntry 3 }

thresholdOduTcmASESHighThres1day OBJECT-TYPE
    SYNTAX      Unsigned32 (0..86400)
    MAX-ACCESS  read-write
    STATUS      current 
    DESCRIPTION
        "Severely Errored Seconds ODU Tandem Connection Monitoring" 
    ::=  { thresholdOduTcmAEntry 4 }

thresholdOduTcmABbeHighThres15min OBJECT-TYPE
    SYNTAX      Unsigned32 (0..900)
    MAX-ACCESS  read-write
    STATUS      current 
    DESCRIPTION
        "Threshold of instance A: Background Block Erros ODU Tandem Connection Monitoring" 
    ::=  { thresholdOduTcmAEntry 5 }

thresholdOduTcmABbeHighThres1day OBJECT-TYPE
    SYNTAX      Unsigned32 (0..86400)
    MAX-ACCESS  read-write
    STATUS      current 
    DESCRIPTION
        "Threshold of instance A: Background Block Erros ODU Tandem Connection Monitoring" 
    ::=  { thresholdOduTcmAEntry 6 }

thresholdOduTcmAUASHighThres15min OBJECT-TYPE
    SYNTAX      Unsigned32 (0..900)
    MAX-ACCESS  read-write
    STATUS      current 
    DESCRIPTION
        "Unavailable Seconds ODU Tandem Connection Monitoring" 
    ::=  { thresholdOduTcmAEntry 7 }

thresholdOduTcmAUASHighThres1day OBJECT-TYPE
    SYNTAX      Unsigned32 (0..86400)
    MAX-ACCESS  read-write
    STATUS      current 
    DESCRIPTION
        "Unavailable Seconds ODU Tandem Connection Monitoring" 
    ::=  { thresholdOduTcmAEntry 8 }

thresholdOduTcmBTable OBJECT-TYPE
    SYNTAX      SEQUENCE OF ThresholdOduTcmBEntry
    MAX-ACCESS  not-accessible
    STATUS      current 
    DESCRIPTION
        "" 
    ::=  { performanceAdmin 4 }

thresholdOduTcmBEntry OBJECT-TYPE
    SYNTAX      ThresholdOduTcmBEntry
    MAX-ACCESS  not-accessible
    STATUS      current 
    DESCRIPTION
        "" 
    INDEX       { entityIndex } 
    ::=  { thresholdOduTcmBTable  1  }

ThresholdOduTcmBEntry ::=  SEQUENCE
  { thresholdOduTcmBBESHighThres15min Unsigned32,
    thresholdOduTcmBESHighThres1day Unsigned32,
    thresholdOduTcmBSESHighThres15min Unsigned32,
    thresholdOduTcmBSESHighThres1day Unsigned32,
    thresholdOduTcmBOduTcmBBbeHighThres15min Unsigned32,
    thresholdOduTcmBOduTcmBBbeHighThres1day Unsigned32,
    thresholdOduTcmBUASHighThres15min Unsigned32,
    thresholdOduTcmBUASHighThres1day Unsigned32 }


  
thresholdOduTcmBBESHighThres15min OBJECT-TYPE
    SYNTAX      Unsigned32 (0..900)
    MAX-ACCESS  read-write
    STATUS      current 
    DESCRIPTION
        "Errored Seconds ODU Tandem Connection Monitoring" 
    ::=  { thresholdOduTcmBEntry 1 }

thresholdOduTcmBESHighThres1day OBJECT-TYPE
    SYNTAX      Unsigned32 (0..86400)
    MAX-ACCESS  read-write
    STATUS      current 
    DESCRIPTION
        "Errored Seconds ODU Tandem Connection Monitoring" 
    ::=  { thresholdOduTcmBEntry 2 }

thresholdOduTcmBSESHighThres15min OBJECT-TYPE
    SYNTAX      Unsigned32 (0..900)
    MAX-ACCESS  read-write
    STATUS      current 
    DESCRIPTION
        "Severely Errored Seconds ODU Tandem Connection Monitoring" 
    ::=  { thresholdOduTcmBEntry 3 }

thresholdOduTcmBSESHighThres1day OBJECT-TYPE
    SYNTAX      Unsigned32 (0..86400)
    MAX-ACCESS  read-write
    STATUS      current 
    DESCRIPTION
        "Severely Errored Seconds ODU Tandem Connection Monitoring" 
    ::=  { thresholdOduTcmBEntry 4 }

thresholdOduTcmBOduTcmBBbeHighThres15min OBJECT-TYPE
    SYNTAX      Unsigned32 (0..900)
    MAX-ACCESS  read-write
    STATUS      current 
    DESCRIPTION
        "Threshold of instance B: Background Block Erros ODU Tandem Connection Monitoring" 
    ::=  { thresholdOduTcmBEntry 5 }

thresholdOduTcmBOduTcmBBbeHighThres1day OBJECT-TYPE
    SYNTAX      Unsigned32 (0..86400)
    MAX-ACCESS  read-write
    STATUS      current 
    DESCRIPTION
        "Threshold of instance B: Background Block Erros ODU Tandem Connection Monitoring" 
    ::=  { thresholdOduTcmBEntry 6 }

thresholdOduTcmBUASHighThres15min OBJECT-TYPE
    SYNTAX      Unsigned32 (0..900)
    MAX-ACCESS  read-write
    STATUS      current 
    DESCRIPTION
        "Unavailable Seconds ODU Tandem Connection Monitoring" 
    ::=  { thresholdOduTcmBEntry 7 }

thresholdOduTcmBUASHighThres1day OBJECT-TYPE
    SYNTAX      Unsigned32 (0..86400)
    MAX-ACCESS  read-write
    STATUS      current 
    DESCRIPTION
        "Unavailable Seconds ODU Tandem Connection Monitoring" 
    ::=  { thresholdOduTcmBEntry 8 }

thresholdSonetSectTable OBJECT-TYPE
    SYNTAX      SEQUENCE OF ThresholdSonetSectEntry
    MAX-ACCESS  not-accessible
    STATUS      current 
    DESCRIPTION
        "" 
    ::=  { performanceAdmin 5 }

thresholdSonetSectEntry OBJECT-TYPE
    SYNTAX      ThresholdSonetSectEntry
    MAX-ACCESS  not-accessible
    STATUS      current 
    DESCRIPTION
        "" 
    INDEX       { entityIndex } 
    ::=  { thresholdSonetSectTable  1  }

ThresholdSonetSectEntry ::=  SEQUENCE
  { thresholdSonetSectESHighThres15min Unsigned32,
    thresholdSonetSectESHighThres1day Unsigned32,
    thresholdSonetSectSESHighThres15min Unsigned32,
    thresholdSonetSectSESHighThres1day Unsigned32,
    thresholdSonetSectSEFSHighThres15min Unsigned32,
    thresholdSonetSectSEFSHighThres1day Unsigned32,
    thresholdSonetSectCVHighThres15min Unsigned32,
    thresholdSonetSectCVHighThres1day Unsigned32 }


  
thresholdSonetSectESHighThres15min OBJECT-TYPE
    SYNTAX      Unsigned32 (0..900)
    MAX-ACCESS  read-write
    STATUS      current 
    DESCRIPTION
        "Errored Seconds Section" 
    ::=  { thresholdSonetSectEntry 1 }

thresholdSonetSectESHighThres1day OBJECT-TYPE
    SYNTAX      Unsigned32 (0..86400)
    MAX-ACCESS  read-write
    STATUS      current 
    DESCRIPTION
        "Errored Seconds Section" 
    ::=  { thresholdSonetSectEntry 2 }

thresholdSonetSectSESHighThres15min OBJECT-TYPE
    SYNTAX      Unsigned32 (0..900)
    MAX-ACCESS  read-write
    STATUS      current 
    DESCRIPTION
        "Severely Errored Seconds Section" 
    ::=  { thresholdSonetSectEntry 3 }

thresholdSonetSectSESHighThres1day OBJECT-TYPE
    SYNTAX      Unsigned32 (0..86400)
    MAX-ACCESS  read-write
    STATUS      current 
    DESCRIPTION
        "Severely Errored Seconds Section" 
    ::=  { thresholdSonetSectEntry 4 }

thresholdSonetSectSEFSHighThres15min OBJECT-TYPE
    SYNTAX      Unsigned32 (0..900)
    MAX-ACCESS  read-write
    STATUS      current 
    DESCRIPTION
        "Severly Errored Framing Seconds Section" 
    ::=  { thresholdSonetSectEntry 5 }

thresholdSonetSectSEFSHighThres1day OBJECT-TYPE
    SYNTAX      Unsigned32 (0..86400)
    MAX-ACCESS  read-write
    STATUS      current 
    DESCRIPTION
        "Severly Errored Framing Seconds Section" 
    ::=  { thresholdSonetSectEntry 6 }

thresholdSonetSectCVHighThres15min OBJECT-TYPE
    SYNTAX      Unsigned32 (0..900)
    MAX-ACCESS  read-write
    STATUS      current 
    DESCRIPTION
        "Threshold 15 Min: Coding Violations Section" 
    ::=  { thresholdSonetSectEntry 7 }

thresholdSonetSectCVHighThres1day OBJECT-TYPE
    SYNTAX      Unsigned32 (0..86400)
    MAX-ACCESS  read-write
    STATUS      current 
    DESCRIPTION
        "Threshold 1 Day: Coding Violations Section" 
    ::=  { thresholdSonetSectEntry 8 }

thresholdSonetLineTable OBJECT-TYPE
    SYNTAX      SEQUENCE OF ThresholdSonetLineEntry
    MAX-ACCESS  not-accessible
    STATUS      current 
    DESCRIPTION
        "" 
    ::=  { performanceAdmin 6 }

thresholdSonetLineEntry OBJECT-TYPE
    SYNTAX      ThresholdSonetLineEntry
    MAX-ACCESS  not-accessible
    STATUS      current 
    DESCRIPTION
        "" 
    INDEX       { entityIndex } 
    ::=  { thresholdSonetLineTable  1  }

ThresholdSonetLineEntry ::=  SEQUENCE
  { thresholdSonetLineESHighThres15min Unsigned32,
    thresholdSonetLineESHighThres1day Unsigned32,
    thresholdSonetLineSESHighThres15min Unsigned32,
    thresholdSonetLineSESHighThres1day Unsigned32,
    thresholdSonetLineUASHighThres15min Unsigned32,
    thresholdSonetLineUASSHighThres1day Unsigned32,
    thresholdSonetLineCVHighThres15min Unsigned32,
    thresholdSonetLineCVSHighThres1day Unsigned32 }


  
thresholdSonetLineESHighThres15min OBJECT-TYPE
    SYNTAX      Unsigned32 (0..900)
    MAX-ACCESS  read-write
    STATUS      current 
    DESCRIPTION
        "Errored Seconds Line / Muliplex Section" 
    ::=  { thresholdSonetLineEntry 1 }

thresholdSonetLineESHighThres1day OBJECT-TYPE
    SYNTAX      Unsigned32 (0..86400)
    MAX-ACCESS  read-write
    STATUS      current 
    DESCRIPTION
        "Errored Seconds Line / Multiplex Section" 
    ::=  { thresholdSonetLineEntry 2 }

thresholdSonetLineSESHighThres15min OBJECT-TYPE
    SYNTAX      Unsigned32 (0..900)
    MAX-ACCESS  read-write
    STATUS      current 
    DESCRIPTION
        "Severely Errored Seconds Line / Multiplex Section" 
    ::=  { thresholdSonetLineEntry 3 }

thresholdSonetLineSESHighThres1day OBJECT-TYPE
    SYNTAX      Unsigned32 (0..86400)
    MAX-ACCESS  read-write
    STATUS      current 
    DESCRIPTION
        "Severely Errored Seconds Line / Multiplex Section" 
    ::=  { thresholdSonetLineEntry 4 }

thresholdSonetLineUASHighThres15min OBJECT-TYPE
    SYNTAX      Unsigned32 (0..900)
    MAX-ACCESS  read-write
    STATUS      current 
    DESCRIPTION
        "Unavailable Seconds Line / Multiplex Section" 
    ::=  { thresholdSonetLineEntry 5 }

thresholdSonetLineUASSHighThres1day OBJECT-TYPE
    SYNTAX      Unsigned32 (0..86400)
    MAX-ACCESS  read-write
    STATUS      current 
    DESCRIPTION
        "Unavailable Seconds Line / Multiplex Section 1Day Threshold" 
    ::=  { thresholdSonetLineEntry 6 }

thresholdSonetLineCVHighThres15min OBJECT-TYPE
    SYNTAX      Unsigned32 (0..900)
    MAX-ACCESS  read-write
    STATUS      current 
    DESCRIPTION
        "Threshold 15 Min: Coding Violations Line / Multiplex Section" 
    ::=  { thresholdSonetLineEntry 7 }

thresholdSonetLineCVSHighThres1day OBJECT-TYPE
    SYNTAX      Unsigned32 (0..86400)
    MAX-ACCESS  read-write
    STATUS      current 
    DESCRIPTION
        "1Day Threshold: Coding Violations Line / Multiplex Section" 
    ::=  { thresholdSonetLineEntry 8 }

thresholdSonetHoPathTable OBJECT-TYPE
    SYNTAX      SEQUENCE OF ThresholdSonetHoPathEntry
    MAX-ACCESS  not-accessible
    STATUS      current 
    DESCRIPTION
        "" 
    ::=  { performanceAdmin 7 }

thresholdSonetHoPathEntry OBJECT-TYPE
    SYNTAX      ThresholdSonetHoPathEntry
    MAX-ACCESS  not-accessible
    STATUS      current 
    DESCRIPTION
        "" 
    INDEX       { entityIndex } 
    ::=  { thresholdSonetHoPathTable  1  }

ThresholdSonetHoPathEntry ::=  SEQUENCE
  { thresholdSonetHoPathESHighThres15min Unsigned32,
    thresholdSonetHoPathESHighThres1day Unsigned32,
    thresholdSonetHoPathSESHighThres15min Unsigned32,
    thresholdSonetHoPathSESHighThres1day Unsigned32,
    thresholdSonetHoPathUASHighThres15min Unsigned32,
    thresholdSonetHoPathUASHighThres1day Unsigned32,
    thresholdSonetHoPathCVHighThres15min Unsigned32,
    thresholdSonetHoPathCVHighThres1day Unsigned32 }


  
thresholdSonetHoPathESHighThres15min OBJECT-TYPE
    SYNTAX      Unsigned32 (0..900)
    MAX-ACCESS  read-write
    STATUS      current 
    DESCRIPTION
        "Errored Seconds Path" 
    ::=  { thresholdSonetHoPathEntry 1 }

thresholdSonetHoPathESHighThres1day OBJECT-TYPE
    SYNTAX      Unsigned32 (0..86400)
    MAX-ACCESS  read-write
    STATUS      current 
    DESCRIPTION
        "Errored Seconds Path" 
    ::=  { thresholdSonetHoPathEntry 2 }

thresholdSonetHoPathSESHighThres15min OBJECT-TYPE
    SYNTAX      Unsigned32 (0..900)
    MAX-ACCESS  read-write
    STATUS      current 
    DESCRIPTION
        "Severely Errored Seconds Path" 
    ::=  { thresholdSonetHoPathEntry 3 }

thresholdSonetHoPathSESHighThres1day OBJECT-TYPE
    SYNTAX      Unsigned32 (0..86400)
    MAX-ACCESS  read-write
    STATUS      current 
    DESCRIPTION
        "Severely Errored Seconds Path" 
    ::=  { thresholdSonetHoPathEntry 4 }

thresholdSonetHoPathUASHighThres15min OBJECT-TYPE
    SYNTAX      Unsigned32 (0..900)
    MAX-ACCESS  read-write
    STATUS      current 
    DESCRIPTION
        "Unavailable Seconds Path" 
    ::=  { thresholdSonetHoPathEntry 5 }

thresholdSonetHoPathUASHighThres1day OBJECT-TYPE
    SYNTAX      Unsigned32 (0..86400)
    MAX-ACCESS  read-write
    STATUS      current 
    DESCRIPTION
        "Coding Violations Path" 
    ::=  { thresholdSonetHoPathEntry 6 }

thresholdSonetHoPathCVHighThres15min OBJECT-TYPE
    SYNTAX      Unsigned32 (0..900)
    MAX-ACCESS  read-write
    STATUS      current 
    DESCRIPTION
        "THreshold 15 Min: Coding Violations Path" 
    ::=  { thresholdSonetHoPathEntry 7 }

thresholdSonetHoPathCVHighThres1day OBJECT-TYPE
    SYNTAX      Unsigned32 (0..86400)
    MAX-ACCESS  read-write
    STATUS      current 
    DESCRIPTION
        "Threshold 1 Day: Coding Violations Path" 
    ::=  { thresholdSonetHoPathEntry 8 }

thresholdSonetLoPathTable OBJECT-TYPE
    SYNTAX      SEQUENCE OF ThresholdSonetLoPathEntry
    MAX-ACCESS  not-accessible
    STATUS      current 
    DESCRIPTION
        "" 
    ::=  { performanceAdmin 8 }

thresholdSonetLoPathEntry OBJECT-TYPE
    SYNTAX      ThresholdSonetLoPathEntry
    MAX-ACCESS  not-accessible
    STATUS      current 
    DESCRIPTION
        "" 
    INDEX       { entityIndex } 
    ::=  { thresholdSonetLoPathTable  1  }

ThresholdSonetLoPathEntry ::=  SEQUENCE
  { thresholdSonetLoPathESHighThres15min Unsigned32,
    thresholdSonetLoPathESHighThres1day Unsigned32,
    thresholdSonetLoPathSESHighThres15min Unsigned32,
    thresholdSonetLoPathSESHighThres1day Unsigned32,
    thresholdSonetLoPathUASHighThres15min Unsigned32,
    thresholdSonetLoPathUASHighThres1day Unsigned32,
    thresholdSonetLoPathCVHighThres15min Unsigned32,
    thresholdSonetLoPathCVHighThres1day Unsigned32 }


  
thresholdSonetLoPathESHighThres15min OBJECT-TYPE
    SYNTAX      Unsigned32 (0..900)
    MAX-ACCESS  read-write
    STATUS      current 
    DESCRIPTION
        "Errored Seconds Lower Order Path Threshold 15MIN" 
    ::=  { thresholdSonetLoPathEntry 1 }

thresholdSonetLoPathESHighThres1day OBJECT-TYPE
    SYNTAX      Unsigned32 (0..86400)
    MAX-ACCESS  read-write
    STATUS      current 
    DESCRIPTION
        "Errored Seconds Lower Order Path Threshold 1DAY" 
    ::=  { thresholdSonetLoPathEntry 2 }

thresholdSonetLoPathSESHighThres15min OBJECT-TYPE
    SYNTAX      Unsigned32 (0..900)
    MAX-ACCESS  read-write
    STATUS      current 
    DESCRIPTION
        "Severely Errored Seconds LO-Path Threshold 15MIN" 
    ::=  { thresholdSonetLoPathEntry 3 }

thresholdSonetLoPathSESHighThres1day OBJECT-TYPE
    SYNTAX      Unsigned32 (0..86400)
    MAX-ACCESS  read-write
    STATUS      current 
    DESCRIPTION
        "Severely Errored Seconds LO-Path Threshold 1DAY" 
    ::=  { thresholdSonetLoPathEntry 4 }

thresholdSonetLoPathUASHighThres15min OBJECT-TYPE
    SYNTAX      Unsigned32 (0..900)
    MAX-ACCESS  read-write
    STATUS      current 
    DESCRIPTION
        "Unavailable Seconds LO-Path Threshold" 
    ::=  { thresholdSonetLoPathEntry 5 }

thresholdSonetLoPathUASHighThres1day OBJECT-TYPE
    SYNTAX      Unsigned32 (0..86400)
    MAX-ACCESS  read-write
    STATUS      current 
    DESCRIPTION
        "Unavailable Seconds LO-Path Threshold 1DAY" 
    ::=  { thresholdSonetLoPathEntry 6 }

thresholdSonetLoPathCVHighThres15min OBJECT-TYPE
    SYNTAX      Unsigned32 (0..900)
    MAX-ACCESS  read-write
    STATUS      current 
    DESCRIPTION
        "Coding Violations Lower Order Path Threshold 15MIN" 
    ::=  { thresholdSonetLoPathEntry 7 }

thresholdSonetLoPathCVHighThres1day OBJECT-TYPE
    SYNTAX      Unsigned32 (0..86400)
    MAX-ACCESS  read-write
    STATUS      current 
    DESCRIPTION
        "Coding Violations Lower Order Path Threshold 1DAY" 
    ::=  { thresholdSonetLoPathEntry 8 }

thresholdPhysPerfTable OBJECT-TYPE
    SYNTAX      SEQUENCE OF ThresholdPhysPerfEntry
    MAX-ACCESS  not-accessible
    STATUS      current 
    DESCRIPTION
        "" 
    ::=  { performanceAdmin 9 }

thresholdPhysPerfEntry OBJECT-TYPE
    SYNTAX      ThresholdPhysPerfEntry
    MAX-ACCESS  not-accessible
    STATUS      current 
    DESCRIPTION
        "" 
    INDEX       { entityIndex } 
    ::=  { thresholdPhysPerfTable  1  }

ThresholdPhysPerfEntry ::=  SEQUENCE
  { thresholdPhysPerfOpticalInputPwrLow Integer32,
    thresholdPhysPerfOpticalInputPwrHigh Integer32,
    thresholdPhysPerfOpticalOutputPwrLow Integer32,
    thresholdPhysPerfOpticalOutputPwrHigh Integer32,
    thresholdPhysPerfLaserBiasCurrentNormalized Unsigned32,
    thresholdPhysPerfAttRxLow Integer32,
    thresholdPhysPerfAttRxHigh Integer32,
    thresholdPhysPerfAttTxLow Integer32,
    thresholdPhysPerfAttTxHigh Integer32,
    thresholdPhysPerfLaserTempLowThres Integer32,
    thresholdPhysPerfLaserTempHighThres Integer32 }


  
thresholdPhysPerfOpticalInputPwrLow OBJECT-TYPE
    SYNTAX      Integer32 (-320..-10)
    UNITS       "0.1 dBm"
    MAX-ACCESS  read-write
    STATUS      current 
    DESCRIPTION
        "Optical Input Power Received" 
    ::=  { thresholdPhysPerfEntry 1 }

thresholdPhysPerfOpticalInputPwrHigh OBJECT-TYPE
    SYNTAX      Integer32 (-310..0)
    UNITS       "0.1 dBm"
    MAX-ACCESS  read-write
    STATUS      current 
    DESCRIPTION
        "Optical Input Power Received" 
    ::=  { thresholdPhysPerfEntry 2 }

thresholdPhysPerfOpticalOutputPwrLow OBJECT-TYPE
    SYNTAX      Integer32
    UNITS       "0.1 dBm"
    MAX-ACCESS  read-write
    STATUS      current 
    DESCRIPTION
        "Low fixed threshold of the Optical Power Transmitted (output)" 
    ::=  { thresholdPhysPerfEntry 3 }

thresholdPhysPerfOpticalOutputPwrHigh OBJECT-TYPE
    SYNTAX      Integer32
    UNITS       "0.1 dBm"
    MAX-ACCESS  read-write
    STATUS      current 
    DESCRIPTION
        "High fixed threshold of the Optical Power Transmitted (output)" 
    ::=  { thresholdPhysPerfEntry 4 }

thresholdPhysPerfLaserBiasCurrentNormalized OBJECT-TYPE
    SYNTAX      Unsigned32
    UNITS       "%"
    MAX-ACCESS  read-write
    STATUS      current 
    DESCRIPTION
        "Laser Bias Current Normalized Fixed High Threshold." 
    ::=  { thresholdPhysPerfEntry 5 }

thresholdPhysPerfAttRxLow OBJECT-TYPE
    SYNTAX      Integer32
    UNITS       "0.1 dB"
    MAX-ACCESS  read-write
    STATUS      current 
    DESCRIPTION
        "Low Threshold for Attenuation on Receive Fiber." 
    ::=  { thresholdPhysPerfEntry 6 }

thresholdPhysPerfAttRxHigh OBJECT-TYPE
    SYNTAX      Integer32
    UNITS       "0.1 dB"
    MAX-ACCESS  read-write
    STATUS      current 
    DESCRIPTION
        "High Threshold for Attenuation on Receive Fiber" 
    ::=  { thresholdPhysPerfEntry 7 }

thresholdPhysPerfAttTxLow OBJECT-TYPE
    SYNTAX      Integer32
    UNITS       "0.1 dB"
    MAX-ACCESS  read-write
    STATUS      current 
    DESCRIPTION
        "Low Threshold Attenuation on Transmit Fiber" 
    ::=  { thresholdPhysPerfEntry 8 }

thresholdPhysPerfAttTxHigh OBJECT-TYPE
    SYNTAX      Integer32
    UNITS       "0.1 dB"
    MAX-ACCESS  read-write
    STATUS      current 
    DESCRIPTION
        "High Threshold of Attenuation on Transmit Fiber" 
    ::=  { thresholdPhysPerfEntry 9 }

thresholdPhysPerfLaserTempLowThres OBJECT-TYPE
    SYNTAX      Integer32
    UNITS       "0.1 °C"
    MAX-ACCESS  read-write
    STATUS      current 
    DESCRIPTION
        "Laser temperature fixed low threshold." 
    ::=  { thresholdPhysPerfEntry 10 }

thresholdPhysPerfLaserTempHighThres OBJECT-TYPE
    SYNTAX      Integer32
    UNITS       "0.1 °C"
    MAX-ACCESS  read-write
    STATUS      current 
    DESCRIPTION
        "Laser temperature fixed high threshold." 
    ::=  { thresholdPhysPerfEntry 11 }

thresholdPhysConvTable OBJECT-TYPE
    SYNTAX      SEQUENCE OF ThresholdPhysConvEntry
    MAX-ACCESS  not-accessible
    STATUS      current 
    DESCRIPTION
        "" 
    ::=  { performanceAdmin 10 }

thresholdPhysConvEntry OBJECT-TYPE
    SYNTAX      ThresholdPhysConvEntry
    MAX-ACCESS  not-accessible
    STATUS      current 
    DESCRIPTION
        "" 
    INDEX       { entityIndex } 
    ::=  { thresholdPhysConvTable  1  }

ThresholdPhysConvEntry ::=  SEQUENCE
  { thresholdPhysConvESHighThres15min Unsigned32,
    thresholdPhysConvESHighThres1day Unsigned32,
    thresholdPhysConvDEHighThres15min Unsigned32,
    thresholdPhysConvDEHighThres1day Unsigned32,
    thresholdPhysConvCVHighThres15min Unsigned32,
    thresholdPhysConvCVHighThres1day Unsigned32 }


  
thresholdPhysConvESHighThres15min OBJECT-TYPE
    SYNTAX      Unsigned32 (0..900)
    MAX-ACCESS  read-write
    STATUS      current 
    DESCRIPTION
        "Errored Seconds Physical Coding Layer" 
    ::=  { thresholdPhysConvEntry 1 }

thresholdPhysConvESHighThres1day OBJECT-TYPE
    SYNTAX      Unsigned32 (0..89400)
    MAX-ACCESS  read-write
    STATUS      current 
    DESCRIPTION
        "Errored Seconds Physical Coding Layer" 
    ::=  { thresholdPhysConvEntry 2 }

thresholdPhysConvDEHighThres15min OBJECT-TYPE
    SYNTAX      Unsigned32 (0..900)
    MAX-ACCESS  read-write
    STATUS      current 
    DESCRIPTION
        "Threshold 15 Min: Disparity Errors Physical Coding Layer" 
    ::=  { thresholdPhysConvEntry 3 }

thresholdPhysConvDEHighThres1day OBJECT-TYPE
    SYNTAX      Unsigned32 (0..86400)
    MAX-ACCESS  read-write
    STATUS      current 
    DESCRIPTION
        "Threshold 1 Day: Disparity Errors Physical Coding Layer" 
    ::=  { thresholdPhysConvEntry 4 }

thresholdPhysConvCVHighThres15min OBJECT-TYPE
    SYNTAX      Unsigned32 (0..900)
    MAX-ACCESS  read-write
    STATUS      current 
    DESCRIPTION
        "Threshold 15 Min: Coding Violations Physical Coding Layer" 
    ::=  { thresholdPhysConvEntry 5 }

thresholdPhysConvCVHighThres1day OBJECT-TYPE
    SYNTAX      Unsigned32 (0..86400)
    MAX-ACCESS  read-write
    STATUS      current 
    DESCRIPTION
        "Threshold 1 Day: Coding Violations - Physical Coding Layer" 
    ::=  { thresholdPhysConvEntry 6 }

thresholdEthRxTable OBJECT-TYPE
    SYNTAX      SEQUENCE OF ThresholdEthRxEntry
    MAX-ACCESS  not-accessible
    STATUS      current 
    DESCRIPTION
        "" 
    ::=  { performanceAdmin 11 }

thresholdEthRxEntry OBJECT-TYPE
    SYNTAX      ThresholdEthRxEntry
    MAX-ACCESS  not-accessible
    STATUS      current 
    DESCRIPTION
        "" 
    INDEX       { entityIndex } 
    ::=  { thresholdEthRxTable  1  }

ThresholdEthRxEntry ::=  SEQUENCE
  { thresholdEthRxPauseFramesHighThres15Min Unsigned32,
    thresholdEthRxPauseFramesHighThres1Day Unsigned32,
    thresholdEthRxCrcFramesHighThres15Min Unsigned32,
    thresholdEthRxCrcFramesHighThres1Day Unsigned32,
    thresholdEthRxDiscardedFramesHighThres15Min Unsigned32,
    thresholdEthRxDiscardedFramesHighThres1Day Unsigned32 }


  
thresholdEthRxPauseFramesHighThres15Min OBJECT-TYPE
    SYNTAX      Unsigned32 (0..900)
    MAX-ACCESS  read-write
    STATUS      current 
    DESCRIPTION
        "Pause Frames Received High Threshold" 
    ::=  { thresholdEthRxEntry 1 }

thresholdEthRxPauseFramesHighThres1Day OBJECT-TYPE
    SYNTAX      Unsigned32 (0..86400)
    MAX-ACCESS  read-write
    STATUS      current 
    DESCRIPTION
        "Pause Frames Received High Threshold" 
    ::=  { thresholdEthRxEntry 2 }

thresholdEthRxCrcFramesHighThres15Min OBJECT-TYPE
    SYNTAX      Unsigned32 (0..900)
    MAX-ACCESS  read-write
    STATUS      current 
    DESCRIPTION
        "Errored Frames (CRC Errors) Received 15 Min Threshold" 
    ::=  { thresholdEthRxEntry 3 }

thresholdEthRxCrcFramesHighThres1Day OBJECT-TYPE
    SYNTAX      Unsigned32 (0..86400)
    MAX-ACCESS  read-write
    STATUS      current 
    DESCRIPTION
        "Errored Frames (CRC Errors) Received 1 Day Threshold" 
    ::=  { thresholdEthRxEntry 4 }

thresholdEthRxDiscardedFramesHighThres15Min OBJECT-TYPE
    SYNTAX      Unsigned32 (0..900)
    MAX-ACCESS  read-write
    STATUS      current 
    DESCRIPTION
        "Received Frames Discarded 15-MIN Threshold" 
    ::=  { thresholdEthRxEntry 5 }

thresholdEthRxDiscardedFramesHighThres1Day OBJECT-TYPE
    SYNTAX      Unsigned32 (0..86400)
    MAX-ACCESS  read-write
    STATUS      current 
    DESCRIPTION
        "Received Frames Discarded 1DAY Threshold" 
    ::=  { thresholdEthRxEntry 6 }

thresholdEthTxTable OBJECT-TYPE
    SYNTAX      SEQUENCE OF ThresholdEthTxEntry
    MAX-ACCESS  not-accessible
    STATUS      current 
    DESCRIPTION
        "" 
    ::=  { performanceAdmin 12 }

thresholdEthTxEntry OBJECT-TYPE
    SYNTAX      ThresholdEthTxEntry
    MAX-ACCESS  not-accessible
    STATUS      current 
    DESCRIPTION
        "" 
    INDEX       { entityIndex } 
    ::=  { thresholdEthTxTable  1  }

ThresholdEthTxEntry ::=  SEQUENCE
  { thresholdEthTxPauseFramesHighThres15Min Unsigned32,
    thresholdEthTxPauseFramesHighThres1Day Unsigned32,
    thresholdEthTxCrcFramesEgressHighThres15Min Unsigned32,
    thresholdEthTxCrcFramesEgressHighThres1Day Unsigned32 }


  
thresholdEthTxPauseFramesHighThres15Min OBJECT-TYPE
    SYNTAX      Unsigned32 (0..900)
    MAX-ACCESS  read-write
    STATUS      current 
    DESCRIPTION
        "Pause Frames Transmitted High Threshold" 
    ::=  { thresholdEthTxEntry 1 }

thresholdEthTxPauseFramesHighThres1Day OBJECT-TYPE
    SYNTAX      Unsigned32 (0..86400)
    MAX-ACCESS  read-write
    STATUS      current 
    DESCRIPTION
        "Pause Frames Transmitted High Threshold" 
    ::=  { thresholdEthTxEntry 2 }

thresholdEthTxCrcFramesEgressHighThres15Min OBJECT-TYPE
    SYNTAX      Unsigned32 (0..900)
    MAX-ACCESS  read-write
    STATUS      current 
    DESCRIPTION
        "Errored Frames (CRC Erors) Received egress from Mapper High Threshold" 
    ::=  { thresholdEthTxEntry 3 }

thresholdEthTxCrcFramesEgressHighThres1Day OBJECT-TYPE
    SYNTAX      Unsigned32 (0..86400)
    MAX-ACCESS  read-write
    STATUS      current 
    DESCRIPTION
        "Errored Frames (CRC Errors) Received egress from Mapper High Threshold" 
    ::=  { thresholdEthTxEntry 4 }

thresholdGfpTable OBJECT-TYPE
    SYNTAX      SEQUENCE OF ThresholdGfpEntry
    MAX-ACCESS  not-accessible
    STATUS      current 
    DESCRIPTION
        "" 
    ::=  { performanceAdmin 13 }

thresholdGfpEntry OBJECT-TYPE
    SYNTAX      ThresholdGfpEntry
    MAX-ACCESS  not-accessible
    STATUS      current 
    DESCRIPTION
        "" 
    INDEX       { entityIndex } 
    ::=  { thresholdGfpTable  1  }

ThresholdGfpEntry ::=  SEQUENCE
  { thresholdGfpCoreHecCorrectedFramesHighThres15Min Unsigned32,
    thresholdGfpCoreHecCorrectedFramesHighThres1Day Unsigned32,
    thresholdGfpTypeHecCorrectedFramesHighThres15Min Unsigned32,
    thresholdGfpTypeHecCorrectedFramesHighThres15Day Unsigned32,
    thresholdGfpTypeHecDiscardedFramesHighThres15Min Unsigned32,
    thresholdGfpTypeHecDiscardedFramesHighThres1Day Unsigned32 }


  
thresholdGfpCoreHecCorrectedFramesHighThres15Min OBJECT-TYPE
    SYNTAX      Unsigned32 (0..900)
    MAX-ACCESS  read-write
    STATUS      current 
    DESCRIPTION
        "Core HEC Corrected Frames High Threshold" 
    ::=  { thresholdGfpEntry 1 }

thresholdGfpCoreHecCorrectedFramesHighThres1Day OBJECT-TYPE
    SYNTAX      Unsigned32 (0..86400)
    MAX-ACCESS  read-write
    STATUS      current 
    DESCRIPTION
        "Core HEC Corrected Frames High Threshold" 
    ::=  { thresholdGfpEntry 2 }

thresholdGfpTypeHecCorrectedFramesHighThres15Min OBJECT-TYPE
    SYNTAX      Unsigned32 (0..900)
    MAX-ACCESS  read-write
    STATUS      current 
    DESCRIPTION
        "Type Field HEC Corrected Frames High Threshold" 
    ::=  { thresholdGfpEntry 3 }

thresholdGfpTypeHecCorrectedFramesHighThres15Day OBJECT-TYPE
    SYNTAX      Unsigned32 (0..86400)
    MAX-ACCESS  read-write
    STATUS      current 
    DESCRIPTION
        "Type Field HEC Corrected Frames High Threshold" 
    ::=  { thresholdGfpEntry 4 }

thresholdGfpTypeHecDiscardedFramesHighThres15Min OBJECT-TYPE
    SYNTAX      Unsigned32 (0..900)
    MAX-ACCESS  read-write
    STATUS      current 
    DESCRIPTION
        "Type Field HEC Discarded Frames High Threshold" 
    ::=  { thresholdGfpEntry 5 }

thresholdGfpTypeHecDiscardedFramesHighThres1Day OBJECT-TYPE
    SYNTAX      Unsigned32 (0..86400)
    MAX-ACCESS  read-write
    STATUS      current 
    DESCRIPTION
        "Type Field HEC Discarded Frames High Threshold" 
    ::=  { thresholdGfpEntry 6 }

thresholdDefectSecondsTable OBJECT-TYPE
    SYNTAX      SEQUENCE OF ThresholdDefectSecondsEntry
    MAX-ACCESS  not-accessible
    STATUS      current 
    DESCRIPTION
        "" 
    ::=  { performanceMIB 14 }

thresholdDefectSecondsEntry OBJECT-TYPE
    SYNTAX      ThresholdDefectSecondsEntry
    MAX-ACCESS  not-accessible
    STATUS      current 
    DESCRIPTION
        "" 
    INDEX       { entityIndex } 
    ::=  { thresholdDefectSecondsTable  1  }

ThresholdDefectSecondsEntry ::=  SEQUENCE
  { thresholdDefectSecondsDefectSecondsHighThres15Min Unsigned32,
    thresholdDefectSecondsDefectSecondsHighThres1Day Unsigned32 }


  
thresholdDefectSecondsDefectSecondsHighThres15Min OBJECT-TYPE
    SYNTAX      Unsigned32 (0..900)
    MAX-ACCESS  read-write
    STATUS      current 
    DESCRIPTION
        "Defect Seconds High Threshold 15 min" 
    ::=  { thresholdDefectSecondsEntry 1 }

thresholdDefectSecondsDefectSecondsHighThres1Day OBJECT-TYPE
    SYNTAX      Unsigned32 (0..86400)
    MAX-ACCESS  read-write
    STATUS      current 
    DESCRIPTION
        "Defect Seconds High Threshold 1 day" 
    ::=  { thresholdDefectSecondsEntry 2 }

thresholdIntrusionTable OBJECT-TYPE
    SYNTAX      SEQUENCE OF ThresholdIntrusionEntry
    MAX-ACCESS  not-accessible
    STATUS      current 
    DESCRIPTION
        "" 
    ::=  { performanceAdmin 15 }

thresholdIntrusionEntry OBJECT-TYPE
    SYNTAX      ThresholdIntrusionEntry
    MAX-ACCESS  not-accessible
    STATUS      current 
    DESCRIPTION
        "" 
    INDEX       { entityIndex } 
    ::=  { thresholdIntrusionTable  1  }

ThresholdIntrusionEntry ::=  SEQUENCE
  { thresholdIntrusionGradient Unsigned32 }


  
thresholdIntrusionGradient OBJECT-TYPE
    SYNTAX      Unsigned32 (5..30)
    UNITS       "0.1 dB/min"
    MAX-ACCESS  read-write
    STATUS      current 
    DESCRIPTION
        "Attenuation Gradient Threshold on Receive Fiber. Applies to both TRMT and RCV directions; but threshold violation is reported for each direction separately by the 'tapping' alarms: INTRUDE-RCV and INTRUDE-TRMT." 
    ::=  { thresholdIntrusionEntry 1 }

thresholdOtuFecTable OBJECT-TYPE
    SYNTAX      SEQUENCE OF ThresholdOtuFecEntry
    MAX-ACCESS  not-accessible
    STATUS      current 
    DESCRIPTION
        "" 
    ::=  { performanceAdmin 16 }

thresholdOtuFecEntry OBJECT-TYPE
    SYNTAX      ThresholdOtuFecEntry
    MAX-ACCESS  not-accessible
    STATUS      current 
    DESCRIPTION
        "" 
    INDEX       { entityIndex } 
    ::=  { thresholdOtuFecTable  1  }

ThresholdOtuFecEntry ::=  SEQUENCE
  { thresholdOtuFecESHighThres15min Unsigned32,
    thresholdOtuFecESHighThres1day Unsigned32,
    thresholdOtuFecSESHighThres15min Unsigned32,
    thresholdOtuFecSESHighThres1day Unsigned32,
    thresholdOtuFecCEHighThres15min Unsigned32,
    thresholdOtuFecCEHighThres1day Unsigned32,
    thresholdOtuFecUBEHighThres15min Unsigned32,
    thresholdOtuFecUBEHighThres1day Unsigned32 }


  
thresholdOtuFecESHighThres15min OBJECT-TYPE
    SYNTAX      Unsigned32 (0..900)
    MAX-ACCESS  read-write
    STATUS      current 
    DESCRIPTION
        "Errored Seconds FEC OTU High Threshold" 
    ::=  { thresholdOtuFecEntry 1 }

thresholdOtuFecESHighThres1day OBJECT-TYPE
    SYNTAX      Unsigned32 (0..86400)
    MAX-ACCESS  read-write
    STATUS      current 
    DESCRIPTION
        "Errored Seconds FEC OTU High Threshold" 
    ::=  { thresholdOtuFecEntry 2 }

thresholdOtuFecSESHighThres15min OBJECT-TYPE
    SYNTAX      Unsigned32 (0..900)
    MAX-ACCESS  read-write
    STATUS      current 
    DESCRIPTION
        "Severely Errored Seconds FEC OTU High Threshold" 
    ::=  { thresholdOtuFecEntry 3 }

thresholdOtuFecSESHighThres1day OBJECT-TYPE
    SYNTAX      Unsigned32 (0..86400)
    MAX-ACCESS  read-write
    STATUS      current 
    DESCRIPTION
        "Severely Errored Seconds FEC OTU High Threshold" 
    ::=  { thresholdOtuFecEntry 4 }

thresholdOtuFecCEHighThres15min OBJECT-TYPE
    SYNTAX      Unsigned32 (0..900)
    MAX-ACCESS  read-write
    STATUS      current 
    DESCRIPTION
        "FEC Corrected Errors 15 Min Threshold" 
    ::=  { thresholdOtuFecEntry 5 }

thresholdOtuFecCEHighThres1day OBJECT-TYPE
    SYNTAX      Unsigned32 (0..86400)
    MAX-ACCESS  read-write
    STATUS      current 
    DESCRIPTION
        "FEC Corrected Errors 1Day Threshold" 
    ::=  { thresholdOtuFecEntry 6 }

thresholdOtuFecUBEHighThres15min OBJECT-TYPE
    SYNTAX      Unsigned32 (0..900)
    MAX-ACCESS  read-write
    STATUS      current 
    DESCRIPTION
        "Uncorrected Block Errors High Threshold" 
    ::=  { thresholdOtuFecEntry 7 }

thresholdOtuFecUBEHighThres1day OBJECT-TYPE
    SYNTAX      Unsigned32 (0..86400)
    MAX-ACCESS  read-write
    STATUS      current 
    DESCRIPTION
        "Uncorrected Block Errors High Threshold" 
    ::=  { thresholdOtuFecEntry 8 }

thresholdGfptTable OBJECT-TYPE
    SYNTAX      SEQUENCE OF ThresholdGfptEntry
    MAX-ACCESS  not-accessible
    STATUS      current 
    DESCRIPTION
        "" 
    ::=  { performanceAdmin 17 }

thresholdGfptEntry OBJECT-TYPE
    SYNTAX      ThresholdGfptEntry
    MAX-ACCESS  not-accessible
    STATUS      current 
    DESCRIPTION
        "" 
    INDEX       { entityIndex } 
    ::=  { thresholdGfptTable  1  }

ThresholdGfptEntry ::=  SEQUENCE
  { thresholdGfptDiscardedSuperblocksHighThres15Min Unsigned32,
    thresholdGfptDiscardedSuperblocksHighThres1Day Unsigned32 }


  
thresholdGfptDiscardedSuperblocksHighThres15Min OBJECT-TYPE
    SYNTAX      Unsigned32 (0..900)
    MAX-ACCESS  read-write
    STATUS      current 
    DESCRIPTION
        "Discarded Super-Blocks 15-MIN Threshold" 
    ::=  { thresholdGfptEntry 1 }

thresholdGfptDiscardedSuperblocksHighThres1Day OBJECT-TYPE
    SYNTAX      Unsigned32 (0..86400)
    MAX-ACCESS  read-write
    STATUS      current 
    DESCRIPTION
        "Discarded Super-Blocks 1-DAY Threshold" 
    ::=  { thresholdGfptEntry 2 }

thresholdSubAggregateTable OBJECT-TYPE
    SYNTAX      SEQUENCE OF ThresholdSubAggregateEntry
    MAX-ACCESS  not-accessible
    STATUS      current 
    DESCRIPTION
        "" 
    ::=  { performanceAdmin 18 }

thresholdSubAggregateEntry OBJECT-TYPE
    SYNTAX      ThresholdSubAggregateEntry
    MAX-ACCESS  not-accessible
    STATUS      current 
    DESCRIPTION
        "" 
    INDEX       { entityIndex } 
    ::=  { thresholdSubAggregateTable  1  }

ThresholdSubAggregateEntry ::=  SEQUENCE
  { thresholdSubAggregateESHighThres15min Unsigned32,
    thresholdSubAggregateESHighThres1day Unsigned32,
    thresholdSubAggregateSESHighThres15min Unsigned32,
    thresholdSubAggregateSESHighThres1day Unsigned32 }


  
thresholdSubAggregateESHighThres15min OBJECT-TYPE
    SYNTAX      Unsigned32 (0..900)
    MAX-ACCESS  read-write
    STATUS      current 
    DESCRIPTION
        "Multiplexer Errored Seconds High Threshold" 
    ::=  { thresholdSubAggregateEntry 1 }

thresholdSubAggregateESHighThres1day OBJECT-TYPE
    SYNTAX      Unsigned32 (0..86400)
    MAX-ACCESS  read-write
    STATUS      current 
    DESCRIPTION
        "Multiplexer Errored Seconds High Threshold" 
    ::=  { thresholdSubAggregateEntry 2 }

thresholdSubAggregateSESHighThres15min OBJECT-TYPE
    SYNTAX      Unsigned32 (0..900)
    MAX-ACCESS  read-write
    STATUS      current 
    DESCRIPTION
        "Multiplexer Severely Errored Seconds High Threshold" 
    ::=  { thresholdSubAggregateEntry 3 }

thresholdSubAggregateSESHighThres1day OBJECT-TYPE
    SYNTAX      Unsigned32 (0..86400)
    MAX-ACCESS  read-write
    STATUS      current 
    DESCRIPTION
        "Multiplexer Severely Errored Seconds High Threshold" 
    ::=  { thresholdSubAggregateEntry 4 }

thresholdOduTcmCTable OBJECT-TYPE
    SYNTAX      SEQUENCE OF ThresholdOduTcmCEntry
    MAX-ACCESS  not-accessible
    STATUS      current 
    DESCRIPTION
        "" 
    ::=  { performanceAdmin 19 }

thresholdOduTcmCEntry OBJECT-TYPE
    SYNTAX      ThresholdOduTcmCEntry
    MAX-ACCESS  not-accessible
    STATUS      current 
    DESCRIPTION
        "" 
    INDEX       { entityIndex } 
    ::=  { thresholdOduTcmCTable  1  }

ThresholdOduTcmCEntry ::=  SEQUENCE
  { thresholdOduTcmCBESHighThres15min Unsigned32,
    thresholdOduTcmCESHighThres1day Unsigned32,
    thresholdOduTcmCSESHighThres15min Unsigned32,
    thresholdOduTcmCSESHighThres1day Unsigned32,
    thresholdOduTcmCOduTcmCBbeHighThres15min Unsigned32,
    thresholdOduTcmCOduTcmCBbeHighThres1day Unsigned32,
    thresholdOduTcmCUASHighThres15min Unsigned32,
    thresholdOduTcmCUASHighThres1day Unsigned32 }


  
thresholdOduTcmCBESHighThres15min OBJECT-TYPE
    SYNTAX      Unsigned32 (0..900)
    MAX-ACCESS  read-write
    STATUS      current 
    DESCRIPTION
        "Errored Seconds ODU Tandem Connection Monitoring" 
    ::=  { thresholdOduTcmCEntry 1 }

thresholdOduTcmCESHighThres1day OBJECT-TYPE
    SYNTAX      Unsigned32 (0..86400)
    MAX-ACCESS  read-write
    STATUS      current 
    DESCRIPTION
        "Errored Seconds ODU Tandem Connection Monitoring" 
    ::=  { thresholdOduTcmCEntry 2 }

thresholdOduTcmCSESHighThres15min OBJECT-TYPE
    SYNTAX      Unsigned32 (0..900)
    MAX-ACCESS  read-write
    STATUS      current 
    DESCRIPTION
        "Severely Errored Seconds ODU Tandem Connection Monitoring" 
    ::=  { thresholdOduTcmCEntry 3 }

thresholdOduTcmCSESHighThres1day OBJECT-TYPE
    SYNTAX      Unsigned32 (0..86400)
    MAX-ACCESS  read-write
    STATUS      current 
    DESCRIPTION
        "Severely Errored Seconds ODU Tandem Connection Monitoring" 
    ::=  { thresholdOduTcmCEntry 4 }

thresholdOduTcmCOduTcmCBbeHighThres15min OBJECT-TYPE
    SYNTAX      Unsigned32 (0..900)
    MAX-ACCESS  read-write
    STATUS      current 
    DESCRIPTION
        "Threshold of instance C: Background Block Erros ODU Tandem Connection Monitoring" 
    ::=  { thresholdOduTcmCEntry 5 }

thresholdOduTcmCOduTcmCBbeHighThres1day OBJECT-TYPE
    SYNTAX      Unsigned32 (0..86400)
    MAX-ACCESS  read-write
    STATUS      current 
    DESCRIPTION
        "Threshold of instance C: Background Block Erros ODU Tandem Connection Monitoring" 
    ::=  { thresholdOduTcmCEntry 6 }

thresholdOduTcmCUASHighThres15min OBJECT-TYPE
    SYNTAX      Unsigned32 (0..900)
    MAX-ACCESS  read-write
    STATUS      current 
    DESCRIPTION
        "Unavailable Seconds ODU Tandem Connection Monitoring" 
    ::=  { thresholdOduTcmCEntry 7 }

thresholdOduTcmCUASHighThres1day OBJECT-TYPE
    SYNTAX      Unsigned32 (0..86400)
    MAX-ACCESS  read-write
    STATUS      current 
    DESCRIPTION
        "Unavailable Seconds ODU Tandem Connection Monitoring" 
    ::=  { thresholdOduTcmCEntry 8 }

thresholdPhysConvHighSpeedTable OBJECT-TYPE
    SYNTAX      SEQUENCE OF ThresholdPhysConvHighSpeedEntry
    MAX-ACCESS  not-accessible
    STATUS      current 
    DESCRIPTION
        "" 
    ::=  { performanceAdmin 20 }

thresholdPhysConvHighSpeedEntry OBJECT-TYPE
    SYNTAX      ThresholdPhysConvHighSpeedEntry
    MAX-ACCESS  not-accessible
    STATUS      current 
    DESCRIPTION
        "" 
    INDEX       { entityIndex } 
    ::=  { thresholdPhysConvHighSpeedTable  1  }

ThresholdPhysConvHighSpeedEntry ::=  SEQUENCE
  { thresholdPhysConvHighSpeedESHighThres15min Unsigned32,
    thresholdPhysConvHighSpeedESHighThres1day Unsigned32,
    thresholdPhysConvHighSpeedCVHighThres15min Unsigned32,
    thresholdPhysConvHighSpeedCVHighThres1day Unsigned32,
    thresholdPhysConvHighSpeedSEHighThres15min Unsigned32,
    thresholdPhysConvHighSpeedSEHighThres1day Unsigned32 }


  
thresholdPhysConvHighSpeedESHighThres15min OBJECT-TYPE
    SYNTAX      Unsigned32 (0..900)
    MAX-ACCESS  read-write
    STATUS      current 
    DESCRIPTION
        "Errored Seconds Physical Coding Layer" 
    ::=  { thresholdPhysConvHighSpeedEntry 1 }

thresholdPhysConvHighSpeedESHighThres1day OBJECT-TYPE
    SYNTAX      Unsigned32 (0..89400)
    MAX-ACCESS  read-write
    STATUS      current 
    DESCRIPTION
        "Errored Seconds Physical Coding Layer" 
    ::=  { thresholdPhysConvHighSpeedEntry 2 }

thresholdPhysConvHighSpeedCVHighThres15min OBJECT-TYPE
    SYNTAX      Unsigned32 (0..900)
    MAX-ACCESS  read-write
    STATUS      current 
    DESCRIPTION
        "Threshold 15 Min: Coding Violations Physical Coding Layer" 
    ::=  { thresholdPhysConvHighSpeedEntry 3 }

thresholdPhysConvHighSpeedCVHighThres1day OBJECT-TYPE
    SYNTAX      Unsigned32 (0..86400)
    MAX-ACCESS  read-write
    STATUS      current 
    DESCRIPTION
        "Threshold 1 Day: Coding Violations - Physical Coding Layer" 
    ::=  { thresholdPhysConvHighSpeedEntry 4 }

thresholdPhysConvHighSpeedSEHighThres15min OBJECT-TYPE
    SYNTAX      Unsigned32 (0..900)
    MAX-ACCESS  read-write
    STATUS      current 
    DESCRIPTION
        "Sync Header Errors Physical Coding Layer" 
    ::=  { thresholdPhysConvHighSpeedEntry 5 }

thresholdPhysConvHighSpeedSEHighThres1day OBJECT-TYPE
    SYNTAX      Unsigned32 (0..86400)
    MAX-ACCESS  read-write
    STATUS      current 
    DESCRIPTION
        "Sync Header Errors Physical Coding Layer" 
    ::=  { thresholdPhysConvHighSpeedEntry 6 }

currentOtu15minTable OBJECT-TYPE
    SYNTAX      SEQUENCE OF CurrentOtu15minEntry
    MAX-ACCESS  not-accessible
    STATUS      current 
    DESCRIPTION
        "" 
    ::=  { performanceMonitoring 1 }

currentOtu15minEntry OBJECT-TYPE
    SYNTAX      CurrentOtu15minEntry
    MAX-ACCESS  not-accessible
    STATUS      current 
    DESCRIPTION
        "" 
    INDEX       { entityIndex } 
    ::=  { currentOtu15minTable  1  }

CurrentOtu15minEntry ::=  SEQUENCE
  { currentOtu15minES Unsigned32,
    currentOtu15minSES Unsigned32,
    currentOtu15minBbe Counter64String,
    currentOtu15minUAS Unsigned32,
    currentOtu15minElapsedTime Integer32 }


  
currentOtu15minES OBJECT-TYPE
    SYNTAX      Unsigned32
    MAX-ACCESS  read-only
    STATUS      current 
    DESCRIPTION
        "Errored Seconds OTU Section Monitoring" 
    ::=  { currentOtu15minEntry 1 }

currentOtu15minSES OBJECT-TYPE
    SYNTAX      Unsigned32
    MAX-ACCESS  read-only
    STATUS      current 
    DESCRIPTION
        "Severely Errored Seconds OTU Section Monitoring" 
    ::=  { currentOtu15minEntry 2 }

currentOtu15minBbe OBJECT-TYPE
    SYNTAX      Counter64String
    MAX-ACCESS  read-only
    STATUS      current 
    DESCRIPTION
        "Background Block Errors OTU Section Monitoring" 
    ::=  { currentOtu15minEntry 3 }

currentOtu15minUAS OBJECT-TYPE
    SYNTAX      Unsigned32
    MAX-ACCESS  read-only
    STATUS      current 
    DESCRIPTION
        "Unavailable Seconds OTU Path Monitoring" 
    ::=  { currentOtu15minEntry 4 }

currentOtu15minElapsedTime OBJECT-TYPE
    SYNTAX      Integer32 (0..9000)
    MAX-ACCESS  read-only
    STATUS      current 
    DESCRIPTION
        "Elapsed 15Min" 
    ::=  { currentOtu15minEntry 5 }

currentOtu1dayTable OBJECT-TYPE
    SYNTAX      SEQUENCE OF CurrentOtu1dayEntry
    MAX-ACCESS  not-accessible
    STATUS      current 
    DESCRIPTION
        "" 
    ::=  { performanceMonitoring 2 }

currentOtu1dayEntry OBJECT-TYPE
    SYNTAX      CurrentOtu1dayEntry
    MAX-ACCESS  not-accessible
    STATUS      current 
    DESCRIPTION
        "" 
    INDEX       { entityIndex } 
    ::=  { currentOtu1dayTable  1  }

CurrentOtu1dayEntry ::=  SEQUENCE
  { currentOtu1dayES Unsigned32,
    currentOtu1daySES Unsigned32,
    currentOtu1dayBbe Counter64String,
    currentOtu1dayUAS Unsigned32,
    currentOtu1dayElapsedTime Integer32 }


  
currentOtu1dayES OBJECT-TYPE
    SYNTAX      Unsigned32
    MAX-ACCESS  read-only
    STATUS      current 
    DESCRIPTION
        "Errored Seconds OTU Section Monitoring" 
    ::=  { currentOtu1dayEntry 1 }

currentOtu1daySES OBJECT-TYPE
    SYNTAX      Unsigned32
    MAX-ACCESS  read-only
    STATUS      current 
    DESCRIPTION
        "Severely Errored Seconds OTU Section Monitoring" 
    ::=  { currentOtu1dayEntry 2 }

currentOtu1dayBbe OBJECT-TYPE
    SYNTAX      Counter64String
    MAX-ACCESS  read-only
    STATUS      current 
    DESCRIPTION
        "Background Block Errors OTU Section Monitoring" 
    ::=  { currentOtu1dayEntry 3 }

currentOtu1dayUAS OBJECT-TYPE
    SYNTAX      Unsigned32
    MAX-ACCESS  read-only
    STATUS      current 
    DESCRIPTION
        "Unavailable Seconds OTU Path Monitoring" 
    ::=  { currentOtu1dayEntry 4 }

currentOtu1dayElapsedTime OBJECT-TYPE
    SYNTAX      Integer32 (0..86400)
    MAX-ACCESS  read-only
    STATUS      current 
    DESCRIPTION
        "Elapsed 1Day" 
    ::=  { currentOtu1dayEntry 5 }

intervalOtu15minTable OBJECT-TYPE
    SYNTAX      SEQUENCE OF IntervalOtu15minEntry
    MAX-ACCESS  not-accessible
    STATUS      current 
    DESCRIPTION
        "" 
    ::=  { performanceMonitoring 3 }

intervalOtu15minEntry OBJECT-TYPE
    SYNTAX      IntervalOtu15minEntry
    MAX-ACCESS  not-accessible
    STATUS      current 
    DESCRIPTION
        "" 
    INDEX       { entityIndex,intervalOtu15minNumber } 
    ::=  { intervalOtu15minTable  1  }

IntervalOtu15minEntry ::=  SEQUENCE
  { intervalOtu15minNumber Integer32,
    intervalOtu15minES Unsigned32,
    intervalOtu15minSES Unsigned32,
    intervalOtu15minBbe Counter64String,
    intervalOtu15minUAS Unsigned32,
    intervalOtu15minValidFlag TruthValue,
    intervalOtu15minTimeStamp DateAndTime }


  
intervalOtu15minNumber OBJECT-TYPE
    SYNTAX      Integer32 (1..96)
    MAX-ACCESS  not-accessible
    STATUS      current 
    DESCRIPTION
        "Number 15min" 
    ::=  { intervalOtu15minEntry 1 }

intervalOtu15minES OBJECT-TYPE
    SYNTAX      Unsigned32
    MAX-ACCESS  read-only
    STATUS      current 
    DESCRIPTION
        "Errored Seconds OTU Section Monitoring" 
    ::=  { intervalOtu15minEntry 2 }

intervalOtu15minSES OBJECT-TYPE
    SYNTAX      Unsigned32
    MAX-ACCESS  read-only
    STATUS      current 
    DESCRIPTION
        "Severely Errored Seconds OTU Section Monitoring" 
    ::=  { intervalOtu15minEntry 3 }

intervalOtu15minBbe OBJECT-TYPE
    SYNTAX      Counter64String
    MAX-ACCESS  read-only
    STATUS      current 
    DESCRIPTION
        "Background Block Errors OTU Section Monitoring" 
    ::=  { intervalOtu15minEntry 4 }

intervalOtu15minUAS OBJECT-TYPE
    SYNTAX      Unsigned32
    MAX-ACCESS  read-only
    STATUS      current 
    DESCRIPTION
        "Unavailable Seconds OTU Path Monitoring" 
    ::=  { intervalOtu15minEntry 5 }

intervalOtu15minValidFlag OBJECT-TYPE
    SYNTAX      TruthValue
    MAX-ACCESS  read-only
    STATUS      current 
    DESCRIPTION
        "" 
    ::=  { intervalOtu15minEntry 6 }

intervalOtu15minTimeStamp OBJECT-TYPE
    SYNTAX      DateAndTime
    MAX-ACCESS  read-only
    STATUS      current 
    DESCRIPTION
        "Timestamp" 
    ::=  { intervalOtu15minEntry 7 }

intervalOtu1dayTable OBJECT-TYPE
    SYNTAX      SEQUENCE OF IntervalOtu1dayEntry
    MAX-ACCESS  not-accessible
    STATUS      current 
    DESCRIPTION
        "" 
    ::=  { performanceMonitoring 4 }

intervalOtu1dayEntry OBJECT-TYPE
    SYNTAX      IntervalOtu1dayEntry
    MAX-ACCESS  not-accessible
    STATUS      current 
    DESCRIPTION
        "" 
    INDEX       { entityIndex,intervalOtu1dayNumber } 
    ::=  { intervalOtu1dayTable  1  }

IntervalOtu1dayEntry ::=  SEQUENCE
  { intervalOtu1dayNumber Integer32,
    intervalOtu1dayES Unsigned32,
    intervalOtu1daySES Unsigned32,
    intervalOtu1dayBbe Counter64String,
    intervalOtu1dayUAS Unsigned32,
    intervalOtu1dayValidFlag TruthValue,
    intervalOtu1dayTimeStamp DateAndTime }


  
intervalOtu1dayNumber OBJECT-TYPE
    SYNTAX      Integer32 (1..31)
    MAX-ACCESS  not-accessible
    STATUS      current 
    DESCRIPTION
        "Number 1day" 
    ::=  { intervalOtu1dayEntry 1 }

intervalOtu1dayES OBJECT-TYPE
    SYNTAX      Unsigned32
    MAX-ACCESS  read-only
    STATUS      current 
    DESCRIPTION
        "Errored Seconds OTU Section Monitoring" 
    ::=  { intervalOtu1dayEntry 2 }

intervalOtu1daySES OBJECT-TYPE
    SYNTAX      Unsigned32
    MAX-ACCESS  read-only
    STATUS      current 
    DESCRIPTION
        "Severely Errored Seconds OTU Section Monitoring" 
    ::=  { intervalOtu1dayEntry 3 }

intervalOtu1dayBbe OBJECT-TYPE
    SYNTAX      Counter64String
    MAX-ACCESS  read-only
    STATUS      current 
    DESCRIPTION
        "Background Block Errors OTU Section Monitoring" 
    ::=  { intervalOtu1dayEntry 4 }

intervalOtu1dayUAS OBJECT-TYPE
    SYNTAX      Unsigned32
    MAX-ACCESS  read-only
    STATUS      current 
    DESCRIPTION
        "Unavailable Seconds OTU Path Monitoring" 
    ::=  { intervalOtu1dayEntry 5 }

intervalOtu1dayValidFlag OBJECT-TYPE
    SYNTAX      TruthValue
    MAX-ACCESS  read-only
    STATUS      current 
    DESCRIPTION
        "" 
    ::=  { intervalOtu1dayEntry 6 }

intervalOtu1dayTimeStamp OBJECT-TYPE
    SYNTAX      DateAndTime
    MAX-ACCESS  read-only
    STATUS      current 
    DESCRIPTION
        "Timestamp" 
    ::=  { intervalOtu1dayEntry 7 }

currentOdu15minTable OBJECT-TYPE
    SYNTAX      SEQUENCE OF CurrentOdu15minEntry
    MAX-ACCESS  not-accessible
    STATUS      current 
    DESCRIPTION
        "" 
    ::=  { performanceMonitoring 5 }

currentOdu15minEntry OBJECT-TYPE
    SYNTAX      CurrentOdu15minEntry
    MAX-ACCESS  not-accessible
    STATUS      current 
    DESCRIPTION
        "" 
    INDEX       { entityIndex } 
    ::=  { currentOdu15minTable  1  }

CurrentOdu15minEntry ::=  SEQUENCE
  { currentOdu15minES Unsigned32,
    currentOdu15minSES Unsigned32,
    currentOdu15minBbe Counter64String,
    currentOdu15minUAS Unsigned32,
    currentOdu15minElapsedTime Integer32 }


  
currentOdu15minES OBJECT-TYPE
    SYNTAX      Unsigned32
    MAX-ACCESS  read-only
    STATUS      current 
    DESCRIPTION
        "Errored Seconds ODU Path Monitoring" 
    ::=  { currentOdu15minEntry 1 }

currentOdu15minSES OBJECT-TYPE
    SYNTAX      Unsigned32
    MAX-ACCESS  read-only
    STATUS      current 
    DESCRIPTION
        "Severely Errored Seconds ODU Path Monitoring" 
    ::=  { currentOdu15minEntry 2 }

currentOdu15minBbe OBJECT-TYPE
    SYNTAX      Counter64String
    MAX-ACCESS  read-only
    STATUS      current 
    DESCRIPTION
        "Background Block Erros ODU Path Monitoring" 
    ::=  { currentOdu15minEntry 3 }

currentOdu15minUAS OBJECT-TYPE
    SYNTAX      Unsigned32
    MAX-ACCESS  read-only
    STATUS      current 
    DESCRIPTION
        "Unavailable Seconds ODU Path Monitoring" 
    ::=  { currentOdu15minEntry 4 }

currentOdu15minElapsedTime OBJECT-TYPE
    SYNTAX      Integer32 (0..9000)
    MAX-ACCESS  read-only
    STATUS      current 
    DESCRIPTION
        "Elapsed 15Min" 
    ::=  { currentOdu15minEntry 5 }

currentOdu1dayTable OBJECT-TYPE
    SYNTAX      SEQUENCE OF CurrentOdu1dayEntry
    MAX-ACCESS  not-accessible
    STATUS      current 
    DESCRIPTION
        "" 
    ::=  { performanceMonitoring 6 }

currentOdu1dayEntry OBJECT-TYPE
    SYNTAX      CurrentOdu1dayEntry
    MAX-ACCESS  not-accessible
    STATUS      current 
    DESCRIPTION
        "" 
    INDEX       { entityIndex } 
    ::=  { currentOdu1dayTable  1  }

CurrentOdu1dayEntry ::=  SEQUENCE
  { currentOdu1dayES Unsigned32,
    currentOdu1daySES Unsigned32,
    currentOdu1dayBbe Counter64String,
    currentOdu1dayUAS Unsigned32,
    currentOdu1dayElapsedTime Integer32 }


  
currentOdu1dayES OBJECT-TYPE
    SYNTAX      Unsigned32
    MAX-ACCESS  read-only
    STATUS      current 
    DESCRIPTION
        "Errored Seconds ODU Path Monitoring" 
    ::=  { currentOdu1dayEntry 1 }

currentOdu1daySES OBJECT-TYPE
    SYNTAX      Unsigned32
    MAX-ACCESS  read-only
    STATUS      current 
    DESCRIPTION
        "Severely Errored Seconds ODU Path Monitoring" 
    ::=  { currentOdu1dayEntry 2 }

currentOdu1dayBbe OBJECT-TYPE
    SYNTAX      Counter64String
    MAX-ACCESS  read-only
    STATUS      current 
    DESCRIPTION
        "Background Block Erros ODU Path Monitoring" 
    ::=  { currentOdu1dayEntry 3 }

currentOdu1dayUAS OBJECT-TYPE
    SYNTAX      Unsigned32
    MAX-ACCESS  read-only
    STATUS      current 
    DESCRIPTION
        "Unavailable Seconds ODU Path Monitoring" 
    ::=  { currentOdu1dayEntry 4 }

currentOdu1dayElapsedTime OBJECT-TYPE
    SYNTAX      Integer32 (0..86400)
    MAX-ACCESS  read-only
    STATUS      current 
    DESCRIPTION
        "Elapsed 1Day" 
    ::=  { currentOdu1dayEntry 5 }

intervalOdu15minTable OBJECT-TYPE
    SYNTAX      SEQUENCE OF IntervalOdu15minEntry
    MAX-ACCESS  not-accessible
    STATUS      current 
    DESCRIPTION
        "" 
    ::=  { performanceMonitoring 7 }

intervalOdu15minEntry OBJECT-TYPE
    SYNTAX      IntervalOdu15minEntry
    MAX-ACCESS  not-accessible
    STATUS      current 
    DESCRIPTION
        "" 
    INDEX       { entityIndex,intervalOdu15minNumber } 
    ::=  { intervalOdu15minTable  1  }

IntervalOdu15minEntry ::=  SEQUENCE
  { intervalOdu15minNumber Integer32,
    intervalOdu15minES Unsigned32,
    intervalOdu15minSES Unsigned32,
    intervalOdu15minBbe Counter64String,
    intervalOdu15minUAS Unsigned32,
    intervalOdu15minValidFlag TruthValue,
    intervalOdu15minTimeStamp DateAndTime }


  
intervalOdu15minNumber OBJECT-TYPE
    SYNTAX      Integer32 (1..96)
    MAX-ACCESS  not-accessible
    STATUS      current 
    DESCRIPTION
        "Number 15min" 
    ::=  { intervalOdu15minEntry 1 }

intervalOdu15minES OBJECT-TYPE
    SYNTAX      Unsigned32
    MAX-ACCESS  read-only
    STATUS      current 
    DESCRIPTION
        "Errored Seconds ODU Path Monitoring" 
    ::=  { intervalOdu15minEntry 2 }

intervalOdu15minSES OBJECT-TYPE
    SYNTAX      Unsigned32
    MAX-ACCESS  read-only
    STATUS      current 
    DESCRIPTION
        "Severely Errored Seconds ODU Path Monitoring" 
    ::=  { intervalOdu15minEntry 3 }

intervalOdu15minBbe OBJECT-TYPE
    SYNTAX      Counter64String
    MAX-ACCESS  read-only
    STATUS      current 
    DESCRIPTION
        "Background Block Erros ODU Path Monitoring" 
    ::=  { intervalOdu15minEntry 4 }

intervalOdu15minUAS OBJECT-TYPE
    SYNTAX      Unsigned32
    MAX-ACCESS  read-only
    STATUS      current 
    DESCRIPTION
        "Unavailable Seconds ODU Path Monitoring" 
    ::=  { intervalOdu15minEntry 5 }

intervalOdu15minValidFlag OBJECT-TYPE
    SYNTAX      TruthValue
    MAX-ACCESS  read-only
    STATUS      current 
    DESCRIPTION
        "" 
    ::=  { intervalOdu15minEntry 6 }

intervalOdu15minTimeStamp OBJECT-TYPE
    SYNTAX      DateAndTime
    MAX-ACCESS  read-only
    STATUS      current 
    DESCRIPTION
        "Timestamp" 
    ::=  { intervalOdu15minEntry 7 }

intervalOdu1dayTable OBJECT-TYPE
    SYNTAX      SEQUENCE OF IntervalOdu1dayEntry
    MAX-ACCESS  not-accessible
    STATUS      current 
    DESCRIPTION
        "" 
    ::=  { performanceMonitoring 8 }

intervalOdu1dayEntry OBJECT-TYPE
    SYNTAX      IntervalOdu1dayEntry
    MAX-ACCESS  not-accessible
    STATUS      current 
    DESCRIPTION
        "" 
    INDEX       { entityIndex,intervalOdu1dayNumber } 
    ::=  { intervalOdu1dayTable  1  }

IntervalOdu1dayEntry ::=  SEQUENCE
  { intervalOdu1dayNumber Integer32,
    intervalOdu1dayES Unsigned32,
    intervalOdu1daySES Unsigned32,
    intervalOdu1dayBbe Counter64String,
    intervalOdu1dayUAS Unsigned32,
    intervalOdu1dayValidFlag TruthValue,
    intervalOdu1dayTimeStamp DateAndTime }


  
intervalOdu1dayNumber OBJECT-TYPE
    SYNTAX      Integer32 (1..31)
    MAX-ACCESS  not-accessible
    STATUS      current 
    DESCRIPTION
        "Number 1day" 
    ::=  { intervalOdu1dayEntry 1 }

intervalOdu1dayES OBJECT-TYPE
    SYNTAX      Unsigned32
    MAX-ACCESS  read-only
    STATUS      current 
    DESCRIPTION
        "Errored Seconds ODU Path Monitoring" 
    ::=  { intervalOdu1dayEntry 2 }

intervalOdu1daySES OBJECT-TYPE
    SYNTAX      Unsigned32
    MAX-ACCESS  read-only
    STATUS      current 
    DESCRIPTION
        "Severely Errored Seconds ODU Path Monitoring" 
    ::=  { intervalOdu1dayEntry 3 }

intervalOdu1dayBbe OBJECT-TYPE
    SYNTAX      Counter64String
    MAX-ACCESS  read-only
    STATUS      current 
    DESCRIPTION
        "Background Block Erros ODU Path Monitoring" 
    ::=  { intervalOdu1dayEntry 4 }

intervalOdu1dayUAS OBJECT-TYPE
    SYNTAX      Unsigned32
    MAX-ACCESS  read-only
    STATUS      current 
    DESCRIPTION
        "Unavailable Seconds ODU Path Monitoring" 
    ::=  { intervalOdu1dayEntry 5 }

intervalOdu1dayValidFlag OBJECT-TYPE
    SYNTAX      TruthValue
    MAX-ACCESS  read-only
    STATUS      current 
    DESCRIPTION
        "" 
    ::=  { intervalOdu1dayEntry 6 }

intervalOdu1dayTimeStamp OBJECT-TYPE
    SYNTAX      DateAndTime
    MAX-ACCESS  read-only
    STATUS      current 
    DESCRIPTION
        "Timestamp" 
    ::=  { intervalOdu1dayEntry 7 }

currentOduTcmA15minTable OBJECT-TYPE
    SYNTAX      SEQUENCE OF CurrentOduTcmA15minEntry
    MAX-ACCESS  not-accessible
    STATUS      current 
    DESCRIPTION
        "" 
    ::=  { performanceMonitoring 9 }

currentOduTcmA15minEntry OBJECT-TYPE
    SYNTAX      CurrentOduTcmA15minEntry
    MAX-ACCESS  not-accessible
    STATUS      current 
    DESCRIPTION
        "" 
    INDEX       { entityIndex } 
    ::=  { currentOduTcmA15minTable  1  }

CurrentOduTcmA15minEntry ::=  SEQUENCE
  { currentOduTcmA15minES Unsigned32,
    currentOduTcmA15minSES Unsigned32,
    currentOduTcmA15minBbe Counter64String,
    currentOduTcmA15minUAS Unsigned32,
    currentOduTcmA15minElapsedTime Integer32 }


  
currentOduTcmA15minES OBJECT-TYPE
    SYNTAX      Unsigned32
    MAX-ACCESS  read-only
    STATUS      current 
    DESCRIPTION
        "Errored Seconds ODU Tandem Connection Monitoring - Instance A" 
    ::=  { currentOduTcmA15minEntry 1 }

currentOduTcmA15minSES OBJECT-TYPE
    SYNTAX      Unsigned32
    MAX-ACCESS  read-only
    STATUS      current 
    DESCRIPTION
        "Severely Errored Seconds ODU Tandem Connection Monitoring - Instance A" 
    ::=  { currentOduTcmA15minEntry 2 }

currentOduTcmA15minBbe OBJECT-TYPE
    SYNTAX      Counter64String
    MAX-ACCESS  read-only
    STATUS      current 
    DESCRIPTION
        "Background Block Erros ODU Tandem Connection Monitoring Instance A" 
    ::=  { currentOduTcmA15minEntry 3 }

currentOduTcmA15minUAS OBJECT-TYPE
    SYNTAX      Unsigned32
    MAX-ACCESS  read-only
    STATUS      current 
    DESCRIPTION
        "Unavailable Seconds ODU Tandem Connection Monitoring - Instance A" 
    ::=  { currentOduTcmA15minEntry 4 }

currentOduTcmA15minElapsedTime OBJECT-TYPE
    SYNTAX      Integer32 (0..9000)
    MAX-ACCESS  read-only
    STATUS      current 
    DESCRIPTION
        "Elapsed 15Min" 
    ::=  { currentOduTcmA15minEntry 5 }

currentOduTcmA1dayTable OBJECT-TYPE
    SYNTAX      SEQUENCE OF CurrentOduTcmA1dayEntry
    MAX-ACCESS  not-accessible
    STATUS      current 
    DESCRIPTION
        "" 
    ::=  { performanceMonitoring 10 }

currentOduTcmA1dayEntry OBJECT-TYPE
    SYNTAX      CurrentOduTcmA1dayEntry
    MAX-ACCESS  not-accessible
    STATUS      current 
    DESCRIPTION
        "" 
    INDEX       { entityIndex } 
    ::=  { currentOduTcmA1dayTable  1  }

CurrentOduTcmA1dayEntry ::=  SEQUENCE
  { currentOduTcmA1dayES Unsigned32,
    currentOduTcmA1daySES Unsigned32,
    currentOduTcmA1dayBbe Counter64String,
    currentOduTcmA1dayUAS Unsigned32,
    currentOduTcmA1dayElapsedTime Integer32 }


  
currentOduTcmA1dayES OBJECT-TYPE
    SYNTAX      Unsigned32
    MAX-ACCESS  read-only
    STATUS      current 
    DESCRIPTION
        "Errored Seconds ODU Tandem Connection Monitoring - Instance A" 
    ::=  { currentOduTcmA1dayEntry 1 }

currentOduTcmA1daySES OBJECT-TYPE
    SYNTAX      Unsigned32
    MAX-ACCESS  read-only
    STATUS      current 
    DESCRIPTION
        "Severely Errored Seconds ODU Tandem Connection Monitoring - Instance A" 
    ::=  { currentOduTcmA1dayEntry 2 }

currentOduTcmA1dayBbe OBJECT-TYPE
    SYNTAX      Counter64String
    MAX-ACCESS  read-only
    STATUS      current 
    DESCRIPTION
        "Background Block Erros ODU Tandem Connection Monitoring Instance A" 
    ::=  { currentOduTcmA1dayEntry 3 }

currentOduTcmA1dayUAS OBJECT-TYPE
    SYNTAX      Unsigned32
    MAX-ACCESS  read-only
    STATUS      current 
    DESCRIPTION
        "Unavailable Seconds ODU Tandem Connection Monitoring - Instance A" 
    ::=  { currentOduTcmA1dayEntry 4 }

currentOduTcmA1dayElapsedTime OBJECT-TYPE
    SYNTAX      Integer32 (0..86400)
    MAX-ACCESS  read-only
    STATUS      current 
    DESCRIPTION
        "Elapsed 1Day" 
    ::=  { currentOduTcmA1dayEntry 5 }

intervalOduTcmA15minTable OBJECT-TYPE
    SYNTAX      SEQUENCE OF IntervalOduTcmA15minEntry
    MAX-ACCESS  not-accessible
    STATUS      current 
    DESCRIPTION
        "" 
    ::=  { performanceMonitoring 11 }

intervalOduTcmA15minEntry OBJECT-TYPE
    SYNTAX      IntervalOduTcmA15minEntry
    MAX-ACCESS  not-accessible
    STATUS      current 
    DESCRIPTION
        "" 
    INDEX       { entityIndex,intervalOduTcmA15minNumber } 
    ::=  { intervalOduTcmA15minTable  1  }

IntervalOduTcmA15minEntry ::=  SEQUENCE
  { intervalOduTcmA15minNumber Integer32,
    intervalOduTcmA15minES Unsigned32,
    intervalOduTcmA15minSES Unsigned32,
    intervalOduTcmA15minBbe Counter64String,
    intervalOduTcmA15minUAS Unsigned32,
    intervalOduTcmA15minValidFlag TruthValue,
    intervalOduTcmA15minTimeStamp DateAndTime }


  
intervalOduTcmA15minNumber OBJECT-TYPE
    SYNTAX      Integer32 (1..96)
    MAX-ACCESS  not-accessible
    STATUS      current 
    DESCRIPTION
        "Number 15min" 
    ::=  { intervalOduTcmA15minEntry 1 }

intervalOduTcmA15minES OBJECT-TYPE
    SYNTAX      Unsigned32
    MAX-ACCESS  read-only
    STATUS      current 
    DESCRIPTION
        "Errored Seconds ODU Tandem Connection Monitoring - Instance A" 
    ::=  { intervalOduTcmA15minEntry 2 }

intervalOduTcmA15minSES OBJECT-TYPE
    SYNTAX      Unsigned32
    MAX-ACCESS  read-only
    STATUS      current 
    DESCRIPTION
        "Severely Errored Seconds ODU Tandem Connection Monitoring - Instance A" 
    ::=  { intervalOduTcmA15minEntry 3 }

intervalOduTcmA15minBbe OBJECT-TYPE
    SYNTAX      Counter64String
    MAX-ACCESS  read-only
    STATUS      current 
    DESCRIPTION
        "Background Block Erros ODU Tandem Connection Monitoring Instance A" 
    ::=  { intervalOduTcmA15minEntry 4 }

intervalOduTcmA15minUAS OBJECT-TYPE
    SYNTAX      Unsigned32
    MAX-ACCESS  read-only
    STATUS      current 
    DESCRIPTION
        "Unavailable Seconds ODU Tandem Connection Monitoring - Instance A" 
    ::=  { intervalOduTcmA15minEntry 5 }

intervalOduTcmA15minValidFlag OBJECT-TYPE
    SYNTAX      TruthValue
    MAX-ACCESS  read-only
    STATUS      current 
    DESCRIPTION
        "" 
    ::=  { intervalOduTcmA15minEntry 6 }

intervalOduTcmA15minTimeStamp OBJECT-TYPE
    SYNTAX      DateAndTime
    MAX-ACCESS  read-only
    STATUS      current 
    DESCRIPTION
        "Timestamp" 
    ::=  { intervalOduTcmA15minEntry 7 }

intervalOduTcmA1dayTable OBJECT-TYPE
    SYNTAX      SEQUENCE OF IntervalOduTcmA1dayEntry
    MAX-ACCESS  not-accessible
    STATUS      current 
    DESCRIPTION
        "" 
    ::=  { performanceMonitoring 12 }

intervalOduTcmA1dayEntry OBJECT-TYPE
    SYNTAX      IntervalOduTcmA1dayEntry
    MAX-ACCESS  not-accessible
    STATUS      current 
    DESCRIPTION
        "" 
    INDEX       { entityIndex,intervalOduTcmA1dayNumber } 
    ::=  { intervalOduTcmA1dayTable  1  }

IntervalOduTcmA1dayEntry ::=  SEQUENCE
  { intervalOduTcmA1dayNumber Integer32,
    intervalOduTcmA1dayES Unsigned32,
    intervalOduTcmA1daySES Unsigned32,
    intervalOduTcmA1dayBbe Counter64String,
    intervalOduTcmA1dayUAS Unsigned32,
    intervalOduTcmA1dayValidFlag TruthValue,
    intervalOduTcmA1dayTimeStamp DateAndTime }


  
intervalOduTcmA1dayNumber OBJECT-TYPE
    SYNTAX      Integer32 (1..31)
    MAX-ACCESS  not-accessible
    STATUS      current 
    DESCRIPTION
        "Number 1day" 
    ::=  { intervalOduTcmA1dayEntry 1 }

intervalOduTcmA1dayES OBJECT-TYPE
    SYNTAX      Unsigned32
    MAX-ACCESS  read-only
    STATUS      current 
    DESCRIPTION
        "Errored Seconds ODU Tandem Connection Monitoring - Instance A" 
    ::=  { intervalOduTcmA1dayEntry 2 }

intervalOduTcmA1daySES OBJECT-TYPE
    SYNTAX      Unsigned32
    MAX-ACCESS  read-only
    STATUS      current 
    DESCRIPTION
        "Severely Errored Seconds ODU Tandem Connection Monitoring - Instance A" 
    ::=  { intervalOduTcmA1dayEntry 3 }

intervalOduTcmA1dayBbe OBJECT-TYPE
    SYNTAX      Counter64String
    MAX-ACCESS  read-only
    STATUS      current 
    DESCRIPTION
        "Background Block Erros ODU Tandem Connection Monitoring Instance A" 
    ::=  { intervalOduTcmA1dayEntry 4 }

intervalOduTcmA1dayUAS OBJECT-TYPE
    SYNTAX      Unsigned32
    MAX-ACCESS  read-only
    STATUS      current 
    DESCRIPTION
        "Unavailable Seconds ODU Tandem Connection Monitoring - Instance A" 
    ::=  { intervalOduTcmA1dayEntry 5 }

intervalOduTcmA1dayValidFlag OBJECT-TYPE
    SYNTAX      TruthValue
    MAX-ACCESS  read-only
    STATUS      current 
    DESCRIPTION
        "" 
    ::=  { intervalOduTcmA1dayEntry 6 }

intervalOduTcmA1dayTimeStamp OBJECT-TYPE
    SYNTAX      DateAndTime
    MAX-ACCESS  read-only
    STATUS      current 
    DESCRIPTION
        "Timestamp" 
    ::=  { intervalOduTcmA1dayEntry 7 }

currentOduTcmB15minTable OBJECT-TYPE
    SYNTAX      SEQUENCE OF CurrentOduTcmB15minEntry
    MAX-ACCESS  not-accessible
    STATUS      current 
    DESCRIPTION
        "" 
    ::=  { performanceMonitoring 13 }

currentOduTcmB15minEntry OBJECT-TYPE
    SYNTAX      CurrentOduTcmB15minEntry
    MAX-ACCESS  not-accessible
    STATUS      current 
    DESCRIPTION
        "" 
    INDEX       { entityIndex } 
    ::=  { currentOduTcmB15minTable  1  }

CurrentOduTcmB15minEntry ::=  SEQUENCE
  { currentOduTcmB15minES Unsigned32,
    currentOduTcmB15minSES Unsigned32,
    currentOduTcmB15minBbe Counter64String,
    currentOduTcmB15minUAS Unsigned32,
    currentOduTcmB15minElapsedTime Integer32 }


  
currentOduTcmB15minES OBJECT-TYPE
    SYNTAX      Unsigned32
    MAX-ACCESS  read-only
    STATUS      current 
    DESCRIPTION
        "Errored Seconds ODU Tandem Connection Monitoring - Instance B" 
    ::=  { currentOduTcmB15minEntry 1 }

currentOduTcmB15minSES OBJECT-TYPE
    SYNTAX      Unsigned32
    MAX-ACCESS  read-only
    STATUS      current 
    DESCRIPTION
        "Severely Errored Seconds ODU Tandem Connection Monitoring - Instance B" 
    ::=  { currentOduTcmB15minEntry 2 }

currentOduTcmB15minBbe OBJECT-TYPE
    SYNTAX      Counter64String
    MAX-ACCESS  read-only
    STATUS      current 
    DESCRIPTION
        "Background Block Erros ODU Tandem Connection Monitoring - Instance B" 
    ::=  { currentOduTcmB15minEntry 3 }

currentOduTcmB15minUAS OBJECT-TYPE
    SYNTAX      Unsigned32
    MAX-ACCESS  read-only
    STATUS      current 
    DESCRIPTION
        "Unavailable Seconds ODU Tandem Connection Monitoring - Instance B" 
    ::=  { currentOduTcmB15minEntry 4 }

currentOduTcmB15minElapsedTime OBJECT-TYPE
    SYNTAX      Integer32 (0..9000)
    MAX-ACCESS  read-only
    STATUS      current 
    DESCRIPTION
        "Elapsed 15Min" 
    ::=  { currentOduTcmB15minEntry 5 }

currentOduTcmB1dayTable OBJECT-TYPE
    SYNTAX      SEQUENCE OF CurrentOduTcmB1dayEntry
    MAX-ACCESS  not-accessible
    STATUS      current 
    DESCRIPTION
        "" 
    ::=  { performanceMonitoring 14 }

currentOduTcmB1dayEntry OBJECT-TYPE
    SYNTAX      CurrentOduTcmB1dayEntry
    MAX-ACCESS  not-accessible
    STATUS      current 
    DESCRIPTION
        "" 
    INDEX       { entityIndex } 
    ::=  { currentOduTcmB1dayTable  1  }

CurrentOduTcmB1dayEntry ::=  SEQUENCE
  { currentOduTcmB1dayES Unsigned32,
    currentOduTcmB1daySES Unsigned32,
    currentOduTcmB1dayBbe Counter64String,
    currentOduTcmB1dayUAS Unsigned32,
    currentOduTcmB1dayElapsedTime Integer32 }


  
currentOduTcmB1dayES OBJECT-TYPE
    SYNTAX      Unsigned32
    MAX-ACCESS  read-only
    STATUS      current 
    DESCRIPTION
        "Errored Seconds ODU Tandem Connection Monitoring - Instance B" 
    ::=  { currentOduTcmB1dayEntry 1 }

currentOduTcmB1daySES OBJECT-TYPE
    SYNTAX      Unsigned32
    MAX-ACCESS  read-only
    STATUS      current 
    DESCRIPTION
        "Severely Errored Seconds ODU Tandem Connection Monitoring - Instance B" 
    ::=  { currentOduTcmB1dayEntry 2 }

currentOduTcmB1dayBbe OBJECT-TYPE
    SYNTAX      Counter64String
    MAX-ACCESS  read-only
    STATUS      current 
    DESCRIPTION
        "Background Block Erros ODU Tandem Connection Monitoring - Instance B" 
    ::=  { currentOduTcmB1dayEntry 3 }

currentOduTcmB1dayUAS OBJECT-TYPE
    SYNTAX      Unsigned32
    MAX-ACCESS  read-only
    STATUS      current 
    DESCRIPTION
        "Unavailable Seconds ODU Tandem Connection Monitoring - Instance B" 
    ::=  { currentOduTcmB1dayEntry 4 }

currentOduTcmB1dayElapsedTime OBJECT-TYPE
    SYNTAX      Integer32 (0..86400)
    MAX-ACCESS  read-only
    STATUS      current 
    DESCRIPTION
        "Elapsed 1Day" 
    ::=  { currentOduTcmB1dayEntry 5 }

intervalOduTcmB15minTable OBJECT-TYPE
    SYNTAX      SEQUENCE OF IntervalOduTcmB15minEntry
    MAX-ACCESS  not-accessible
    STATUS      current 
    DESCRIPTION
        "" 
    ::=  { performanceMonitoring 15 }

intervalOduTcmB15minEntry OBJECT-TYPE
    SYNTAX      IntervalOduTcmB15minEntry
    MAX-ACCESS  not-accessible
    STATUS      current 
    DESCRIPTION
        "" 
    INDEX       { entityIndex,intervalOduTcmB15minNumber } 
    ::=  { intervalOduTcmB15minTable  1  }

IntervalOduTcmB15minEntry ::=  SEQUENCE
  { intervalOduTcmB15minNumber Integer32,
    intervalOduTcmB15minES Unsigned32,
    intervalOduTcmB15minSES Unsigned32,
    intervalOduTcmB15minBbe Counter64String,
    intervalOduTcmB15minUAS Unsigned32,
    intervalOduTcmB15minValidFlag TruthValue,
    intervalOduTcmB15minTimeStamp DateAndTime }


  
intervalOduTcmB15minNumber OBJECT-TYPE
    SYNTAX      Integer32 (1..96)
    MAX-ACCESS  not-accessible
    STATUS      current 
    DESCRIPTION
        "Number 15min" 
    ::=  { intervalOduTcmB15minEntry 1 }

intervalOduTcmB15minES OBJECT-TYPE
    SYNTAX      Unsigned32
    MAX-ACCESS  read-only
    STATUS      current 
    DESCRIPTION
        "Errored Seconds ODU Tandem Connection Monitoring - Instance B" 
    ::=  { intervalOduTcmB15minEntry 2 }

intervalOduTcmB15minSES OBJECT-TYPE
    SYNTAX      Unsigned32
    MAX-ACCESS  read-only
    STATUS      current 
    DESCRIPTION
        "Severely Errored Seconds ODU Tandem Connection Monitoring - Instance B" 
    ::=  { intervalOduTcmB15minEntry 3 }

intervalOduTcmB15minBbe OBJECT-TYPE
    SYNTAX      Counter64String
    MAX-ACCESS  read-only
    STATUS      current 
    DESCRIPTION
        "Background Block Erros ODU Tandem Connection Monitoring - Instance B" 
    ::=  { intervalOduTcmB15minEntry 4 }

intervalOduTcmB15minUAS OBJECT-TYPE
    SYNTAX      Unsigned32
    MAX-ACCESS  read-only
    STATUS      current 
    DESCRIPTION
        "Unavailable Seconds ODU Tandem Connection Monitoring - Instance B" 
    ::=  { intervalOduTcmB15minEntry 5 }

intervalOduTcmB15minValidFlag OBJECT-TYPE
    SYNTAX      TruthValue
    MAX-ACCESS  read-only
    STATUS      current 
    DESCRIPTION
        "" 
    ::=  { intervalOduTcmB15minEntry 6 }

intervalOduTcmB15minTimeStamp OBJECT-TYPE
    SYNTAX      DateAndTime
    MAX-ACCESS  read-only
    STATUS      current 
    DESCRIPTION
        "Timestamp" 
    ::=  { intervalOduTcmB15minEntry 7 }

intervalOduTcmB1dayTable OBJECT-TYPE
    SYNTAX      SEQUENCE OF IntervalOduTcmB1dayEntry
    MAX-ACCESS  not-accessible
    STATUS      current 
    DESCRIPTION
        "" 
    ::=  { performanceMonitoring 16 }

intervalOduTcmB1dayEntry OBJECT-TYPE
    SYNTAX      IntervalOduTcmB1dayEntry
    MAX-ACCESS  not-accessible
    STATUS      current 
    DESCRIPTION
        "" 
    INDEX       { entityIndex,intervalOduTcmB1dayNumber } 
    ::=  { intervalOduTcmB1dayTable  1  }

IntervalOduTcmB1dayEntry ::=  SEQUENCE
  { intervalOduTcmB1dayNumber Integer32,
    intervalOduTcmB1dayES Unsigned32,
    intervalOduTcmB1daySES Unsigned32,
    intervalOduTcmB1dayBbe Counter64String,
    intervalOduTcmB1dayUAS Unsigned32,
    intervalOduTcmB1dayValidFlag TruthValue,
    intervalOduTcmB1dayTimeStamp DateAndTime }


  
intervalOduTcmB1dayNumber OBJECT-TYPE
    SYNTAX      Integer32 (1..31)
    MAX-ACCESS  not-accessible
    STATUS      current 
    DESCRIPTION
        "Number 1day" 
    ::=  { intervalOduTcmB1dayEntry 1 }

intervalOduTcmB1dayES OBJECT-TYPE
    SYNTAX      Unsigned32
    MAX-ACCESS  read-only
    STATUS      current 
    DESCRIPTION
        "Errored Seconds ODU Tandem Connection Monitoring - Instance B" 
    ::=  { intervalOduTcmB1dayEntry 2 }

intervalOduTcmB1daySES OBJECT-TYPE
    SYNTAX      Unsigned32
    MAX-ACCESS  read-only
    STATUS      current 
    DESCRIPTION
        "Severely Errored Seconds ODU Tandem Connection Monitoring - Instance B" 
    ::=  { intervalOduTcmB1dayEntry 3 }

intervalOduTcmB1dayBbe OBJECT-TYPE
    SYNTAX      Counter64String
    MAX-ACCESS  read-only
    STATUS      current 
    DESCRIPTION
        "Background Block Erros ODU Tandem Connection Monitoring - Instance B" 
    ::=  { intervalOduTcmB1dayEntry 4 }

intervalOduTcmB1dayUAS OBJECT-TYPE
    SYNTAX      Unsigned32
    MAX-ACCESS  read-only
    STATUS      current 
    DESCRIPTION
        "Unavailable Seconds ODU Tandem Connection Monitoring - Instance B" 
    ::=  { intervalOduTcmB1dayEntry 5 }

intervalOduTcmB1dayValidFlag OBJECT-TYPE
    SYNTAX      TruthValue
    MAX-ACCESS  read-only
    STATUS      current 
    DESCRIPTION
        "" 
    ::=  { intervalOduTcmB1dayEntry 6 }

intervalOduTcmB1dayTimeStamp OBJECT-TYPE
    SYNTAX      DateAndTime
    MAX-ACCESS  read-only
    STATUS      current 
    DESCRIPTION
        "Timestamp" 
    ::=  { intervalOduTcmB1dayEntry 7 }

currentSonetSect15minTable OBJECT-TYPE
    SYNTAX      SEQUENCE OF CurrentSonetSect15minEntry
    MAX-ACCESS  not-accessible
    STATUS      current 
    DESCRIPTION
        "" 
    ::=  { performanceMonitoring 17 }

currentSonetSect15minEntry OBJECT-TYPE
    SYNTAX      CurrentSonetSect15minEntry
    MAX-ACCESS  not-accessible
    STATUS      current 
    DESCRIPTION
        "" 
    INDEX       { entityIndex } 
    ::=  { currentSonetSect15minTable  1  }

CurrentSonetSect15minEntry ::=  SEQUENCE
  { currentSonetSect15minES Unsigned32,
    currentSonetSect15minSES Unsigned32,
    currentSonetSect15minSEFS Unsigned32,
    currentSonetSect15minCV Counter64String,
    currentSonetSect15minElapsedTime Integer32 }


  
currentSonetSect15minES OBJECT-TYPE
    SYNTAX      Unsigned32
    MAX-ACCESS  read-only
    STATUS      current 
    DESCRIPTION
        "Errored Seconds Section" 
    ::=  { currentSonetSect15minEntry 1 }

currentSonetSect15minSES OBJECT-TYPE
    SYNTAX      Unsigned32
    MAX-ACCESS  read-only
    STATUS      current 
    DESCRIPTION
        "Severely Errored Seconds Section" 
    ::=  { currentSonetSect15minEntry 2 }

currentSonetSect15minSEFS OBJECT-TYPE
    SYNTAX      Unsigned32
    MAX-ACCESS  read-only
    STATUS      current 
    DESCRIPTION
        "Severly Errored Framing Seconds Section" 
    ::=  { currentSonetSect15minEntry 3 }

currentSonetSect15minCV OBJECT-TYPE
    SYNTAX      Counter64String
    MAX-ACCESS  read-only
    STATUS      current 
    DESCRIPTION
        "Coding Violations Section" 
    ::=  { currentSonetSect15minEntry 4 }

currentSonetSect15minElapsedTime OBJECT-TYPE
    SYNTAX      Integer32 (0..9000)
    MAX-ACCESS  read-only
    STATUS      current 
    DESCRIPTION
        "Elapsed 15Min" 
    ::=  { currentSonetSect15minEntry 5 }

currentSonetSect1dayTable OBJECT-TYPE
    SYNTAX      SEQUENCE OF CurrentSonetSect1dayEntry
    MAX-ACCESS  not-accessible
    STATUS      current 
    DESCRIPTION
        "" 
    ::=  { performanceMonitoring 18 }

currentSonetSect1dayEntry OBJECT-TYPE
    SYNTAX      CurrentSonetSect1dayEntry
    MAX-ACCESS  not-accessible
    STATUS      current 
    DESCRIPTION
        "" 
    INDEX       { entityIndex } 
    ::=  { currentSonetSect1dayTable  1  }

CurrentSonetSect1dayEntry ::=  SEQUENCE
  { currentSonetSect1dayES Unsigned32,
    currentSonetSect1daySES Unsigned32,
    currentSonetSect1daySEFS Unsigned32,
    currentSonetSect1dayCV Counter64String,
    currentSonetSect1dayElapsedTime Integer32 }


  
currentSonetSect1dayES OBJECT-TYPE
    SYNTAX      Unsigned32
    MAX-ACCESS  read-only
    STATUS      current 
    DESCRIPTION
        "Errored Seconds Section" 
    ::=  { currentSonetSect1dayEntry 1 }

currentSonetSect1daySES OBJECT-TYPE
    SYNTAX      Unsigned32
    MAX-ACCESS  read-only
    STATUS      current 
    DESCRIPTION
        "Severely Errored Seconds Section" 
    ::=  { currentSonetSect1dayEntry 2 }

currentSonetSect1daySEFS OBJECT-TYPE
    SYNTAX      Unsigned32
    MAX-ACCESS  read-only
    STATUS      current 
    DESCRIPTION
        "Severly Errored Framing Seconds Section" 
    ::=  { currentSonetSect1dayEntry 3 }

currentSonetSect1dayCV OBJECT-TYPE
    SYNTAX      Counter64String
    MAX-ACCESS  read-only
    STATUS      current 
    DESCRIPTION
        "Coding Violations Section" 
    ::=  { currentSonetSect1dayEntry 4 }

currentSonetSect1dayElapsedTime OBJECT-TYPE
    SYNTAX      Integer32 (0..86400)
    MAX-ACCESS  read-only
    STATUS      current 
    DESCRIPTION
        "Elapsed 1Day" 
    ::=  { currentSonetSect1dayEntry 5 }

intervalSonetSect15minTable OBJECT-TYPE
    SYNTAX      SEQUENCE OF IntervalSonetSect15minEntry
    MAX-ACCESS  not-accessible
    STATUS      current 
    DESCRIPTION
        "" 
    ::=  { performanceMonitoring 19 }

intervalSonetSect15minEntry OBJECT-TYPE
    SYNTAX      IntervalSonetSect15minEntry
    MAX-ACCESS  not-accessible
    STATUS      current 
    DESCRIPTION
        "" 
    INDEX       { entityIndex,intervalSonetSect15minNumber } 
    ::=  { intervalSonetSect15minTable  1  }

IntervalSonetSect15minEntry ::=  SEQUENCE
  { intervalSonetSect15minNumber Integer32,
    intervalSonetSect15minES Unsigned32,
    intervalSonetSect15minSES Unsigned32,
    intervalSonetSect15minSEFS Unsigned32,
    intervalSonetSect15minCV Counter64String,
    intervalSonetSect15minValidFlag TruthValue,
    intervalSonetSect15minTimeStamp DateAndTime }


  
intervalSonetSect15minNumber OBJECT-TYPE
    SYNTAX      Integer32 (1..96)
    MAX-ACCESS  not-accessible
    STATUS      current 
    DESCRIPTION
        "Number 15min" 
    ::=  { intervalSonetSect15minEntry 1 }

intervalSonetSect15minES OBJECT-TYPE
    SYNTAX      Unsigned32
    MAX-ACCESS  read-only
    STATUS      current 
    DESCRIPTION
        "Errored Seconds Section" 
    ::=  { intervalSonetSect15minEntry 2 }

intervalSonetSect15minSES OBJECT-TYPE
    SYNTAX      Unsigned32
    MAX-ACCESS  read-only
    STATUS      current 
    DESCRIPTION
        "Severely Errored Seconds Section" 
    ::=  { intervalSonetSect15minEntry 3 }

intervalSonetSect15minSEFS OBJECT-TYPE
    SYNTAX      Unsigned32
    MAX-ACCESS  read-only
    STATUS      current 
    DESCRIPTION
        "Severly Errored Framing Seconds Section" 
    ::=  { intervalSonetSect15minEntry 4 }

intervalSonetSect15minCV OBJECT-TYPE
    SYNTAX      Counter64String
    MAX-ACCESS  read-only
    STATUS      current 
    DESCRIPTION
        "Coding Violations Section" 
    ::=  { intervalSonetSect15minEntry 5 }

intervalSonetSect15minValidFlag OBJECT-TYPE
    SYNTAX      TruthValue
    MAX-ACCESS  read-only
    STATUS      current 
    DESCRIPTION
        "" 
    ::=  { intervalSonetSect15minEntry 6 }

intervalSonetSect15minTimeStamp OBJECT-TYPE
    SYNTAX      DateAndTime
    MAX-ACCESS  read-only
    STATUS      current 
    DESCRIPTION
        "Timestamp" 
    ::=  { intervalSonetSect15minEntry 7 }

intervalSonetSect1dayTable OBJECT-TYPE
    SYNTAX      SEQUENCE OF IntervalSonetSect1dayEntry
    MAX-ACCESS  not-accessible
    STATUS      current 
    DESCRIPTION
        "" 
    ::=  { performanceMonitoring 20 }

intervalSonetSect1dayEntry OBJECT-TYPE
    SYNTAX      IntervalSonetSect1dayEntry
    MAX-ACCESS  not-accessible
    STATUS      current 
    DESCRIPTION
        "" 
    INDEX       { entityIndex,intervalSonetSect1dayNumber } 
    ::=  { intervalSonetSect1dayTable  1  }

IntervalSonetSect1dayEntry ::=  SEQUENCE
  { intervalSonetSect1dayNumber Integer32,
    intervalSonetSect1dayES Unsigned32,
    intervalSonetSect1daySES Unsigned32,
    intervalSonetSect1daySEFS Unsigned32,
    intervalSonetSect1dayCV Counter64String,
    intervalSonetSect1dayValidFlag TruthValue,
    intervalSonetSect1dayTimeStamp DateAndTime }


  
intervalSonetSect1dayNumber OBJECT-TYPE
    SYNTAX      Integer32 (1..31)
    MAX-ACCESS  not-accessible
    STATUS      current 
    DESCRIPTION
        "Number 1day" 
    ::=  { intervalSonetSect1dayEntry 1 }

intervalSonetSect1dayES OBJECT-TYPE
    SYNTAX      Unsigned32
    MAX-ACCESS  read-only
    STATUS      current 
    DESCRIPTION
        "Errored Seconds Section" 
    ::=  { intervalSonetSect1dayEntry 2 }

intervalSonetSect1daySES OBJECT-TYPE
    SYNTAX      Unsigned32
    MAX-ACCESS  read-only
    STATUS      current 
    DESCRIPTION
        "Severely Errored Seconds Section" 
    ::=  { intervalSonetSect1dayEntry 3 }

intervalSonetSect1daySEFS OBJECT-TYPE
    SYNTAX      Unsigned32
    MAX-ACCESS  read-only
    STATUS      current 
    DESCRIPTION
        "Severly Errored Framing Seconds Section" 
    ::=  { intervalSonetSect1dayEntry 4 }

intervalSonetSect1dayCV OBJECT-TYPE
    SYNTAX      Counter64String
    MAX-ACCESS  read-only
    STATUS      current 
    DESCRIPTION
        "Coding Violations Section" 
    ::=  { intervalSonetSect1dayEntry 5 }

intervalSonetSect1dayValidFlag OBJECT-TYPE
    SYNTAX      TruthValue
    MAX-ACCESS  read-only
    STATUS      current 
    DESCRIPTION
        "" 
    ::=  { intervalSonetSect1dayEntry 6 }

intervalSonetSect1dayTimeStamp OBJECT-TYPE
    SYNTAX      DateAndTime
    MAX-ACCESS  read-only
    STATUS      current 
    DESCRIPTION
        "Timestamp" 
    ::=  { intervalSonetSect1dayEntry 7 }

currentSonetLine15minTable OBJECT-TYPE
    SYNTAX      SEQUENCE OF CurrentSonetLine15minEntry
    MAX-ACCESS  not-accessible
    STATUS      current 
    DESCRIPTION
        "" 
    ::=  { performanceMonitoring 21 }

currentSonetLine15minEntry OBJECT-TYPE
    SYNTAX      CurrentSonetLine15minEntry
    MAX-ACCESS  not-accessible
    STATUS      current 
    DESCRIPTION
        "" 
    INDEX       { entityIndex } 
    ::=  { currentSonetLine15minTable  1  }

CurrentSonetLine15minEntry ::=  SEQUENCE
  { currentSonetLine15minES Unsigned32,
    currentSonetLine15minSES Unsigned32,
    currentSonetLine15minUAS Unsigned32,
    currentSonetLine15minCV Counter64String,
    currentSonetLine15minElapsedTime Integer32 }


  
currentSonetLine15minES OBJECT-TYPE
    SYNTAX      Unsigned32
    MAX-ACCESS  read-only
    STATUS      current 
    DESCRIPTION
        "Errored Seconds Line" 
    ::=  { currentSonetLine15minEntry 1 }

currentSonetLine15minSES OBJECT-TYPE
    SYNTAX      Unsigned32
    MAX-ACCESS  read-only
    STATUS      current 
    DESCRIPTION
        "Severely Errored Seconds Line" 
    ::=  { currentSonetLine15minEntry 2 }

currentSonetLine15minUAS OBJECT-TYPE
    SYNTAX      Unsigned32
    MAX-ACCESS  read-only
    STATUS      current 
    DESCRIPTION
        "Unavailable Seconds Line" 
    ::=  { currentSonetLine15minEntry 3 }

currentSonetLine15minCV OBJECT-TYPE
    SYNTAX      Counter64String
    MAX-ACCESS  read-only
    STATUS      current 
    DESCRIPTION
        "Coding Violations Line" 
    ::=  { currentSonetLine15minEntry 4 }

currentSonetLine15minElapsedTime OBJECT-TYPE
    SYNTAX      Integer32 (0..9000)
    MAX-ACCESS  read-only
    STATUS      current 
    DESCRIPTION
        "Elapsed 15Min" 
    ::=  { currentSonetLine15minEntry 5 }

currentSonetLine1dayTable OBJECT-TYPE
    SYNTAX      SEQUENCE OF CurrentSonetLine1dayEntry
    MAX-ACCESS  not-accessible
    STATUS      current 
    DESCRIPTION
        "" 
    ::=  { performanceMonitoring 22 }

currentSonetLine1dayEntry OBJECT-TYPE
    SYNTAX      CurrentSonetLine1dayEntry
    MAX-ACCESS  not-accessible
    STATUS      current 
    DESCRIPTION
        "" 
    INDEX       { entityIndex } 
    ::=  { currentSonetLine1dayTable  1  }

CurrentSonetLine1dayEntry ::=  SEQUENCE
  { currentSonetLine1dayES Unsigned32,
    currentSonetLine1daySES Unsigned32,
    currentSonetLine1dayUAS Unsigned32,
    currentSonetLine1dayCV Counter64String,
    currentSonetLine1dayElapsedTime Integer32 }


  
currentSonetLine1dayES OBJECT-TYPE
    SYNTAX      Unsigned32
    MAX-ACCESS  read-only
    STATUS      current 
    DESCRIPTION
        "Errored Seconds Line" 
    ::=  { currentSonetLine1dayEntry 1 }

currentSonetLine1daySES OBJECT-TYPE
    SYNTAX      Unsigned32
    MAX-ACCESS  read-only
    STATUS      current 
    DESCRIPTION
        "Severely Errored Seconds Line" 
    ::=  { currentSonetLine1dayEntry 2 }

currentSonetLine1dayUAS OBJECT-TYPE
    SYNTAX      Unsigned32
    MAX-ACCESS  read-only
    STATUS      current 
    DESCRIPTION
        "Unavailable Seconds Line" 
    ::=  { currentSonetLine1dayEntry 3 }

currentSonetLine1dayCV OBJECT-TYPE
    SYNTAX      Counter64String
    MAX-ACCESS  read-only
    STATUS      current 
    DESCRIPTION
        "Coding Violations Line" 
    ::=  { currentSonetLine1dayEntry 4 }

currentSonetLine1dayElapsedTime OBJECT-TYPE
    SYNTAX      Integer32 (0..86400)
    MAX-ACCESS  read-only
    STATUS      current 
    DESCRIPTION
        "Elapsed 1Day" 
    ::=  { currentSonetLine1dayEntry 5 }

intervalSonetLine15minTable OBJECT-TYPE
    SYNTAX      SEQUENCE OF IntervalSonetLine15minEntry
    MAX-ACCESS  not-accessible
    STATUS      current 
    DESCRIPTION
        "" 
    ::=  { performanceMonitoring 23 }

intervalSonetLine15minEntry OBJECT-TYPE
    SYNTAX      IntervalSonetLine15minEntry
    MAX-ACCESS  not-accessible
    STATUS      current 
    DESCRIPTION
        "" 
    INDEX       { entityIndex,intervalSonetLine15minNumber } 
    ::=  { intervalSonetLine15minTable  1  }

IntervalSonetLine15minEntry ::=  SEQUENCE
  { intervalSonetLine15minNumber Integer32,
    intervalSonetLine15minES Unsigned32,
    intervalSonetLine15minSES Unsigned32,
    intervalSonetLine15minUAS Unsigned32,
    intervalSonetLine15minCV Counter64String,
    intervalSonetLine15minValidFlag TruthValue,
    intervalSonetLine15minTimeStamp DateAndTime }


  
intervalSonetLine15minNumber OBJECT-TYPE
    SYNTAX      Integer32 (1..96)
    MAX-ACCESS  not-accessible
    STATUS      current 
    DESCRIPTION
        "Number 15min" 
    ::=  { intervalSonetLine15minEntry 1 }

intervalSonetLine15minES OBJECT-TYPE
    SYNTAX      Unsigned32
    MAX-ACCESS  read-only
    STATUS      current 
    DESCRIPTION
        "Errored Seconds Line" 
    ::=  { intervalSonetLine15minEntry 2 }

intervalSonetLine15minSES OBJECT-TYPE
    SYNTAX      Unsigned32
    MAX-ACCESS  read-only
    STATUS      current 
    DESCRIPTION
        "Severely Errored Seconds Line" 
    ::=  { intervalSonetLine15minEntry 3 }

intervalSonetLine15minUAS OBJECT-TYPE
    SYNTAX      Unsigned32
    MAX-ACCESS  read-only
    STATUS      current 
    DESCRIPTION
        "Unavailable Seconds Line" 
    ::=  { intervalSonetLine15minEntry 4 }

intervalSonetLine15minCV OBJECT-TYPE
    SYNTAX      Counter64String
    MAX-ACCESS  read-only
    STATUS      current 
    DESCRIPTION
        "Coding Violations Line" 
    ::=  { intervalSonetLine15minEntry 5 }

intervalSonetLine15minValidFlag OBJECT-TYPE
    SYNTAX      TruthValue
    MAX-ACCESS  read-only
    STATUS      current 
    DESCRIPTION
        "" 
    ::=  { intervalSonetLine15minEntry 6 }

intervalSonetLine15minTimeStamp OBJECT-TYPE
    SYNTAX      DateAndTime
    MAX-ACCESS  read-only
    STATUS      current 
    DESCRIPTION
        "Timestamp" 
    ::=  { intervalSonetLine15minEntry 7 }

intervalSonetLine1dayTable OBJECT-TYPE
    SYNTAX      SEQUENCE OF IntervalSonetLine1dayEntry
    MAX-ACCESS  not-accessible
    STATUS      current 
    DESCRIPTION
        "" 
    ::=  { performanceMonitoring 24 }

intervalSonetLine1dayEntry OBJECT-TYPE
    SYNTAX      IntervalSonetLine1dayEntry
    MAX-ACCESS  not-accessible
    STATUS      current 
    DESCRIPTION
        "" 
    INDEX       { entityIndex,intervalSonetLine1dayNumber } 
    ::=  { intervalSonetLine1dayTable  1  }

IntervalSonetLine1dayEntry ::=  SEQUENCE
  { intervalSonetLine1dayNumber Integer32,
    intervalSonetLine1dayES Unsigned32,
    intervalSonetLine1daySES Unsigned32,
    intervalSonetLine1dayUAS Unsigned32,
    intervalSonetLine1dayCV Counter64String,
    intervalSonetLine1dayValidFlag TruthValue,
    intervalSonetLine1dayTimeStamp DateAndTime }


  
intervalSonetLine1dayNumber OBJECT-TYPE
    SYNTAX      Integer32 (1..31)
    MAX-ACCESS  not-accessible
    STATUS      current 
    DESCRIPTION
        "Number 1day" 
    ::=  { intervalSonetLine1dayEntry 1 }

intervalSonetLine1dayES OBJECT-TYPE
    SYNTAX      Unsigned32
    MAX-ACCESS  read-only
    STATUS      current 
    DESCRIPTION
        "Errored Seconds Line" 
    ::=  { intervalSonetLine1dayEntry 2 }

intervalSonetLine1daySES OBJECT-TYPE
    SYNTAX      Unsigned32
    MAX-ACCESS  read-only
    STATUS      current 
    DESCRIPTION
        "Severely Errored Seconds Line" 
    ::=  { intervalSonetLine1dayEntry 3 }

intervalSonetLine1dayUAS OBJECT-TYPE
    SYNTAX      Unsigned32
    MAX-ACCESS  read-only
    STATUS      current 
    DESCRIPTION
        "Unavailable Seconds Line" 
    ::=  { intervalSonetLine1dayEntry 4 }

intervalSonetLine1dayCV OBJECT-TYPE
    SYNTAX      Counter64String
    MAX-ACCESS  read-only
    STATUS      current 
    DESCRIPTION
        "Coding Violations Line" 
    ::=  { intervalSonetLine1dayEntry 5 }

intervalSonetLine1dayValidFlag OBJECT-TYPE
    SYNTAX      TruthValue
    MAX-ACCESS  read-only
    STATUS      current 
    DESCRIPTION
        "" 
    ::=  { intervalSonetLine1dayEntry 6 }

intervalSonetLine1dayTimeStamp OBJECT-TYPE
    SYNTAX      DateAndTime
    MAX-ACCESS  read-only
    STATUS      current 
    DESCRIPTION
        "Timestamp" 
    ::=  { intervalSonetLine1dayEntry 7 }

currentSonetHoPath15minTable OBJECT-TYPE
    SYNTAX      SEQUENCE OF CurrentSonetHoPath15minEntry
    MAX-ACCESS  not-accessible
    STATUS      current 
    DESCRIPTION
        "" 
    ::=  { performanceMonitoring 25 }

currentSonetHoPath15minEntry OBJECT-TYPE
    SYNTAX      CurrentSonetHoPath15minEntry
    MAX-ACCESS  not-accessible
    STATUS      current 
    DESCRIPTION
        "" 
    INDEX       { entityIndex } 
    ::=  { currentSonetHoPath15minTable  1  }

CurrentSonetHoPath15minEntry ::=  SEQUENCE
  { currentSonetHoPath15minES Unsigned32,
    currentSonetHoPath15minSES Unsigned32,
    currentSonetHoPath15minUAS Unsigned32,
    currentSonetHoPath15minCV Counter64String,
    currentSonetHoPath15minElapsedTime Integer32 }


  
currentSonetHoPath15minES OBJECT-TYPE
    SYNTAX      Unsigned32
    MAX-ACCESS  read-only
    STATUS      current 
    DESCRIPTION
        "Errored Seconds Path" 
    ::=  { currentSonetHoPath15minEntry 1 }

currentSonetHoPath15minSES OBJECT-TYPE
    SYNTAX      Unsigned32
    MAX-ACCESS  read-only
    STATUS      current 
    DESCRIPTION
        "Severely Errored Seconds Path" 
    ::=  { currentSonetHoPath15minEntry 2 }

currentSonetHoPath15minUAS OBJECT-TYPE
    SYNTAX      Unsigned32
    MAX-ACCESS  read-only
    STATUS      current 
    DESCRIPTION
        "Unavailable Seconds Path" 
    ::=  { currentSonetHoPath15minEntry 3 }

currentSonetHoPath15minCV OBJECT-TYPE
    SYNTAX      Counter64String
    MAX-ACCESS  read-only
    STATUS      current 
    DESCRIPTION
        "Coding Violations Path" 
    ::=  { currentSonetHoPath15minEntry 4 }

currentSonetHoPath15minElapsedTime OBJECT-TYPE
    SYNTAX      Integer32 (0..9000)
    MAX-ACCESS  read-only
    STATUS      current 
    DESCRIPTION
        "Elapsed 15Min" 
    ::=  { currentSonetHoPath15minEntry 5 }

currentSonetHoPath1dayTable OBJECT-TYPE
    SYNTAX      SEQUENCE OF CurrentSonetHoPath1dayEntry
    MAX-ACCESS  not-accessible
    STATUS      current 
    DESCRIPTION
        "" 
    ::=  { performanceMonitoring 26 }

currentSonetHoPath1dayEntry OBJECT-TYPE
    SYNTAX      CurrentSonetHoPath1dayEntry
    MAX-ACCESS  not-accessible
    STATUS      current 
    DESCRIPTION
        "" 
    INDEX       { entityIndex } 
    ::=  { currentSonetHoPath1dayTable  1  }

CurrentSonetHoPath1dayEntry ::=  SEQUENCE
  { currentSonetHoPath1dayES Unsigned32,
    currentSonetHoPath1daySES Unsigned32,
    currentSonetHoPath1dayUAS Unsigned32,
    currentSonetHoPath1dayCV Counter64String,
    currentSonetHoPath1dayElapsedTime Integer32 }


  
currentSonetHoPath1dayES OBJECT-TYPE
    SYNTAX      Unsigned32
    MAX-ACCESS  read-only
    STATUS      current 
    DESCRIPTION
        "Errored Seconds Path" 
    ::=  { currentSonetHoPath1dayEntry 1 }

currentSonetHoPath1daySES OBJECT-TYPE
    SYNTAX      Unsigned32
    MAX-ACCESS  read-only
    STATUS      current 
    DESCRIPTION
        "Severely Errored Seconds Path" 
    ::=  { currentSonetHoPath1dayEntry 2 }

currentSonetHoPath1dayUAS OBJECT-TYPE
    SYNTAX      Unsigned32
    MAX-ACCESS  read-only
    STATUS      current 
    DESCRIPTION
        "Unavailable Seconds Path" 
    ::=  { currentSonetHoPath1dayEntry 3 }

currentSonetHoPath1dayCV OBJECT-TYPE
    SYNTAX      Counter64String
    MAX-ACCESS  read-only
    STATUS      current 
    DESCRIPTION
        "Coding Violations Path" 
    ::=  { currentSonetHoPath1dayEntry 4 }

currentSonetHoPath1dayElapsedTime OBJECT-TYPE
    SYNTAX      Integer32 (0..86400)
    MAX-ACCESS  read-only
    STATUS      current 
    DESCRIPTION
        "Elapsed 1Day" 
    ::=  { currentSonetHoPath1dayEntry 5 }

intervalSonetHoPath15minTable OBJECT-TYPE
    SYNTAX      SEQUENCE OF IntervalSonetHoPath15minEntry
    MAX-ACCESS  not-accessible
    STATUS      current 
    DESCRIPTION
        "" 
    ::=  { performanceMonitoring 27 }

intervalSonetHoPath15minEntry OBJECT-TYPE
    SYNTAX      IntervalSonetHoPath15minEntry
    MAX-ACCESS  not-accessible
    STATUS      current 
    DESCRIPTION
        "" 
    INDEX       { entityIndex,intervalSonetHoPath15minNumber } 
    ::=  { intervalSonetHoPath15minTable  1  }

IntervalSonetHoPath15minEntry ::=  SEQUENCE
  { intervalSonetHoPath15minNumber Integer32,
    intervalSonetHoPath15minES Unsigned32,
    intervalSonetHoPath15minSES Unsigned32,
    intervalSonetHoPath15minUAS Unsigned32,
    intervalSonetHoPath15minCV Counter64String,
    intervalSonetHoPath15minValidFlag TruthValue,
    intervalSonetHoPath15minTimeStamp DateAndTime }


  
intervalSonetHoPath15minNumber OBJECT-TYPE
    SYNTAX      Integer32 (1..96)
    MAX-ACCESS  not-accessible
    STATUS      current 
    DESCRIPTION
        "Number 15min" 
    ::=  { intervalSonetHoPath15minEntry 1 }

intervalSonetHoPath15minES OBJECT-TYPE
    SYNTAX      Unsigned32
    MAX-ACCESS  read-only
    STATUS      current 
    DESCRIPTION
        "Errored Seconds Path" 
    ::=  { intervalSonetHoPath15minEntry 2 }

intervalSonetHoPath15minSES OBJECT-TYPE
    SYNTAX      Unsigned32
    MAX-ACCESS  read-only
    STATUS      current 
    DESCRIPTION
        "Severely Errored Seconds Path" 
    ::=  { intervalSonetHoPath15minEntry 3 }

intervalSonetHoPath15minUAS OBJECT-TYPE
    SYNTAX      Unsigned32
    MAX-ACCESS  read-only
    STATUS      current 
    DESCRIPTION
        "Unavailable Seconds Path" 
    ::=  { intervalSonetHoPath15minEntry 4 }

intervalSonetHoPath15minCV OBJECT-TYPE
    SYNTAX      Counter64String
    MAX-ACCESS  read-only
    STATUS      current 
    DESCRIPTION
        "Coding Violations Path" 
    ::=  { intervalSonetHoPath15minEntry 5 }

intervalSonetHoPath15minValidFlag OBJECT-TYPE
    SYNTAX      TruthValue
    MAX-ACCESS  read-only
    STATUS      current 
    DESCRIPTION
        "" 
    ::=  { intervalSonetHoPath15minEntry 6 }

intervalSonetHoPath15minTimeStamp OBJECT-TYPE
    SYNTAX      DateAndTime
    MAX-ACCESS  read-only
    STATUS      current 
    DESCRIPTION
        "Timestamp" 
    ::=  { intervalSonetHoPath15minEntry 7 }

intervalSonetHoPath1dayTable OBJECT-TYPE
    SYNTAX      SEQUENCE OF IntervalSonetHoPath1dayEntry
    MAX-ACCESS  not-accessible
    STATUS      current 
    DESCRIPTION
        "" 
    ::=  { performanceMonitoring 28 }

intervalSonetHoPath1dayEntry OBJECT-TYPE
    SYNTAX      IntervalSonetHoPath1dayEntry
    MAX-ACCESS  not-accessible
    STATUS      current 
    DESCRIPTION
        "" 
    INDEX       { entityIndex,intervalSonetHoPath1dayNumber } 
    ::=  { intervalSonetHoPath1dayTable  1  }

IntervalSonetHoPath1dayEntry ::=  SEQUENCE
  { intervalSonetHoPath1dayNumber Integer32,
    intervalSonetHoPath1dayES Unsigned32,
    intervalSonetHoPath1daySES Unsigned32,
    intervalSonetHoPath1dayUAS Unsigned32,
    intervalSonetHoPath1dayCV Counter64String,
    intervalSonetHoPath1dayValidFlag TruthValue,
    intervalSonetHoPath1dayTimeStamp DateAndTime }


  
intervalSonetHoPath1dayNumber OBJECT-TYPE
    SYNTAX      Integer32 (1..31)
    MAX-ACCESS  not-accessible
    STATUS      current 
    DESCRIPTION
        "Number 1day" 
    ::=  { intervalSonetHoPath1dayEntry 1 }

intervalSonetHoPath1dayES OBJECT-TYPE
    SYNTAX      Unsigned32
    MAX-ACCESS  read-only
    STATUS      current 
    DESCRIPTION
        "Errored Seconds Path" 
    ::=  { intervalSonetHoPath1dayEntry 2 }

intervalSonetHoPath1daySES OBJECT-TYPE
    SYNTAX      Unsigned32
    MAX-ACCESS  read-only
    STATUS      current 
    DESCRIPTION
        "Severely Errored Seconds Path" 
    ::=  { intervalSonetHoPath1dayEntry 3 }

intervalSonetHoPath1dayUAS OBJECT-TYPE
    SYNTAX      Unsigned32
    MAX-ACCESS  read-only
    STATUS      current 
    DESCRIPTION
        "Unavailable Seconds Path" 
    ::=  { intervalSonetHoPath1dayEntry 4 }

intervalSonetHoPath1dayCV OBJECT-TYPE
    SYNTAX      Counter64String
    MAX-ACCESS  read-only
    STATUS      current 
    DESCRIPTION
        "Coding Violations Path" 
    ::=  { intervalSonetHoPath1dayEntry 5 }

intervalSonetHoPath1dayValidFlag OBJECT-TYPE
    SYNTAX      TruthValue
    MAX-ACCESS  read-only
    STATUS      current 
    DESCRIPTION
        "" 
    ::=  { intervalSonetHoPath1dayEntry 6 }

intervalSonetHoPath1dayTimeStamp OBJECT-TYPE
    SYNTAX      DateAndTime
    MAX-ACCESS  read-only
    STATUS      current 
    DESCRIPTION
        "Timestamp" 
    ::=  { intervalSonetHoPath1dayEntry 7 }

currentSonetLoPath15minTable OBJECT-TYPE
    SYNTAX      SEQUENCE OF CurrentSonetLoPath15minEntry
    MAX-ACCESS  not-accessible
    STATUS      current 
    DESCRIPTION
        "" 
    ::=  { performanceMonitoring 29 }

currentSonetLoPath15minEntry OBJECT-TYPE
    SYNTAX      CurrentSonetLoPath15minEntry
    MAX-ACCESS  not-accessible
    STATUS      current 
    DESCRIPTION
        "" 
    INDEX       { entityIndex } 
    ::=  { currentSonetLoPath15minTable  1  }

CurrentSonetLoPath15minEntry ::=  SEQUENCE
  { currentSonetLoPath15minES Unsigned32,
    currentSonetLoPath15minSES Unsigned32,
    currentSonetLoPath15minUAS Unsigned32,
    currentSonetLoPath15minCV Counter64String,
    currentSonetLoPath15minElapsedTime Integer32 }


  
currentSonetLoPath15minES OBJECT-TYPE
    SYNTAX      Unsigned32
    MAX-ACCESS  read-only
    STATUS      current 
    DESCRIPTION
        "Errored Seconds Lower Order Path" 
    ::=  { currentSonetLoPath15minEntry 1 }

currentSonetLoPath15minSES OBJECT-TYPE
    SYNTAX      Unsigned32
    MAX-ACCESS  read-only
    STATUS      current 
    DESCRIPTION
        "Severely Errored Seconds LO-Path" 
    ::=  { currentSonetLoPath15minEntry 2 }

currentSonetLoPath15minUAS OBJECT-TYPE
    SYNTAX      Unsigned32
    MAX-ACCESS  read-only
    STATUS      current 
    DESCRIPTION
        "Unavailable Seconds LO-Path" 
    ::=  { currentSonetLoPath15minEntry 3 }

currentSonetLoPath15minCV OBJECT-TYPE
    SYNTAX      Counter64String
    MAX-ACCESS  read-only
    STATUS      current 
    DESCRIPTION
        "Coding Violations Lower Order Path" 
    ::=  { currentSonetLoPath15minEntry 4 }

currentSonetLoPath15minElapsedTime OBJECT-TYPE
    SYNTAX      Integer32 (0..9000)
    MAX-ACCESS  read-only
    STATUS      current 
    DESCRIPTION
        "Elapsed 15Min" 
    ::=  { currentSonetLoPath15minEntry 5 }

currentSonetLoPath1dayTable OBJECT-TYPE
    SYNTAX      SEQUENCE OF CurrentSonetLoPath1dayEntry
    MAX-ACCESS  not-accessible
    STATUS      current 
    DESCRIPTION
        "" 
    ::=  { performanceMonitoring 30 }

currentSonetLoPath1dayEntry OBJECT-TYPE
    SYNTAX      CurrentSonetLoPath1dayEntry
    MAX-ACCESS  not-accessible
    STATUS      current 
    DESCRIPTION
        "" 
    INDEX       { entityIndex } 
    ::=  { currentSonetLoPath1dayTable  1  }

CurrentSonetLoPath1dayEntry ::=  SEQUENCE
  { currentSonetLoPath1dayES Unsigned32,
    currentSonetLoPath1daySES Unsigned32,
    currentSonetLoPath1dayUAS Unsigned32,
    currentSonetLoPath1dayCV Counter64String,
    currentSonetLoPath1dayElapsedTime Integer32 }


  
currentSonetLoPath1dayES OBJECT-TYPE
    SYNTAX      Unsigned32
    MAX-ACCESS  read-only
    STATUS      current 
    DESCRIPTION
        "Errored Seconds Lower Order Path" 
    ::=  { currentSonetLoPath1dayEntry 1 }

currentSonetLoPath1daySES OBJECT-TYPE
    SYNTAX      Unsigned32
    MAX-ACCESS  read-only
    STATUS      current 
    DESCRIPTION
        "Severely Errored Seconds LO-Path" 
    ::=  { currentSonetLoPath1dayEntry 2 }

currentSonetLoPath1dayUAS OBJECT-TYPE
    SYNTAX      Unsigned32
    MAX-ACCESS  read-only
    STATUS      current 
    DESCRIPTION
        "Unavailable Seconds LO-Path" 
    ::=  { currentSonetLoPath1dayEntry 3 }

currentSonetLoPath1dayCV OBJECT-TYPE
    SYNTAX      Counter64String
    MAX-ACCESS  read-only
    STATUS      current 
    DESCRIPTION
        "Coding Violations Lower Order Path" 
    ::=  { currentSonetLoPath1dayEntry 4 }

currentSonetLoPath1dayElapsedTime OBJECT-TYPE
    SYNTAX      Integer32 (0..86400)
    MAX-ACCESS  read-only
    STATUS      current 
    DESCRIPTION
        "Elapsed 1Day" 
    ::=  { currentSonetLoPath1dayEntry 5 }

intervalSonetLoPath15minTable OBJECT-TYPE
    SYNTAX      SEQUENCE OF IntervalSonetLoPath15minEntry
    MAX-ACCESS  not-accessible
    STATUS      current 
    DESCRIPTION
        "" 
    ::=  { performanceMonitoring 31 }

intervalSonetLoPath15minEntry OBJECT-TYPE
    SYNTAX      IntervalSonetLoPath15minEntry
    MAX-ACCESS  not-accessible
    STATUS      current 
    DESCRIPTION
        "" 
    INDEX       { entityIndex,intervalSonetLoPath15minNumber } 
    ::=  { intervalSonetLoPath15minTable  1  }

IntervalSonetLoPath15minEntry ::=  SEQUENCE
  { intervalSonetLoPath15minNumber Integer32,
    intervalSonetLoPath15minES Unsigned32,
    intervalSonetLoPath15minSES Unsigned32,
    intervalSonetLoPath15minUAS Unsigned32,
    intervalSonetLoPath15minCV Counter64String,
    intervalSonetLoPath15minValidFlag TruthValue,
    intervalSonetLoPath15minTimeStamp DateAndTime }


  
intervalSonetLoPath15minNumber OBJECT-TYPE
    SYNTAX      Integer32 (1..96)
    MAX-ACCESS  not-accessible
    STATUS      current 
    DESCRIPTION
        "Number 15min" 
    ::=  { intervalSonetLoPath15minEntry 1 }

intervalSonetLoPath15minES OBJECT-TYPE
    SYNTAX      Unsigned32
    MAX-ACCESS  read-only
    STATUS      current 
    DESCRIPTION
        "Errored Seconds Lower Order Path" 
    ::=  { intervalSonetLoPath15minEntry 2 }

intervalSonetLoPath15minSES OBJECT-TYPE
    SYNTAX      Unsigned32
    MAX-ACCESS  read-only
    STATUS      current 
    DESCRIPTION
        "Severely Errored Seconds LO-Path" 
    ::=  { intervalSonetLoPath15minEntry 3 }

intervalSonetLoPath15minUAS OBJECT-TYPE
    SYNTAX      Unsigned32
    MAX-ACCESS  read-only
    STATUS      current 
    DESCRIPTION
        "Unavailable Seconds LO-Path" 
    ::=  { intervalSonetLoPath15minEntry 4 }

intervalSonetLoPath15minCV OBJECT-TYPE
    SYNTAX      Counter64String
    MAX-ACCESS  read-only
    STATUS      current 
    DESCRIPTION
        "Coding Violations Lower Order Path" 
    ::=  { intervalSonetLoPath15minEntry 5 }

intervalSonetLoPath15minValidFlag OBJECT-TYPE
    SYNTAX      TruthValue
    MAX-ACCESS  read-only
    STATUS      current 
    DESCRIPTION
        "" 
    ::=  { intervalSonetLoPath15minEntry 6 }

intervalSonetLoPath15minTimeStamp OBJECT-TYPE
    SYNTAX      DateAndTime
    MAX-ACCESS  read-only
    STATUS      current 
    DESCRIPTION
        "Timestamp" 
    ::=  { intervalSonetLoPath15minEntry 7 }

intervalSonetLoPath1dayTable OBJECT-TYPE
    SYNTAX      SEQUENCE OF IntervalSonetLoPath1dayEntry
    MAX-ACCESS  not-accessible
    STATUS      current 
    DESCRIPTION
        "" 
    ::=  { performanceMonitoring 32 }

intervalSonetLoPath1dayEntry OBJECT-TYPE
    SYNTAX      IntervalSonetLoPath1dayEntry
    MAX-ACCESS  not-accessible
    STATUS      current 
    DESCRIPTION
        "" 
    INDEX       { entityIndex,intervalSonetLoPath1dayNumber } 
    ::=  { intervalSonetLoPath1dayTable  1  }

IntervalSonetLoPath1dayEntry ::=  SEQUENCE
  { intervalSonetLoPath1dayNumber Integer32,
    intervalSonetLoPath1dayES Unsigned32,
    intervalSonetLoPath1daySES Unsigned32,
    intervalSonetLoPath1dayUAS Unsigned32,
    intervalSonetLoPath1dayCV Counter64String,
    intervalSonetLoPath1dayValidFlag TruthValue,
    intervalSonetLoPath1dayTimeStamp DateAndTime }


  
intervalSonetLoPath1dayNumber OBJECT-TYPE
    SYNTAX      Integer32 (1..31)
    MAX-ACCESS  not-accessible
    STATUS      current 
    DESCRIPTION
        "Number 1day" 
    ::=  { intervalSonetLoPath1dayEntry 1 }

intervalSonetLoPath1dayES OBJECT-TYPE
    SYNTAX      Unsigned32
    MAX-ACCESS  read-only
    STATUS      current 
    DESCRIPTION
        "Errored Seconds Lower Order Path" 
    ::=  { intervalSonetLoPath1dayEntry 2 }

intervalSonetLoPath1daySES OBJECT-TYPE
    SYNTAX      Unsigned32
    MAX-ACCESS  read-only
    STATUS      current 
    DESCRIPTION
        "Severely Errored Seconds LO-Path" 
    ::=  { intervalSonetLoPath1dayEntry 3 }

intervalSonetLoPath1dayUAS OBJECT-TYPE
    SYNTAX      Unsigned32
    MAX-ACCESS  read-only
    STATUS      current 
    DESCRIPTION
        "Unavailable Seconds LO-Path" 
    ::=  { intervalSonetLoPath1dayEntry 4 }

intervalSonetLoPath1dayCV OBJECT-TYPE
    SYNTAX      Counter64String
    MAX-ACCESS  read-only
    STATUS      current 
    DESCRIPTION
        "Coding Violations Lower Order Path" 
    ::=  { intervalSonetLoPath1dayEntry 5 }

intervalSonetLoPath1dayValidFlag OBJECT-TYPE
    SYNTAX      TruthValue
    MAX-ACCESS  read-only
    STATUS      current 
    DESCRIPTION
        "" 
    ::=  { intervalSonetLoPath1dayEntry 6 }

intervalSonetLoPath1dayTimeStamp OBJECT-TYPE
    SYNTAX      DateAndTime
    MAX-ACCESS  read-only
    STATUS      current 
    DESCRIPTION
        "Timestamp" 
    ::=  { intervalSonetLoPath1dayEntry 7 }

intervalPhysPerfOpticalInputPwr15minTable OBJECT-TYPE
    SYNTAX      SEQUENCE OF IntervalPhysPerfOpticalInputPwr15minEntry
    MAX-ACCESS  not-accessible
    STATUS      current 
    DESCRIPTION
        "" 
    ::=  { performanceMonitoring 33 }

intervalPhysPerfOpticalInputPwr15minEntry OBJECT-TYPE
    SYNTAX      IntervalPhysPerfOpticalInputPwr15minEntry
    MAX-ACCESS  not-accessible
    STATUS      current 
    DESCRIPTION
        "" 
    INDEX       { entityIndex,intervalPhysPerfOpticalInputPwr15minNumber } 
    ::=  { intervalPhysPerfOpticalInputPwr15minTable  1  }

IntervalPhysPerfOpticalInputPwr15minEntry ::=  SEQUENCE
  { intervalPhysPerfOpticalInputPwr15minNumber Integer32,
    intervalPhysPerfOpticalInputPwr15minLow Integer32,
    intervalPhysPerfOpticalInputPwr15minMean Integer32,
    intervalPhysPerfOpticalInputPwr15minHigh Integer32,
    intervalPhysPerfOpticalInputPwr15minValidFlag TruthValue,
    intervalPhysPerfOpticalInputPwr15minTimeStamp DateAndTime }


  
intervalPhysPerfOpticalInputPwr15minNumber OBJECT-TYPE
    SYNTAX      Integer32 (1..96)
    MAX-ACCESS  not-accessible
    STATUS      current 
    DESCRIPTION
        "Number 15min" 
    ::=  { intervalPhysPerfOpticalInputPwr15minEntry 1 }

intervalPhysPerfOpticalInputPwr15minLow OBJECT-TYPE
    SYNTAX      Integer32
    UNITS       "0.1 dBm"
    MAX-ACCESS  read-only
    STATUS      current 
    DESCRIPTION
        "Optical Input Power Received" 
    ::=  { intervalPhysPerfOpticalInputPwr15minEntry 2 }

intervalPhysPerfOpticalInputPwr15minMean OBJECT-TYPE
    SYNTAX      Integer32
    UNITS       "0.1 dBm"
    MAX-ACCESS  read-only
    STATUS      current 
    DESCRIPTION
        "Optical Input Power Received" 
    ::=  { intervalPhysPerfOpticalInputPwr15minEntry 3 }

intervalPhysPerfOpticalInputPwr15minHigh OBJECT-TYPE
    SYNTAX      Integer32
    UNITS       "0.1 dBm"
    MAX-ACCESS  read-only
    STATUS      current 
    DESCRIPTION
        "Optical Input Power Received" 
    ::=  { intervalPhysPerfOpticalInputPwr15minEntry 4 }

intervalPhysPerfOpticalInputPwr15minValidFlag OBJECT-TYPE
    SYNTAX      TruthValue
    MAX-ACCESS  read-only
    STATUS      current 
    DESCRIPTION
        "" 
    ::=  { intervalPhysPerfOpticalInputPwr15minEntry 5 }

intervalPhysPerfOpticalInputPwr15minTimeStamp OBJECT-TYPE
    SYNTAX      DateAndTime
    MAX-ACCESS  read-only
    STATUS      current 
    DESCRIPTION
        "Timestamp" 
    ::=  { intervalPhysPerfOpticalInputPwr15minEntry 6 }

intervalPhysPerfOpticalInputPwr1dayTable OBJECT-TYPE
    SYNTAX      SEQUENCE OF IntervalPhysPerfOpticalInputPwr1dayEntry
    MAX-ACCESS  not-accessible
    STATUS      current 
    DESCRIPTION
        "" 
    ::=  { performanceMonitoring 34 }

intervalPhysPerfOpticalInputPwr1dayEntry OBJECT-TYPE
    SYNTAX      IntervalPhysPerfOpticalInputPwr1dayEntry
    MAX-ACCESS  not-accessible
    STATUS      current 
    DESCRIPTION
        "" 
    INDEX       { entityIndex,intervalPhysPerfOpticalInputPwr1dayNumber } 
    ::=  { intervalPhysPerfOpticalInputPwr1dayTable  1  }

IntervalPhysPerfOpticalInputPwr1dayEntry ::=  SEQUENCE
  { intervalPhysPerfOpticalInputPwr1dayNumber Integer32,
    intervalPhysPerfOpticalInputPwr1dayLow Integer32,
    intervalPhysPerfOpticalInputPwr1dayMean Integer32,
    intervalPhysPerfOpticalInputPwr1dayHigh Integer32,
    intervalPhysPerfOpticalInputPwr1dayValidFlag TruthValue,
    intervalPhysPerfOpticalInputPwr1dayTimeStamp DateAndTime }


  
intervalPhysPerfOpticalInputPwr1dayNumber OBJECT-TYPE
    SYNTAX      Integer32 (1..31)
    MAX-ACCESS  not-accessible
    STATUS      current 
    DESCRIPTION
        "Number 1day" 
    ::=  { intervalPhysPerfOpticalInputPwr1dayEntry 1 }

intervalPhysPerfOpticalInputPwr1dayLow OBJECT-TYPE
    SYNTAX      Integer32
    UNITS       "0.1 dBm"
    MAX-ACCESS  read-only
    STATUS      current 
    DESCRIPTION
        "Optical Input Power Received" 
    ::=  { intervalPhysPerfOpticalInputPwr1dayEntry 2 }

intervalPhysPerfOpticalInputPwr1dayMean OBJECT-TYPE
    SYNTAX      Integer32
    UNITS       "0.1 dBm"
    MAX-ACCESS  read-only
    STATUS      current 
    DESCRIPTION
        "Optical Input Power Received" 
    ::=  { intervalPhysPerfOpticalInputPwr1dayEntry 3 }

intervalPhysPerfOpticalInputPwr1dayHigh OBJECT-TYPE
    SYNTAX      Integer32
    UNITS       "0.1 dBm"
    MAX-ACCESS  read-only
    STATUS      current 
    DESCRIPTION
        "Optical Input Power Received" 
    ::=  { intervalPhysPerfOpticalInputPwr1dayEntry 4 }

intervalPhysPerfOpticalInputPwr1dayValidFlag OBJECT-TYPE
    SYNTAX      TruthValue
    MAX-ACCESS  read-only
    STATUS      current 
    DESCRIPTION
        "" 
    ::=  { intervalPhysPerfOpticalInputPwr1dayEntry 5 }

intervalPhysPerfOpticalInputPwr1dayTimeStamp OBJECT-TYPE
    SYNTAX      DateAndTime
    MAX-ACCESS  read-only
    STATUS      current 
    DESCRIPTION
        "Timestamp" 
    ::=  { intervalPhysPerfOpticalInputPwr1dayEntry 6 }

intervalPhysPerfOpticalInputPwr1weekTable OBJECT-TYPE
    SYNTAX      SEQUENCE OF IntervalPhysPerfOpticalInputPwr1weekEntry
    MAX-ACCESS  not-accessible
    STATUS      current 
    DESCRIPTION
        "" 
    ::=  { performanceMonitoring 35 }

intervalPhysPerfOpticalInputPwr1weekEntry OBJECT-TYPE
    SYNTAX      IntervalPhysPerfOpticalInputPwr1weekEntry
    MAX-ACCESS  not-accessible
    STATUS      current 
    DESCRIPTION
        "" 
    INDEX       { entityIndex,intervalPhysPerfOpticalInputPwr1weekNumber } 
    ::=  { intervalPhysPerfOpticalInputPwr1weekTable  1  }

IntervalPhysPerfOpticalInputPwr1weekEntry ::=  SEQUENCE
  { intervalPhysPerfOpticalInputPwr1weekNumber Integer32,
    intervalPhysPerfOpticalInputPwr1weekLow Integer32,
    intervalPhysPerfOpticalInputPwr1weekMean Integer32,
    intervalPhysPerfOpticalInputPwr1weekHigh Integer32,
    intervalPhysPerfOpticalInputPwr1weekValidFlag TruthValue,
    intervalPhysPerfOpticalInputPwr1weekTimeStamp DateAndTime }


  
intervalPhysPerfOpticalInputPwr1weekNumber OBJECT-TYPE
    SYNTAX      Integer32 (1..52)
    MAX-ACCESS  not-accessible
    STATUS      current 
    DESCRIPTION
        "Number 1week" 
    ::=  { intervalPhysPerfOpticalInputPwr1weekEntry 1 }

intervalPhysPerfOpticalInputPwr1weekLow OBJECT-TYPE
    SYNTAX      Integer32
    UNITS       "0.1 dBm"
    MAX-ACCESS  read-only
    STATUS      current 
    DESCRIPTION
        "Optical Input Power Received" 
    ::=  { intervalPhysPerfOpticalInputPwr1weekEntry 2 }

intervalPhysPerfOpticalInputPwr1weekMean OBJECT-TYPE
    SYNTAX      Integer32
    UNITS       "0.1 dBm"
    MAX-ACCESS  read-only
    STATUS      current 
    DESCRIPTION
        "Optical Input Power Received" 
    ::=  { intervalPhysPerfOpticalInputPwr1weekEntry 3 }

intervalPhysPerfOpticalInputPwr1weekHigh OBJECT-TYPE
    SYNTAX      Integer32
    UNITS       "0.1 dBm"
    MAX-ACCESS  read-only
    STATUS      current 
    DESCRIPTION
        "Optical Input Power Received" 
    ::=  { intervalPhysPerfOpticalInputPwr1weekEntry 4 }

intervalPhysPerfOpticalInputPwr1weekValidFlag OBJECT-TYPE
    SYNTAX      TruthValue
    MAX-ACCESS  read-only
    STATUS      current 
    DESCRIPTION
        "" 
    ::=  { intervalPhysPerfOpticalInputPwr1weekEntry 5 }

intervalPhysPerfOpticalInputPwr1weekTimeStamp OBJECT-TYPE
    SYNTAX      DateAndTime
    MAX-ACCESS  read-only
    STATUS      current 
    DESCRIPTION
        "Timestamp" 
    ::=  { intervalPhysPerfOpticalInputPwr1weekEntry 6 }

intervalPhysPerfOpticalOutputPwr15minTable OBJECT-TYPE
    SYNTAX      SEQUENCE OF IntervalPhysPerfOpticalOutputPwr15minEntry
    MAX-ACCESS  not-accessible
    STATUS      current 
    DESCRIPTION
        "" 
    ::=  { performanceMonitoring 36 }

intervalPhysPerfOpticalOutputPwr15minEntry OBJECT-TYPE
    SYNTAX      IntervalPhysPerfOpticalOutputPwr15minEntry
    MAX-ACCESS  not-accessible
    STATUS      current 
    DESCRIPTION
        "" 
    INDEX       { entityIndex,intervalPhysPerfOpticalOutputPwr15minNumber } 
    ::=  { intervalPhysPerfOpticalOutputPwr15minTable  1  }

IntervalPhysPerfOpticalOutputPwr15minEntry ::=  SEQUENCE
  { intervalPhysPerfOpticalOutputPwr15minNumber Integer32,
    intervalPhysPerfOpticalOutputPwr15minLow Integer32,
    intervalPhysPerfOpticalOutputPwr15minMean Integer32,
    intervalPhysPerfOpticalOutputPwr15minHigh Integer32,
    intervalPhysPerfOpticalOutputPwr15minValidFlag TruthValue,
    intervalPhysPerfOpticalOutputPwr15minTimeStamp DateAndTime }


  
intervalPhysPerfOpticalOutputPwr15minNumber OBJECT-TYPE
    SYNTAX      Integer32 (1..96)
    MAX-ACCESS  not-accessible
    STATUS      current 
    DESCRIPTION
        "Number 15min" 
    ::=  { intervalPhysPerfOpticalOutputPwr15minEntry 1 }

intervalPhysPerfOpticalOutputPwr15minLow OBJECT-TYPE
    SYNTAX      Integer32
    UNITS       "0.1 dBm"
    MAX-ACCESS  read-only
    STATUS      current 
    DESCRIPTION
        "Optical Output Power Transmitted" 
    ::=  { intervalPhysPerfOpticalOutputPwr15minEntry 2 }

intervalPhysPerfOpticalOutputPwr15minMean OBJECT-TYPE
    SYNTAX      Integer32
    UNITS       "0.1 dBm"
    MAX-ACCESS  read-only
    STATUS      current 
    DESCRIPTION
        "Optical Output Power Transmitted" 
    ::=  { intervalPhysPerfOpticalOutputPwr15minEntry 3 }

intervalPhysPerfOpticalOutputPwr15minHigh OBJECT-TYPE
    SYNTAX      Integer32
    UNITS       "0.1 dBm"
    MAX-ACCESS  read-only
    STATUS      current 
    DESCRIPTION
        "Optical Output Power Transmitted" 
    ::=  { intervalPhysPerfOpticalOutputPwr15minEntry 4 }

intervalPhysPerfOpticalOutputPwr15minValidFlag OBJECT-TYPE
    SYNTAX      TruthValue
    MAX-ACCESS  read-only
    STATUS      current 
    DESCRIPTION
        "" 
    ::=  { intervalPhysPerfOpticalOutputPwr15minEntry 5 }

intervalPhysPerfOpticalOutputPwr15minTimeStamp OBJECT-TYPE
    SYNTAX      DateAndTime
    MAX-ACCESS  read-only
    STATUS      current 
    DESCRIPTION
        "Timestamp" 
    ::=  { intervalPhysPerfOpticalOutputPwr15minEntry 6 }

intervalPhysPerfOpticalOutputPwr1dayTable OBJECT-TYPE
    SYNTAX      SEQUENCE OF IntervalPhysPerfOpticalOutputPwr1dayEntry
    MAX-ACCESS  not-accessible
    STATUS      current 
    DESCRIPTION
        "" 
    ::=  { performanceMonitoring 37 }

intervalPhysPerfOpticalOutputPwr1dayEntry OBJECT-TYPE
    SYNTAX      IntervalPhysPerfOpticalOutputPwr1dayEntry
    MAX-ACCESS  not-accessible
    STATUS      current 
    DESCRIPTION
        "" 
    INDEX       { entityIndex,intervalPhysPerfOpticalOutputPwr1dayNumber } 
    ::=  { intervalPhysPerfOpticalOutputPwr1dayTable  1  }

IntervalPhysPerfOpticalOutputPwr1dayEntry ::=  SEQUENCE
  { intervalPhysPerfOpticalOutputPwr1dayNumber Integer32,
    intervalPhysPerfOpticalOutputPwr1dayLow Integer32,
    intervalPhysPerfOpticalOutputPwr1dayMean Integer32,
    intervalPhysPerfOpticalOutputPwr1dayHigh Integer32,
    intervalPhysPerfOpticalOutputPwr1dayValidFlag TruthValue,
    intervalPhysPerfOpticalOutputPwr1dayTimeStamp DateAndTime }


  
intervalPhysPerfOpticalOutputPwr1dayNumber OBJECT-TYPE
    SYNTAX      Integer32 (1..31)
    MAX-ACCESS  not-accessible
    STATUS      current 
    DESCRIPTION
        "Number 1day" 
    ::=  { intervalPhysPerfOpticalOutputPwr1dayEntry 1 }

intervalPhysPerfOpticalOutputPwr1dayLow OBJECT-TYPE
    SYNTAX      Integer32
    UNITS       "0.1 dBm"
    MAX-ACCESS  read-only
    STATUS      current 
    DESCRIPTION
        "Optical Output Power Transmitted" 
    ::=  { intervalPhysPerfOpticalOutputPwr1dayEntry 2 }

intervalPhysPerfOpticalOutputPwr1dayMean OBJECT-TYPE
    SYNTAX      Integer32
    UNITS       "0.1 dBm"
    MAX-ACCESS  read-only
    STATUS      current 
    DESCRIPTION
        "Optical Output Power Transmitted" 
    ::=  { intervalPhysPerfOpticalOutputPwr1dayEntry 3 }

intervalPhysPerfOpticalOutputPwr1dayHigh OBJECT-TYPE
    SYNTAX      Integer32
    UNITS       "0.1 dBm"
    MAX-ACCESS  read-only
    STATUS      current 
    DESCRIPTION
        "Optical Output Power Transmitted" 
    ::=  { intervalPhysPerfOpticalOutputPwr1dayEntry 4 }

intervalPhysPerfOpticalOutputPwr1dayValidFlag OBJECT-TYPE
    SYNTAX      TruthValue
    MAX-ACCESS  read-only
    STATUS      current 
    DESCRIPTION
        "" 
    ::=  { intervalPhysPerfOpticalOutputPwr1dayEntry 5 }

intervalPhysPerfOpticalOutputPwr1dayTimeStamp OBJECT-TYPE
    SYNTAX      DateAndTime
    MAX-ACCESS  read-only
    STATUS      current 
    DESCRIPTION
        "Timestamp" 
    ::=  { intervalPhysPerfOpticalOutputPwr1dayEntry 6 }

intervalPhysPerfOpticalOutputPwr1weekTable OBJECT-TYPE
    SYNTAX      SEQUENCE OF IntervalPhysPerfOpticalOutputPwr1weekEntry
    MAX-ACCESS  not-accessible
    STATUS      current 
    DESCRIPTION
        "" 
    ::=  { performanceMonitoring 38 }

intervalPhysPerfOpticalOutputPwr1weekEntry OBJECT-TYPE
    SYNTAX      IntervalPhysPerfOpticalOutputPwr1weekEntry
    MAX-ACCESS  not-accessible
    STATUS      current 
    DESCRIPTION
        "" 
    INDEX       { entityIndex,intervalPhysPerfOpticalOutputPwr1weekNumber } 
    ::=  { intervalPhysPerfOpticalOutputPwr1weekTable  1  }

IntervalPhysPerfOpticalOutputPwr1weekEntry ::=  SEQUENCE
  { intervalPhysPerfOpticalOutputPwr1weekNumber Integer32,
    intervalPhysPerfOpticalOutputPwr1weekLow Integer32,
    intervalPhysPerfOpticalOutputPwr1weekMean Integer32,
    intervalPhysPerfOpticalOutputPwr1weekHigh Integer32,
    intervalPhysPerfOpticalOutputPwr1weekValidFlag TruthValue,
    intervalPhysPerfOpticalOutputPwr1weekTimeStamp DateAndTime }


  
intervalPhysPerfOpticalOutputPwr1weekNumber OBJECT-TYPE
    SYNTAX      Integer32 (1..52)
    MAX-ACCESS  not-accessible
    STATUS      current 
    DESCRIPTION
        "Number 1week" 
    ::=  { intervalPhysPerfOpticalOutputPwr1weekEntry 1 }

intervalPhysPerfOpticalOutputPwr1weekLow OBJECT-TYPE
    SYNTAX      Integer32
    UNITS       "0.1 dBm"
    MAX-ACCESS  read-only
    STATUS      current 
    DESCRIPTION
        "Optical Output Power Transmitted" 
    ::=  { intervalPhysPerfOpticalOutputPwr1weekEntry 2 }

intervalPhysPerfOpticalOutputPwr1weekMean OBJECT-TYPE
    SYNTAX      Integer32
    UNITS       "0.1 dBm"
    MAX-ACCESS  read-only
    STATUS      current 
    DESCRIPTION
        "Optical Output Power Transmitted" 
    ::=  { intervalPhysPerfOpticalOutputPwr1weekEntry 3 }

intervalPhysPerfOpticalOutputPwr1weekHigh OBJECT-TYPE
    SYNTAX      Integer32
    UNITS       "0.1 dBm"
    MAX-ACCESS  read-only
    STATUS      current 
    DESCRIPTION
        "Optical Output Power Transmitted" 
    ::=  { intervalPhysPerfOpticalOutputPwr1weekEntry 4 }

intervalPhysPerfOpticalOutputPwr1weekValidFlag OBJECT-TYPE
    SYNTAX      TruthValue
    MAX-ACCESS  read-only
    STATUS      current 
    DESCRIPTION
        "" 
    ::=  { intervalPhysPerfOpticalOutputPwr1weekEntry 5 }

intervalPhysPerfOpticalOutputPwr1weekTimeStamp OBJECT-TYPE
    SYNTAX      DateAndTime
    MAX-ACCESS  read-only
    STATUS      current 
    DESCRIPTION
        "Timestamp" 
    ::=  { intervalPhysPerfOpticalOutputPwr1weekEntry 6 }

intervalPhysPerfLaserBiasCurrentNormalized15minTable OBJECT-TYPE
    SYNTAX      SEQUENCE OF IntervalPhysPerfLaserBiasCurrentNormalized15minEntry
    MAX-ACCESS  not-accessible
    STATUS      current 
    DESCRIPTION
        "" 
    ::=  { performanceMonitoring 39 }

intervalPhysPerfLaserBiasCurrentNormalized15minEntry OBJECT-TYPE
    SYNTAX      IntervalPhysPerfLaserBiasCurrentNormalized15minEntry
    MAX-ACCESS  not-accessible
    STATUS      current 
    DESCRIPTION
        "" 
    INDEX       { entityIndex,intervalPhysPerfLaserBiasCurrentNormalized15minNumber } 
    ::=  { intervalPhysPerfLaserBiasCurrentNormalized15minTable  1  }

IntervalPhysPerfLaserBiasCurrentNormalized15minEntry ::=  SEQUENCE
  { intervalPhysPerfLaserBiasCurrentNormalized15minNumber Integer32,
    intervalPhysPerfLaserBiasCurrentNormalized15minLow Unsigned32,
    intervalPhysPerfLaserBiasCurrentNormalized15minMean Unsigned32,
    intervalPhysPerfLaserBiasCurrentNormalized15minHigh Unsigned32,
    intervalPhysPerfLaserBiasCurrentNormalized15minValidFlag TruthValue,
    intervalPhysPerfLaserBiasCurrentNormalized15minTimeStamp DateAndTime }


  
intervalPhysPerfLaserBiasCurrentNormalized15minNumber OBJECT-TYPE
    SYNTAX      Integer32 (1..96)
    MAX-ACCESS  not-accessible
    STATUS      current 
    DESCRIPTION
        "Number 15min" 
    ::=  { intervalPhysPerfLaserBiasCurrentNormalized15minEntry 1 }

intervalPhysPerfLaserBiasCurrentNormalized15minLow OBJECT-TYPE
    SYNTAX      Unsigned32
    UNITS       "%"
    MAX-ACCESS  read-only
    STATUS      current 
    DESCRIPTION
        "Laser Bias Current Normalized" 
    ::=  { intervalPhysPerfLaserBiasCurrentNormalized15minEntry 2 }

intervalPhysPerfLaserBiasCurrentNormalized15minMean OBJECT-TYPE
    SYNTAX      Unsigned32
    UNITS       "%"
    MAX-ACCESS  read-only
    STATUS      current 
    DESCRIPTION
        "Laser Bias Current Normalized" 
    ::=  { intervalPhysPerfLaserBiasCurrentNormalized15minEntry 3 }

intervalPhysPerfLaserBiasCurrentNormalized15minHigh OBJECT-TYPE
    SYNTAX      Unsigned32
    UNITS       "%"
    MAX-ACCESS  read-only
    STATUS      current 
    DESCRIPTION
        "Laser Bias Current Normalized" 
    ::=  { intervalPhysPerfLaserBiasCurrentNormalized15minEntry 4 }

intervalPhysPerfLaserBiasCurrentNormalized15minValidFlag OBJECT-TYPE
    SYNTAX      TruthValue
    MAX-ACCESS  read-only
    STATUS      current 
    DESCRIPTION
        "" 
    ::=  { intervalPhysPerfLaserBiasCurrentNormalized15minEntry 5 }

intervalPhysPerfLaserBiasCurrentNormalized15minTimeStamp OBJECT-TYPE
    SYNTAX      DateAndTime
    MAX-ACCESS  read-only
    STATUS      current 
    DESCRIPTION
        "Timestamp" 
    ::=  { intervalPhysPerfLaserBiasCurrentNormalized15minEntry 6 }

intervalPhysPerfLaserBiasCurrentNormalized1dayTable OBJECT-TYPE
    SYNTAX      SEQUENCE OF IntervalPhysPerfLaserBiasCurrentNormalized1dayEntry
    MAX-ACCESS  not-accessible
    STATUS      current 
    DESCRIPTION
        "" 
    ::=  { performanceMonitoring 40 }

intervalPhysPerfLaserBiasCurrentNormalized1dayEntry OBJECT-TYPE
    SYNTAX      IntervalPhysPerfLaserBiasCurrentNormalized1dayEntry
    MAX-ACCESS  not-accessible
    STATUS      current 
    DESCRIPTION
        "" 
    INDEX       { entityIndex,intervalPhysPerfLaserBiasCurrentNormalized1dayNumber } 
    ::=  { intervalPhysPerfLaserBiasCurrentNormalized1dayTable  1  }

IntervalPhysPerfLaserBiasCurrentNormalized1dayEntry ::=  SEQUENCE
  { intervalPhysPerfLaserBiasCurrentNormalized1dayNumber Integer32,
    intervalPhysPerfLaserBiasCurrentNormalized1dayLow Unsigned32,
    intervalPhysPerfLaserBiasCurrentNormalized1dayMean Unsigned32,
    intervalPhysPerfLaserBiasCurrentNormalized1dayHigh Unsigned32,
    intervalPhysPerfLaserBiasCurrentNormalized1dayValidFlag TruthValue,
    intervalPhysPerfLaserBiasCurrentNormalized1dayTimeStamp DateAndTime }


  
intervalPhysPerfLaserBiasCurrentNormalized1dayNumber OBJECT-TYPE
    SYNTAX      Integer32 (1..31)
    MAX-ACCESS  not-accessible
    STATUS      current 
    DESCRIPTION
        "Number 1day" 
    ::=  { intervalPhysPerfLaserBiasCurrentNormalized1dayEntry 1 }

intervalPhysPerfLaserBiasCurrentNormalized1dayLow OBJECT-TYPE
    SYNTAX      Unsigned32
    UNITS       "%"
    MAX-ACCESS  read-only
    STATUS      current 
    DESCRIPTION
        "Laser Bias Current Normalized" 
    ::=  { intervalPhysPerfLaserBiasCurrentNormalized1dayEntry 2 }

intervalPhysPerfLaserBiasCurrentNormalized1dayMean OBJECT-TYPE
    SYNTAX      Unsigned32
    UNITS       "%"
    MAX-ACCESS  read-only
    STATUS      current 
    DESCRIPTION
        "Laser Bias Current Normalized" 
    ::=  { intervalPhysPerfLaserBiasCurrentNormalized1dayEntry 3 }

intervalPhysPerfLaserBiasCurrentNormalized1dayHigh OBJECT-TYPE
    SYNTAX      Unsigned32
    UNITS       "%"
    MAX-ACCESS  read-only
    STATUS      current 
    DESCRIPTION
        "Laser Bias Current Normalized" 
    ::=  { intervalPhysPerfLaserBiasCurrentNormalized1dayEntry 4 }

intervalPhysPerfLaserBiasCurrentNormalized1dayValidFlag OBJECT-TYPE
    SYNTAX      TruthValue
    MAX-ACCESS  read-only
    STATUS      current 
    DESCRIPTION
        "" 
    ::=  { intervalPhysPerfLaserBiasCurrentNormalized1dayEntry 5 }

intervalPhysPerfLaserBiasCurrentNormalized1dayTimeStamp OBJECT-TYPE
    SYNTAX      DateAndTime
    MAX-ACCESS  read-only
    STATUS      current 
    DESCRIPTION
        "Timestamp" 
    ::=  { intervalPhysPerfLaserBiasCurrentNormalized1dayEntry 6 }

intervalPhysPerfLaserBiasCurrentNormalized1weekTable OBJECT-TYPE
    SYNTAX      SEQUENCE OF IntervalPhysPerfLaserBiasCurrentNormalized1weekEntry
    MAX-ACCESS  not-accessible
    STATUS      current 
    DESCRIPTION
        "" 
    ::=  { performanceMonitoring 41 }

intervalPhysPerfLaserBiasCurrentNormalized1weekEntry OBJECT-TYPE
    SYNTAX      IntervalPhysPerfLaserBiasCurrentNormalized1weekEntry
    MAX-ACCESS  not-accessible
    STATUS      current 
    DESCRIPTION
        "" 
    INDEX       { entityIndex,intervalPhysPerfLaserBiasCurrentNormalized1weekNumber } 
    ::=  { intervalPhysPerfLaserBiasCurrentNormalized1weekTable  1  }

IntervalPhysPerfLaserBiasCurrentNormalized1weekEntry ::=  SEQUENCE
  { intervalPhysPerfLaserBiasCurrentNormalized1weekNumber Integer32,
    intervalPhysPerfLaserBiasCurrentNormalized1weekLow Unsigned32,
    intervalPhysPerfLaserBiasCurrentNormalized1weekMean Unsigned32,
    intervalPhysPerfLaserBiasCurrentNormalized1weekHigh Unsigned32,
    intervalPhysPerfLaserBiasCurrentNormalized1weekValidFlag TruthValue,
    intervalPhysPerfLaserBiasCurrentNormalized1weekTimeStamp DateAndTime }


  
intervalPhysPerfLaserBiasCurrentNormalized1weekNumber OBJECT-TYPE
    SYNTAX      Integer32 (1..52)
    MAX-ACCESS  not-accessible
    STATUS      current 
    DESCRIPTION
        "Number 1week" 
    ::=  { intervalPhysPerfLaserBiasCurrentNormalized1weekEntry 1 }

intervalPhysPerfLaserBiasCurrentNormalized1weekLow OBJECT-TYPE
    SYNTAX      Unsigned32
    UNITS       "%"
    MAX-ACCESS  read-only
    STATUS      current 
    DESCRIPTION
        "Laser Bias Current Normalized" 
    ::=  { intervalPhysPerfLaserBiasCurrentNormalized1weekEntry 2 }

intervalPhysPerfLaserBiasCurrentNormalized1weekMean OBJECT-TYPE
    SYNTAX      Unsigned32
    UNITS       "%"
    MAX-ACCESS  read-only
    STATUS      current 
    DESCRIPTION
        "Laser Bias Current Normalized" 
    ::=  { intervalPhysPerfLaserBiasCurrentNormalized1weekEntry 3 }

intervalPhysPerfLaserBiasCurrentNormalized1weekHigh OBJECT-TYPE
    SYNTAX      Unsigned32
    UNITS       "%"
    MAX-ACCESS  read-only
    STATUS      current 
    DESCRIPTION
        "Laser Bias Current Normalized" 
    ::=  { intervalPhysPerfLaserBiasCurrentNormalized1weekEntry 4 }

intervalPhysPerfLaserBiasCurrentNormalized1weekValidFlag OBJECT-TYPE
    SYNTAX      TruthValue
    MAX-ACCESS  read-only
    STATUS      current 
    DESCRIPTION
        "" 
    ::=  { intervalPhysPerfLaserBiasCurrentNormalized1weekEntry 5 }

intervalPhysPerfLaserBiasCurrentNormalized1weekTimeStamp OBJECT-TYPE
    SYNTAX      DateAndTime
    MAX-ACCESS  read-only
    STATUS      current 
    DESCRIPTION
        "Timestamp" 
    ::=  { intervalPhysPerfLaserBiasCurrentNormalized1weekEntry 6 }

intervalPhysPerfOlmRxLineAtt15minTable OBJECT-TYPE
    SYNTAX      SEQUENCE OF IntervalPhysPerfOlmRxLineAtt15minEntry
    MAX-ACCESS  not-accessible
    STATUS      current 
    DESCRIPTION
        "" 
    ::=  { performanceMonitoring 42 }

intervalPhysPerfOlmRxLineAtt15minEntry OBJECT-TYPE
    SYNTAX      IntervalPhysPerfOlmRxLineAtt15minEntry
    MAX-ACCESS  not-accessible
    STATUS      current 
    DESCRIPTION
        "" 
    INDEX       { entityIndex,intervalPhysPerfOlmRxLineAtt15minNumber } 
    ::=  { intervalPhysPerfOlmRxLineAtt15minTable  1  }

IntervalPhysPerfOlmRxLineAtt15minEntry ::=  SEQUENCE
  { intervalPhysPerfOlmRxLineAtt15minNumber Integer32,
    intervalPhysPerfOlmRxLineAtt15minLow Integer32,
    intervalPhysPerfOlmRxLineAtt15minMean Integer32,
    intervalPhysPerfOlmRxLineAtt15minHigh Integer32,
    intervalPhysPerfOlmRxLineAtt15minValidFlag TruthValue,
    intervalPhysPerfOlmRxLineAtt15minTimeStamp DateAndTime }


  
intervalPhysPerfOlmRxLineAtt15minNumber OBJECT-TYPE
    SYNTAX      Integer32 (1..96)
    MAX-ACCESS  not-accessible
    STATUS      current 
    DESCRIPTION
        "Number 15min" 
    ::=  { intervalPhysPerfOlmRxLineAtt15minEntry 1 }

intervalPhysPerfOlmRxLineAtt15minLow OBJECT-TYPE
    SYNTAX      Integer32
    UNITS       "0.1 dB"
    MAX-ACCESS  read-only
    STATUS      current 
    DESCRIPTION
        "Low Attenuation on Receive Fiber" 
    ::=  { intervalPhysPerfOlmRxLineAtt15minEntry 2 }

intervalPhysPerfOlmRxLineAtt15minMean OBJECT-TYPE
    SYNTAX      Integer32
    UNITS       "0.1 dB"
    MAX-ACCESS  read-only
    STATUS      current 
    DESCRIPTION
        "Mean Attenuation on Receive Fiber" 
    ::=  { intervalPhysPerfOlmRxLineAtt15minEntry 3 }

intervalPhysPerfOlmRxLineAtt15minHigh OBJECT-TYPE
    SYNTAX      Integer32
    UNITS       "0.1 dB"
    MAX-ACCESS  read-only
    STATUS      current 
    DESCRIPTION
        "High Attenuation on Receive Fiber" 
    ::=  { intervalPhysPerfOlmRxLineAtt15minEntry 4 }

intervalPhysPerfOlmRxLineAtt15minValidFlag OBJECT-TYPE
    SYNTAX      TruthValue
    MAX-ACCESS  read-only
    STATUS      current 
    DESCRIPTION
        "" 
    ::=  { intervalPhysPerfOlmRxLineAtt15minEntry 5 }

intervalPhysPerfOlmRxLineAtt15minTimeStamp OBJECT-TYPE
    SYNTAX      DateAndTime
    MAX-ACCESS  read-only
    STATUS      current 
    DESCRIPTION
        "Timestamp" 
    ::=  { intervalPhysPerfOlmRxLineAtt15minEntry 6 }

intervalPhysPerfOlmRxLineAtt1dayTable OBJECT-TYPE
    SYNTAX      SEQUENCE OF IntervalPhysPerfOlmRxLineAtt1dayEntry
    MAX-ACCESS  not-accessible
    STATUS      current 
    DESCRIPTION
        "" 
    ::=  { performanceMonitoring 43 }

intervalPhysPerfOlmRxLineAtt1dayEntry OBJECT-TYPE
    SYNTAX      IntervalPhysPerfOlmRxLineAtt1dayEntry
    MAX-ACCESS  not-accessible
    STATUS      current 
    DESCRIPTION
        "" 
    INDEX       { entityIndex,intervalPhysPerfOlmRxLineAtt1dayNumber } 
    ::=  { intervalPhysPerfOlmRxLineAtt1dayTable  1  }

IntervalPhysPerfOlmRxLineAtt1dayEntry ::=  SEQUENCE
  { intervalPhysPerfOlmRxLineAtt1dayNumber Integer32,
    intervalPhysPerfOlmRxLineAtt1dayLow Integer32,
    intervalPhysPerfOlmRxLineAtt1dayMean Integer32,
    intervalPhysPerfOlmRxLineAtt1dayHigh Integer32,
    intervalPhysPerfOlmRxLineAtt1dayValidFlag TruthValue,
    intervalPhysPerfOlmRxLineAtt1dayTimeStamp DateAndTime }


  
intervalPhysPerfOlmRxLineAtt1dayNumber OBJECT-TYPE
    SYNTAX      Integer32 (1..31)
    MAX-ACCESS  not-accessible
    STATUS      current 
    DESCRIPTION
        "Number 1day" 
    ::=  { intervalPhysPerfOlmRxLineAtt1dayEntry 1 }

intervalPhysPerfOlmRxLineAtt1dayLow OBJECT-TYPE
    SYNTAX      Integer32
    UNITS       "0.1 dB"
    MAX-ACCESS  read-only
    STATUS      current 
    DESCRIPTION
        "Low Attenuation on Receive Fiber" 
    ::=  { intervalPhysPerfOlmRxLineAtt1dayEntry 2 }

intervalPhysPerfOlmRxLineAtt1dayMean OBJECT-TYPE
    SYNTAX      Integer32
    UNITS       "0.1 dB"
    MAX-ACCESS  read-only
    STATUS      current 
    DESCRIPTION
        "Mean Attenuation on Receive Fiber" 
    ::=  { intervalPhysPerfOlmRxLineAtt1dayEntry 3 }

intervalPhysPerfOlmRxLineAtt1dayHigh OBJECT-TYPE
    SYNTAX      Integer32
    UNITS       "0.1 dB"
    MAX-ACCESS  read-only
    STATUS      current 
    DESCRIPTION
        "High Attenuation on Receive Fiber" 
    ::=  { intervalPhysPerfOlmRxLineAtt1dayEntry 4 }

intervalPhysPerfOlmRxLineAtt1dayValidFlag OBJECT-TYPE
    SYNTAX      TruthValue
    MAX-ACCESS  read-only
    STATUS      current 
    DESCRIPTION
        "" 
    ::=  { intervalPhysPerfOlmRxLineAtt1dayEntry 5 }

intervalPhysPerfOlmRxLineAtt1dayTimeStamp OBJECT-TYPE
    SYNTAX      DateAndTime
    MAX-ACCESS  read-only
    STATUS      current 
    DESCRIPTION
        "Timestamp" 
    ::=  { intervalPhysPerfOlmRxLineAtt1dayEntry 6 }

intervalPhysPerfOlmRxLineAtt1weekTable OBJECT-TYPE
    SYNTAX      SEQUENCE OF IntervalPhysPerfOlmRxLineAtt1weekEntry
    MAX-ACCESS  not-accessible
    STATUS      current 
    DESCRIPTION
        "" 
    ::=  { performanceMonitoring 44 }

intervalPhysPerfOlmRxLineAtt1weekEntry OBJECT-TYPE
    SYNTAX      IntervalPhysPerfOlmRxLineAtt1weekEntry
    MAX-ACCESS  not-accessible
    STATUS      current 
    DESCRIPTION
        "" 
    INDEX       { entityIndex,intervalPhysPerfOlmRxLineAtt1weekNumber } 
    ::=  { intervalPhysPerfOlmRxLineAtt1weekTable  1  }

IntervalPhysPerfOlmRxLineAtt1weekEntry ::=  SEQUENCE
  { intervalPhysPerfOlmRxLineAtt1weekNumber Integer32,
    intervalPhysPerfOlmRxLineAtt1weekLow Integer32,
    intervalPhysPerfOlmRxLineAtt1weekMean Integer32,
    intervalPhysPerfOlmRxLineAtt1weekHigh Integer32,
    intervalPhysPerfOlmRxLineAtt1weekValidFlag TruthValue,
    intervalPhysPerfOlmRxLineAtt1weekTimeStamp DateAndTime }


  
intervalPhysPerfOlmRxLineAtt1weekNumber OBJECT-TYPE
    SYNTAX      Integer32 (1..52)
    MAX-ACCESS  not-accessible
    STATUS      current 
    DESCRIPTION
        "Number 1week" 
    ::=  { intervalPhysPerfOlmRxLineAtt1weekEntry 1 }

intervalPhysPerfOlmRxLineAtt1weekLow OBJECT-TYPE
    SYNTAX      Integer32
    UNITS       "0.1 dB"
    MAX-ACCESS  read-only
    STATUS      current 
    DESCRIPTION
        "Low Attenuation on Receive Fiber" 
    ::=  { intervalPhysPerfOlmRxLineAtt1weekEntry 2 }

intervalPhysPerfOlmRxLineAtt1weekMean OBJECT-TYPE
    SYNTAX      Integer32
    UNITS       "0.1 dB"
    MAX-ACCESS  read-only
    STATUS      current 
    DESCRIPTION
        "Mean Attenuation on Receive Fiber" 
    ::=  { intervalPhysPerfOlmRxLineAtt1weekEntry 3 }

intervalPhysPerfOlmRxLineAtt1weekHigh OBJECT-TYPE
    SYNTAX      Integer32
    UNITS       "0.1 dB"
    MAX-ACCESS  read-only
    STATUS      current 
    DESCRIPTION
        "High Attenuation on Receive Fiber" 
    ::=  { intervalPhysPerfOlmRxLineAtt1weekEntry 4 }

intervalPhysPerfOlmRxLineAtt1weekValidFlag OBJECT-TYPE
    SYNTAX      TruthValue
    MAX-ACCESS  read-only
    STATUS      current 
    DESCRIPTION
        "" 
    ::=  { intervalPhysPerfOlmRxLineAtt1weekEntry 5 }

intervalPhysPerfOlmRxLineAtt1weekTimeStamp OBJECT-TYPE
    SYNTAX      DateAndTime
    MAX-ACCESS  read-only
    STATUS      current 
    DESCRIPTION
        "Timestamp" 
    ::=  { intervalPhysPerfOlmRxLineAtt1weekEntry 6 }

intervalPhysPerfOlmTxLineAtt15minTable OBJECT-TYPE
    SYNTAX      SEQUENCE OF IntervalPhysPerfOlmTxLineAtt15minEntry
    MAX-ACCESS  not-accessible
    STATUS      current 
    DESCRIPTION
        "" 
    ::=  { performanceMonitoring 45 }

intervalPhysPerfOlmTxLineAtt15minEntry OBJECT-TYPE
    SYNTAX      IntervalPhysPerfOlmTxLineAtt15minEntry
    MAX-ACCESS  not-accessible
    STATUS      current 
    DESCRIPTION
        "" 
    INDEX       { entityIndex,intervalPhysPerfOlmTxLineAtt15minNumber } 
    ::=  { intervalPhysPerfOlmTxLineAtt15minTable  1  }

IntervalPhysPerfOlmTxLineAtt15minEntry ::=  SEQUENCE
  { intervalPhysPerfOlmTxLineAtt15minNumber Integer32,
    intervalPhysPerfOlmTxLineAtt15minLow Integer32,
    intervalPhysPerfOlmTxLineAtt15minHigh Integer32,
    intervalPhysPerfOlmTxLineAtt15minMean Integer32,
    intervalPhysPerfOlmTxLineAtt15minValidFlag TruthValue,
    intervalPhysPerfOlmTxLineAtt15minTimeStamp DateAndTime }


  
intervalPhysPerfOlmTxLineAtt15minNumber OBJECT-TYPE
    SYNTAX      Integer32 (1..96)
    MAX-ACCESS  not-accessible
    STATUS      current 
    DESCRIPTION
        "Number 15min" 
    ::=  { intervalPhysPerfOlmTxLineAtt15minEntry 1 }

intervalPhysPerfOlmTxLineAtt15minLow OBJECT-TYPE
    SYNTAX      Integer32
    UNITS       "0.1 dB"
    MAX-ACCESS  read-only
    STATUS      current 
    DESCRIPTION
        "Low Attenuation on Transmit Fiber" 
    ::=  { intervalPhysPerfOlmTxLineAtt15minEntry 2 }

intervalPhysPerfOlmTxLineAtt15minHigh OBJECT-TYPE
    SYNTAX      Integer32
    UNITS       "0.1 dB"
    MAX-ACCESS  read-only
    STATUS      current 
    DESCRIPTION
        "Mean Attenuation on Transmit Fiber" 
    ::=  { intervalPhysPerfOlmTxLineAtt15minEntry 3 }

intervalPhysPerfOlmTxLineAtt15minMean OBJECT-TYPE
    SYNTAX      Integer32
    UNITS       "0.1 dB"
    MAX-ACCESS  read-only
    STATUS      current 
    DESCRIPTION
        "High Attenuation on Transmit Fiber" 
    ::=  { intervalPhysPerfOlmTxLineAtt15minEntry 4 }

intervalPhysPerfOlmTxLineAtt15minValidFlag OBJECT-TYPE
    SYNTAX      TruthValue
    MAX-ACCESS  read-only
    STATUS      current 
    DESCRIPTION
        "" 
    ::=  { intervalPhysPerfOlmTxLineAtt15minEntry 5 }

intervalPhysPerfOlmTxLineAtt15minTimeStamp OBJECT-TYPE
    SYNTAX      DateAndTime
    MAX-ACCESS  read-only
    STATUS      current 
    DESCRIPTION
        "Timestamp" 
    ::=  { intervalPhysPerfOlmTxLineAtt15minEntry 6 }

intervalPhysPerfOlmTxLineAtt1dayTable OBJECT-TYPE
    SYNTAX      SEQUENCE OF IntervalPhysPerfOlmTxLineAtt1dayEntry
    MAX-ACCESS  not-accessible
    STATUS      current 
    DESCRIPTION
        "" 
    ::=  { performanceMonitoring 46 }

intervalPhysPerfOlmTxLineAtt1dayEntry OBJECT-TYPE
    SYNTAX      IntervalPhysPerfOlmTxLineAtt1dayEntry
    MAX-ACCESS  not-accessible
    STATUS      current 
    DESCRIPTION
        "" 
    INDEX       { entityIndex,intervalPhysPerfOlmTxLineAtt1dayNumber } 
    ::=  { intervalPhysPerfOlmTxLineAtt1dayTable  1  }

IntervalPhysPerfOlmTxLineAtt1dayEntry ::=  SEQUENCE
  { intervalPhysPerfOlmTxLineAtt1dayNumber Integer32,
    intervalPhysPerfOlmTxLineAtt1dayLow Integer32,
    intervalPhysPerfOlmTxLineAtt1dayHigh Integer32,
    intervalPhysPerfOlmTxLineAtt1dayMean Integer32,
    intervalPhysPerfOlmTxLineAtt1dayValidFlag TruthValue,
    intervalPhysPerfOlmTxLineAtt1dayTimeStamp DateAndTime }


  
intervalPhysPerfOlmTxLineAtt1dayNumber OBJECT-TYPE
    SYNTAX      Integer32 (1..31)
    MAX-ACCESS  not-accessible
    STATUS      current 
    DESCRIPTION
        "Number 1day" 
    ::=  { intervalPhysPerfOlmTxLineAtt1dayEntry 1 }

intervalPhysPerfOlmTxLineAtt1dayLow OBJECT-TYPE
    SYNTAX      Integer32
    UNITS       "0.1 dB"
    MAX-ACCESS  read-only
    STATUS      current 
    DESCRIPTION
        "Low Attenuation on Transmit Fiber" 
    ::=  { intervalPhysPerfOlmTxLineAtt1dayEntry 2 }

intervalPhysPerfOlmTxLineAtt1dayHigh OBJECT-TYPE
    SYNTAX      Integer32
    UNITS       "0.1 dB"
    MAX-ACCESS  read-only
    STATUS      current 
    DESCRIPTION
        "Mean Attenuation on Transmit Fiber" 
    ::=  { intervalPhysPerfOlmTxLineAtt1dayEntry 3 }

intervalPhysPerfOlmTxLineAtt1dayMean OBJECT-TYPE
    SYNTAX      Integer32
    UNITS       "0.1 dB"
    MAX-ACCESS  read-only
    STATUS      current 
    DESCRIPTION
        "High Attenuation on Transmit Fiber" 
    ::=  { intervalPhysPerfOlmTxLineAtt1dayEntry 4 }

intervalPhysPerfOlmTxLineAtt1dayValidFlag OBJECT-TYPE
    SYNTAX      TruthValue
    MAX-ACCESS  read-only
    STATUS      current 
    DESCRIPTION
        "" 
    ::=  { intervalPhysPerfOlmTxLineAtt1dayEntry 5 }

intervalPhysPerfOlmTxLineAtt1dayTimeStamp OBJECT-TYPE
    SYNTAX      DateAndTime
    MAX-ACCESS  read-only
    STATUS      current 
    DESCRIPTION
        "Timestamp" 
    ::=  { intervalPhysPerfOlmTxLineAtt1dayEntry 6 }

intervalPhysPerfOlmTxLineAtt1weekTable OBJECT-TYPE
    SYNTAX      SEQUENCE OF IntervalPhysPerfOlmTxLineAtt1weekEntry
    MAX-ACCESS  not-accessible
    STATUS      current 
    DESCRIPTION
        "" 
    ::=  { performanceMonitoring 47 }

intervalPhysPerfOlmTxLineAtt1weekEntry OBJECT-TYPE
    SYNTAX      IntervalPhysPerfOlmTxLineAtt1weekEntry
    MAX-ACCESS  not-accessible
    STATUS      current 
    DESCRIPTION
        "" 
    INDEX       { entityIndex,intervalPhysPerfOlmTxLineAtt1weekNumber } 
    ::=  { intervalPhysPerfOlmTxLineAtt1weekTable  1  }

IntervalPhysPerfOlmTxLineAtt1weekEntry ::=  SEQUENCE
  { intervalPhysPerfOlmTxLineAtt1weekNumber Integer32,
    intervalPhysPerfOlmTxLineAtt1weekLow Integer32,
    intervalPhysPerfOlmTxLineAtt1weekHigh Integer32,
    intervalPhysPerfOlmTxLineAtt1weekMean Integer32,
    intervalPhysPerfOlmTxLineAtt1weekValidFlag TruthValue,
    intervalPhysPerfOlmTxLineAtt1weekTimeStamp DateAndTime }


  
intervalPhysPerfOlmTxLineAtt1weekNumber OBJECT-TYPE
    SYNTAX      Integer32 (1..52)
    MAX-ACCESS  not-accessible
    STATUS      current 
    DESCRIPTION
        "Number 1week" 
    ::=  { intervalPhysPerfOlmTxLineAtt1weekEntry 1 }

intervalPhysPerfOlmTxLineAtt1weekLow OBJECT-TYPE
    SYNTAX      Integer32
    UNITS       "0.1 dB"
    MAX-ACCESS  read-only
    STATUS      current 
    DESCRIPTION
        "Low Attenuation on Transmit Fiber" 
    ::=  { intervalPhysPerfOlmTxLineAtt1weekEntry 2 }

intervalPhysPerfOlmTxLineAtt1weekHigh OBJECT-TYPE
    SYNTAX      Integer32
    UNITS       "0.1 dB"
    MAX-ACCESS  read-only
    STATUS      current 
    DESCRIPTION
        "Mean Attenuation on Transmit Fiber" 
    ::=  { intervalPhysPerfOlmTxLineAtt1weekEntry 3 }

intervalPhysPerfOlmTxLineAtt1weekMean OBJECT-TYPE
    SYNTAX      Integer32
    UNITS       "0.1 dB"
    MAX-ACCESS  read-only
    STATUS      current 
    DESCRIPTION
        "High Attenuation on Transmit Fiber" 
    ::=  { intervalPhysPerfOlmTxLineAtt1weekEntry 4 }

intervalPhysPerfOlmTxLineAtt1weekValidFlag OBJECT-TYPE
    SYNTAX      TruthValue
    MAX-ACCESS  read-only
    STATUS      current 
    DESCRIPTION
        "" 
    ::=  { intervalPhysPerfOlmTxLineAtt1weekEntry 5 }

intervalPhysPerfOlmTxLineAtt1weekTimeStamp OBJECT-TYPE
    SYNTAX      DateAndTime
    MAX-ACCESS  read-only
    STATUS      current 
    DESCRIPTION
        "Timestamp" 
    ::=  { intervalPhysPerfOlmTxLineAtt1weekEntry 6 }

currentPhysConv15minTable OBJECT-TYPE
    SYNTAX      SEQUENCE OF CurrentPhysConv15minEntry
    MAX-ACCESS  not-accessible
    STATUS      current 
    DESCRIPTION
        "" 
    ::=  { performanceMonitoring 48 }

currentPhysConv15minEntry OBJECT-TYPE
    SYNTAX      CurrentPhysConv15minEntry
    MAX-ACCESS  not-accessible
    STATUS      current 
    DESCRIPTION
        "" 
    INDEX       { entityIndex } 
    ::=  { currentPhysConv15minTable  1  }

CurrentPhysConv15minEntry ::=  SEQUENCE
  { currentPhysConv15minES Unsigned32,
    currentPhysConv15minDE Unsigned32,
    currentPhysConv15minCV Counter64String,
    currentPhysConv15minElapsedTime Integer32 }


  
currentPhysConv15minES OBJECT-TYPE
    SYNTAX      Unsigned32
    MAX-ACCESS  read-only
    STATUS      current 
    DESCRIPTION
        "Errored Seconds Physical Coding Layer" 
    ::=  { currentPhysConv15minEntry 1 }

currentPhysConv15minDE OBJECT-TYPE
    SYNTAX      Unsigned32
    MAX-ACCESS  read-only
    STATUS      current 
    DESCRIPTION
        "Disparity Errors Physical Coding Layer" 
    ::=  { currentPhysConv15minEntry 2 }

currentPhysConv15minCV OBJECT-TYPE
    SYNTAX      Counter64String
    MAX-ACCESS  read-only
    STATUS      current 
    DESCRIPTION
        "Coding Violations Physical Coding Layer" 
    ::=  { currentPhysConv15minEntry 3 }

currentPhysConv15minElapsedTime OBJECT-TYPE
    SYNTAX      Integer32 (0..9000)
    MAX-ACCESS  read-only
    STATUS      current 
    DESCRIPTION
        "Elapsed 15Min" 
    ::=  { currentPhysConv15minEntry 4 }

currentPhysConv1dayTable OBJECT-TYPE
    SYNTAX      SEQUENCE OF CurrentPhysConv1dayEntry
    MAX-ACCESS  not-accessible
    STATUS      current 
    DESCRIPTION
        "" 
    ::=  { performanceMonitoring 49 }

currentPhysConv1dayEntry OBJECT-TYPE
    SYNTAX      CurrentPhysConv1dayEntry
    MAX-ACCESS  not-accessible
    STATUS      current 
    DESCRIPTION
        "" 
    INDEX       { entityIndex } 
    ::=  { currentPhysConv1dayTable  1  }

CurrentPhysConv1dayEntry ::=  SEQUENCE
  { currentPhysConv1dayES Unsigned32,
    currentPhysConv1dayDE Unsigned32,
    currentPhysConv1dayCV Counter64String,
    currentPhysConv1dayElapsedTime Integer32 }


  
currentPhysConv1dayES OBJECT-TYPE
    SYNTAX      Unsigned32
    MAX-ACCESS  read-only
    STATUS      current 
    DESCRIPTION
        "Errored Seconds Physical Coding Layer" 
    ::=  { currentPhysConv1dayEntry 1 }

currentPhysConv1dayDE OBJECT-TYPE
    SYNTAX      Unsigned32
    MAX-ACCESS  read-only
    STATUS      current 
    DESCRIPTION
        "Disparity Errors Physical Coding Layer" 
    ::=  { currentPhysConv1dayEntry 2 }

currentPhysConv1dayCV OBJECT-TYPE
    SYNTAX      Counter64String
    MAX-ACCESS  read-only
    STATUS      current 
    DESCRIPTION
        "Coding Violations Physical Coding Layer" 
    ::=  { currentPhysConv1dayEntry 3 }

currentPhysConv1dayElapsedTime OBJECT-TYPE
    SYNTAX      Integer32 (0..86400)
    MAX-ACCESS  read-only
    STATUS      current 
    DESCRIPTION
        "Elapsed 1Day" 
    ::=  { currentPhysConv1dayEntry 4 }

intervalPhysConv15minTable OBJECT-TYPE
    SYNTAX      SEQUENCE OF IntervalPhysConv15minEntry
    MAX-ACCESS  not-accessible
    STATUS      current 
    DESCRIPTION
        "" 
    ::=  { performanceMonitoring 50 }

intervalPhysConv15minEntry OBJECT-TYPE
    SYNTAX      IntervalPhysConv15minEntry
    MAX-ACCESS  not-accessible
    STATUS      current 
    DESCRIPTION
        "" 
    INDEX       { entityIndex,intervalPhysConv15minNumber } 
    ::=  { intervalPhysConv15minTable  1  }

IntervalPhysConv15minEntry ::=  SEQUENCE
  { intervalPhysConv15minNumber Integer32,
    intervalPhysConv15minES Unsigned32,
    intervalPhysConv15minDE Unsigned32,
    intervalPhysConv15minCV Counter64String,
    intervalPhysConv15minValidFlag TruthValue,
    intervalPhysConv15minTimeStamp DateAndTime }


  
intervalPhysConv15minNumber OBJECT-TYPE
    SYNTAX      Integer32 (1..96)
    MAX-ACCESS  not-accessible
    STATUS      current 
    DESCRIPTION
        "Number 15min" 
    ::=  { intervalPhysConv15minEntry 1 }

intervalPhysConv15minES OBJECT-TYPE
    SYNTAX      Unsigned32
    MAX-ACCESS  read-only
    STATUS      current 
    DESCRIPTION
        "Errored Seconds Physical Coding Layer" 
    ::=  { intervalPhysConv15minEntry 2 }

intervalPhysConv15minDE OBJECT-TYPE
    SYNTAX      Unsigned32
    MAX-ACCESS  read-only
    STATUS      current 
    DESCRIPTION
        "Disparity Errors Physical Coding Layer" 
    ::=  { intervalPhysConv15minEntry 3 }

intervalPhysConv15minCV OBJECT-TYPE
    SYNTAX      Counter64String
    MAX-ACCESS  read-only
    STATUS      current 
    DESCRIPTION
        "Coding Violations Physical Coding Layer" 
    ::=  { intervalPhysConv15minEntry 4 }

intervalPhysConv15minValidFlag OBJECT-TYPE
    SYNTAX      TruthValue
    MAX-ACCESS  read-only
    STATUS      current 
    DESCRIPTION
        "" 
    ::=  { intervalPhysConv15minEntry 5 }

intervalPhysConv15minTimeStamp OBJECT-TYPE
    SYNTAX      DateAndTime
    MAX-ACCESS  read-only
    STATUS      current 
    DESCRIPTION
        "Timestamp" 
    ::=  { intervalPhysConv15minEntry 6 }

intervalPhysConv1dayTable OBJECT-TYPE
    SYNTAX      SEQUENCE OF IntervalPhysConv1dayEntry
    MAX-ACCESS  not-accessible
    STATUS      current 
    DESCRIPTION
        "" 
    ::=  { performanceMonitoring 51 }

intervalPhysConv1dayEntry OBJECT-TYPE
    SYNTAX      IntervalPhysConv1dayEntry
    MAX-ACCESS  not-accessible
    STATUS      current 
    DESCRIPTION
        "" 
    INDEX       { entityIndex,intervalPhysConv1dayNumber } 
    ::=  { intervalPhysConv1dayTable  1  }

IntervalPhysConv1dayEntry ::=  SEQUENCE
  { intervalPhysConv1dayNumber Integer32,
    intervalPhysConv1dayES Unsigned32,
    intervalPhysConv1dayDE Unsigned32,
    intervalPhysConv1dayCV Counter64String,
    intervalPhysConv1dayValidFlag TruthValue,
    intervalPhysConv1dayTimeStamp DateAndTime }


  
intervalPhysConv1dayNumber OBJECT-TYPE
    SYNTAX      Integer32 (1..31)
    MAX-ACCESS  not-accessible
    STATUS      current 
    DESCRIPTION
        "Number 1day" 
    ::=  { intervalPhysConv1dayEntry 1 }

intervalPhysConv1dayES OBJECT-TYPE
    SYNTAX      Unsigned32
    MAX-ACCESS  read-only
    STATUS      current 
    DESCRIPTION
        "Errored Seconds Physical Coding Layer" 
    ::=  { intervalPhysConv1dayEntry 2 }

intervalPhysConv1dayDE OBJECT-TYPE
    SYNTAX      Unsigned32
    MAX-ACCESS  read-only
    STATUS      current 
    DESCRIPTION
        "Disparity Errors Physical Coding Layer" 
    ::=  { intervalPhysConv1dayEntry 3 }

intervalPhysConv1dayCV OBJECT-TYPE
    SYNTAX      Counter64String
    MAX-ACCESS  read-only
    STATUS      current 
    DESCRIPTION
        "Coding Violations Physical Coding Layer" 
    ::=  { intervalPhysConv1dayEntry 4 }

intervalPhysConv1dayValidFlag OBJECT-TYPE
    SYNTAX      TruthValue
    MAX-ACCESS  read-only
    STATUS      current 
    DESCRIPTION
        "" 
    ::=  { intervalPhysConv1dayEntry 5 }

intervalPhysConv1dayTimeStamp OBJECT-TYPE
    SYNTAX      DateAndTime
    MAX-ACCESS  read-only
    STATUS      current 
    DESCRIPTION
        "Timestamp" 
    ::=  { intervalPhysConv1dayEntry 6 }

currentEthRx15minTable OBJECT-TYPE
    SYNTAX      SEQUENCE OF CurrentEthRx15minEntry
    MAX-ACCESS  not-accessible
    STATUS      current 
    DESCRIPTION
        "" 
    ::=  { performanceMonitoring 52 }

currentEthRx15minEntry OBJECT-TYPE
    SYNTAX      CurrentEthRx15minEntry
    MAX-ACCESS  not-accessible
    STATUS      current 
    DESCRIPTION
        "" 
    INDEX       { entityIndex } 
    ::=  { currentEthRx15minTable  1  }

CurrentEthRx15minEntry ::=  SEQUENCE
  { currentEthRx15minGoodFrames Counter64String,
    currentEthRx15minPauseFrames Counter64String,
    currentEthRx15minCrcFrames Counter64String,
    currentEthRx15minDiscardedFrames Counter64String,
    currentEthRx15minBytes Counter64String,
    currentEthRx15minElapsedTime Integer32 }


  
currentEthRx15minGoodFrames OBJECT-TYPE
    SYNTAX      Counter64String
    MAX-ACCESS  read-only
    STATUS      current 
    DESCRIPTION
        "Frames Received" 
    ::=  { currentEthRx15minEntry 1 }

currentEthRx15minPauseFrames OBJECT-TYPE
    SYNTAX      Counter64String
    MAX-ACCESS  read-only
    STATUS      current 
    DESCRIPTION
        "PAUSE Frames Received" 
    ::=  { currentEthRx15minEntry 2 }

currentEthRx15minCrcFrames OBJECT-TYPE
    SYNTAX      Counter64String
    MAX-ACCESS  read-only
    STATUS      current 
    DESCRIPTION
        "Received CRC Errors" 
    ::=  { currentEthRx15minEntry 3 }

currentEthRx15minDiscardedFrames OBJECT-TYPE
    SYNTAX      Counter64String
    MAX-ACCESS  read-only
    STATUS      current 
    DESCRIPTION
        "Received Frames Discarded" 
    ::=  { currentEthRx15minEntry 4 }

currentEthRx15minBytes OBJECT-TYPE
    SYNTAX      Counter64String
    MAX-ACCESS  read-only
    STATUS      current 
    DESCRIPTION
        "Bytes Received" 
    ::=  { currentEthRx15minEntry 5 }

currentEthRx15minElapsedTime OBJECT-TYPE
    SYNTAX      Integer32 (0..9000)
    MAX-ACCESS  read-only
    STATUS      current 
    DESCRIPTION
        "Elapsed 15Min" 
    ::=  { currentEthRx15minEntry 6 }

currentEthRx1dayTable OBJECT-TYPE
    SYNTAX      SEQUENCE OF CurrentEthRx1dayEntry
    MAX-ACCESS  not-accessible
    STATUS      current 
    DESCRIPTION
        "" 
    ::=  { performanceMonitoring 53 }

currentEthRx1dayEntry OBJECT-TYPE
    SYNTAX      CurrentEthRx1dayEntry
    MAX-ACCESS  not-accessible
    STATUS      current 
    DESCRIPTION
        "" 
    INDEX       { entityIndex } 
    ::=  { currentEthRx1dayTable  1  }

CurrentEthRx1dayEntry ::=  SEQUENCE
  { currentEthRx1dayGoodFrames Counter64String,
    currentEthRx1dayPauseFrames Counter64String,
    currentEthRx1dayCrcFrames Counter64String,
    currentEthRx1dayDiscardedFrames Counter64String,
    currentEthRx1dayBytes Counter64String,
    currentEthRx1dayElapsedTime Integer32 }


  
currentEthRx1dayGoodFrames OBJECT-TYPE
    SYNTAX      Counter64String
    MAX-ACCESS  read-only
    STATUS      current 
    DESCRIPTION
        "Frames Received" 
    ::=  { currentEthRx1dayEntry 1 }

currentEthRx1dayPauseFrames OBJECT-TYPE
    SYNTAX      Counter64String
    MAX-ACCESS  read-only
    STATUS      current 
    DESCRIPTION
        "PAUSE Frames Received" 
    ::=  { currentEthRx1dayEntry 2 }

currentEthRx1dayCrcFrames OBJECT-TYPE
    SYNTAX      Counter64String
    MAX-ACCESS  read-only
    STATUS      current 
    DESCRIPTION
        "Received CRC Errors" 
    ::=  { currentEthRx1dayEntry 3 }

currentEthRx1dayDiscardedFrames OBJECT-TYPE
    SYNTAX      Counter64String
    MAX-ACCESS  read-only
    STATUS      current 
    DESCRIPTION
        "Received Frames Discarded" 
    ::=  { currentEthRx1dayEntry 4 }

currentEthRx1dayBytes OBJECT-TYPE
    SYNTAX      Counter64String
    MAX-ACCESS  read-only
    STATUS      current 
    DESCRIPTION
        "Bytes Received" 
    ::=  { currentEthRx1dayEntry 5 }

currentEthRx1dayElapsedTime OBJECT-TYPE
    SYNTAX      Integer32 (0..86400)
    MAX-ACCESS  read-only
    STATUS      current 
    DESCRIPTION
        "Elapsed 1Day" 
    ::=  { currentEthRx1dayEntry 6 }

intervalEthRx15minTable OBJECT-TYPE
    SYNTAX      SEQUENCE OF IntervalEthRx15minEntry
    MAX-ACCESS  not-accessible
    STATUS      current 
    DESCRIPTION
        "" 
    ::=  { performanceMonitoring 54 }

intervalEthRx15minEntry OBJECT-TYPE
    SYNTAX      IntervalEthRx15minEntry
    MAX-ACCESS  not-accessible
    STATUS      current 
    DESCRIPTION
        "" 
    INDEX       { entityIndex,intervalEthRx15minNumber } 
    ::=  { intervalEthRx15minTable  1  }

IntervalEthRx15minEntry ::=  SEQUENCE
  { intervalEthRx15minNumber Integer32,
    intervalEthRx15minGoodFrames Counter64String,
    intervalEthRx15minPauseFrames Counter64String,
    intervalEthRx15minCrcFrames Counter64String,
    intervalEthRx15minDiscardedFrames Counter64String,
    intervalEthRx15minBytes Counter64String,
    intervalEthRx15minValidFlag TruthValue,
    intervalEthRx15minTimeStamp DateAndTime }


  
intervalEthRx15minNumber OBJECT-TYPE
    SYNTAX      Integer32 (1..96)
    MAX-ACCESS  not-accessible
    STATUS      current 
    DESCRIPTION
        "Number 15min" 
    ::=  { intervalEthRx15minEntry 1 }

intervalEthRx15minGoodFrames OBJECT-TYPE
    SYNTAX      Counter64String
    MAX-ACCESS  read-only
    STATUS      current 
    DESCRIPTION
        "Frames Received" 
    ::=  { intervalEthRx15minEntry 2 }

intervalEthRx15minPauseFrames OBJECT-TYPE
    SYNTAX      Counter64String
    MAX-ACCESS  read-only
    STATUS      current 
    DESCRIPTION
        "PAUSE Frames Received" 
    ::=  { intervalEthRx15minEntry 3 }

intervalEthRx15minCrcFrames OBJECT-TYPE
    SYNTAX      Counter64String
    MAX-ACCESS  read-only
    STATUS      current 
    DESCRIPTION
        "Received CRC Errors" 
    ::=  { intervalEthRx15minEntry 4 }

intervalEthRx15minDiscardedFrames OBJECT-TYPE
    SYNTAX      Counter64String
    MAX-ACCESS  read-only
    STATUS      current 
    DESCRIPTION
        "Received Frames Discarded" 
    ::=  { intervalEthRx15minEntry 5 }

intervalEthRx15minBytes OBJECT-TYPE
    SYNTAX      Counter64String
    MAX-ACCESS  read-only
    STATUS      current 
    DESCRIPTION
        "Bytes Received" 
    ::=  { intervalEthRx15minEntry 6 }

intervalEthRx15minValidFlag OBJECT-TYPE
    SYNTAX      TruthValue
    MAX-ACCESS  read-only
    STATUS      current 
    DESCRIPTION
        "" 
    ::=  { intervalEthRx15minEntry 7 }

intervalEthRx15minTimeStamp OBJECT-TYPE
    SYNTAX      DateAndTime
    MAX-ACCESS  read-only
    STATUS      current 
    DESCRIPTION
        "Timestamp" 
    ::=  { intervalEthRx15minEntry 8 }

intervalEthRx1dayTable OBJECT-TYPE
    SYNTAX      SEQUENCE OF IntervalEthRx1dayEntry
    MAX-ACCESS  not-accessible
    STATUS      current 
    DESCRIPTION
        "" 
    ::=  { performanceMonitoring 55 }

intervalEthRx1dayEntry OBJECT-TYPE
    SYNTAX      IntervalEthRx1dayEntry
    MAX-ACCESS  not-accessible
    STATUS      current 
    DESCRIPTION
        "" 
    INDEX       { entityIndex,intervalEthRx1dayNumber } 
    ::=  { intervalEthRx1dayTable  1  }

IntervalEthRx1dayEntry ::=  SEQUENCE
  { intervalEthRx1dayNumber Integer32,
    intervalEthRx1dayGoodFrames Counter64String,
    intervalEthRx1dayPauseFrames Counter64String,
    intervalEthRx1dayCrcFrames Counter64String,
    intervalEthRx1dayDiscardedFrames Counter64String,
    intervalEthRx1dayBytes Counter64String,
    intervalEthRx1dayValidFlag TruthValue,
    intervalEthRx1dayTimeStamp DateAndTime }


  
intervalEthRx1dayNumber OBJECT-TYPE
    SYNTAX      Integer32 (1..31)
    MAX-ACCESS  not-accessible
    STATUS      current 
    DESCRIPTION
        "Number 1day" 
    ::=  { intervalEthRx1dayEntry 1 }

intervalEthRx1dayGoodFrames OBJECT-TYPE
    SYNTAX      Counter64String
    MAX-ACCESS  read-only
    STATUS      current 
    DESCRIPTION
        "Frames Received" 
    ::=  { intervalEthRx1dayEntry 2 }

intervalEthRx1dayPauseFrames OBJECT-TYPE
    SYNTAX      Counter64String
    MAX-ACCESS  read-only
    STATUS      current 
    DESCRIPTION
        "PAUSE Frames Received" 
    ::=  { intervalEthRx1dayEntry 3 }

intervalEthRx1dayCrcFrames OBJECT-TYPE
    SYNTAX      Counter64String
    MAX-ACCESS  read-only
    STATUS      current 
    DESCRIPTION
        "Received CRC Errors" 
    ::=  { intervalEthRx1dayEntry 4 }

intervalEthRx1dayDiscardedFrames OBJECT-TYPE
    SYNTAX      Counter64String
    MAX-ACCESS  read-only
    STATUS      current 
    DESCRIPTION
        "Received Frames Discarded" 
    ::=  { intervalEthRx1dayEntry 5 }

intervalEthRx1dayBytes OBJECT-TYPE
    SYNTAX      Counter64String
    MAX-ACCESS  read-only
    STATUS      current 
    DESCRIPTION
        "Bytes Received" 
    ::=  { intervalEthRx1dayEntry 6 }

intervalEthRx1dayValidFlag OBJECT-TYPE
    SYNTAX      TruthValue
    MAX-ACCESS  read-only
    STATUS      current 
    DESCRIPTION
        "" 
    ::=  { intervalEthRx1dayEntry 7 }

intervalEthRx1dayTimeStamp OBJECT-TYPE
    SYNTAX      DateAndTime
    MAX-ACCESS  read-only
    STATUS      current 
    DESCRIPTION
        "Timestamp" 
    ::=  { intervalEthRx1dayEntry 8 }

currentEthTx15minTable OBJECT-TYPE
    SYNTAX      SEQUENCE OF CurrentEthTx15minEntry
    MAX-ACCESS  not-accessible
    STATUS      current 
    DESCRIPTION
        "" 
    ::=  { performanceMonitoring 56 }

currentEthTx15minEntry OBJECT-TYPE
    SYNTAX      CurrentEthTx15minEntry
    MAX-ACCESS  not-accessible
    STATUS      current 
    DESCRIPTION
        "" 
    INDEX       { entityIndex } 
    ::=  { currentEthTx15minTable  1  }

CurrentEthTx15minEntry ::=  SEQUENCE
  { currentEthTx15minGoodFramesx Counter64String,
    currentEthTx15minPauseFrames Counter64String,
    currentEthTx15minBytes Counter64String,
    currentEthTx15minCrcFramesEgress Counter64String,
    currentEthTx15minElapsedTime Integer32 }


  
currentEthTx15minGoodFramesx OBJECT-TYPE
    SYNTAX      Counter64String
    MAX-ACCESS  read-only
    STATUS      current 
    DESCRIPTION
        "Frames Transmitted" 
    ::=  { currentEthTx15minEntry 1 }

currentEthTx15minPauseFrames OBJECT-TYPE
    SYNTAX      Counter64String
    MAX-ACCESS  read-only
    STATUS      current 
    DESCRIPTION
        "PAUSE Frames Transmitted" 
    ::=  { currentEthTx15minEntry 2 }

currentEthTx15minBytes OBJECT-TYPE
    SYNTAX      Counter64String
    MAX-ACCESS  read-only
    STATUS      current 
    DESCRIPTION
        "Transmitted Bytes" 
    ::=  { currentEthTx15minEntry 3 }

currentEthTx15minCrcFramesEgress OBJECT-TYPE
    SYNTAX      Counter64String
    MAX-ACCESS  read-only
    STATUS      current 
    DESCRIPTION
        "Errored Frames (CRC Erors) Received egress from Mapper" 
    ::=  { currentEthTx15minEntry 4 }

currentEthTx15minElapsedTime OBJECT-TYPE
    SYNTAX      Integer32 (0..9000)
    MAX-ACCESS  read-only
    STATUS      current 
    DESCRIPTION
        "Elapsed 15Min" 
    ::=  { currentEthTx15minEntry 5 }

currentEthTx1dayTable OBJECT-TYPE
    SYNTAX      SEQUENCE OF CurrentEthTx1dayEntry
    MAX-ACCESS  not-accessible
    STATUS      current 
    DESCRIPTION
        "" 
    ::=  { performanceMonitoring 57 }

currentEthTx1dayEntry OBJECT-TYPE
    SYNTAX      CurrentEthTx1dayEntry
    MAX-ACCESS  not-accessible
    STATUS      current 
    DESCRIPTION
        "" 
    INDEX       { entityIndex } 
    ::=  { currentEthTx1dayTable  1  }

CurrentEthTx1dayEntry ::=  SEQUENCE
  { currentEthTx1dayGoodFramesx Counter64String,
    currentEthTx1dayPauseFrames Counter64String,
    currentEthTx1dayBytes Counter64String,
    currentEthTx1dayCrcFramesEgress Counter64String,
    currentEthTx1dayElapsedTime Integer32 }


  
currentEthTx1dayGoodFramesx OBJECT-TYPE
    SYNTAX      Counter64String
    MAX-ACCESS  read-only
    STATUS      current 
    DESCRIPTION
        "Frames Transmitted" 
    ::=  { currentEthTx1dayEntry 1 }

currentEthTx1dayPauseFrames OBJECT-TYPE
    SYNTAX      Counter64String
    MAX-ACCESS  read-only
    STATUS      current 
    DESCRIPTION
        "PAUSE Frames Transmitted" 
    ::=  { currentEthTx1dayEntry 2 }

currentEthTx1dayBytes OBJECT-TYPE
    SYNTAX      Counter64String
    MAX-ACCESS  read-only
    STATUS      current 
    DESCRIPTION
        "Transmitted Bytes" 
    ::=  { currentEthTx1dayEntry 3 }

currentEthTx1dayCrcFramesEgress OBJECT-TYPE
    SYNTAX      Counter64String
    MAX-ACCESS  read-only
    STATUS      current 
    DESCRIPTION
        "Errored Frames (CRC Erors) Received egress from Mapper" 
    ::=  { currentEthTx1dayEntry 4 }

currentEthTx1dayElapsedTime OBJECT-TYPE
    SYNTAX      Integer32 (0..86400)
    MAX-ACCESS  read-only
    STATUS      current 
    DESCRIPTION
        "Elapsed 1Day" 
    ::=  { currentEthTx1dayEntry 5 }

intervalEthTx15minTable OBJECT-TYPE
    SYNTAX      SEQUENCE OF IntervalEthTx15minEntry
    MAX-ACCESS  not-accessible
    STATUS      current 
    DESCRIPTION
        "" 
    ::=  { performanceMonitoring 58 }

intervalEthTx15minEntry OBJECT-TYPE
    SYNTAX      IntervalEthTx15minEntry
    MAX-ACCESS  not-accessible
    STATUS      current 
    DESCRIPTION
        "" 
    INDEX       { entityIndex,intervalEthTx15minNumber } 
    ::=  { intervalEthTx15minTable  1  }

IntervalEthTx15minEntry ::=  SEQUENCE
  { intervalEthTx15minNumber Integer32,
    intervalEthTx15minGoodFramesx Counter64String,
    intervalEthTx15minPauseFrames Counter64String,
    intervalEthTx15minBytes Counter64String,
    intervalEthTx15minCrcFramesEgress Counter64String,
    intervalEthTx15minValidFlag TruthValue,
    intervalEthTx15minTimeStamp DateAndTime }


  
intervalEthTx15minNumber OBJECT-TYPE
    SYNTAX      Integer32 (1..96)
    MAX-ACCESS  not-accessible
    STATUS      current 
    DESCRIPTION
        "Number 15min" 
    ::=  { intervalEthTx15minEntry 1 }

intervalEthTx15minGoodFramesx OBJECT-TYPE
    SYNTAX      Counter64String
    MAX-ACCESS  read-only
    STATUS      current 
    DESCRIPTION
        "Frames Transmitted" 
    ::=  { intervalEthTx15minEntry 2 }

intervalEthTx15minPauseFrames OBJECT-TYPE
    SYNTAX      Counter64String
    MAX-ACCESS  read-only
    STATUS      current 
    DESCRIPTION
        "PAUSE Frames Transmitted" 
    ::=  { intervalEthTx15minEntry 3 }

intervalEthTx15minBytes OBJECT-TYPE
    SYNTAX      Counter64String
    MAX-ACCESS  read-only
    STATUS      current 
    DESCRIPTION
        "Transmitted Bytes" 
    ::=  { intervalEthTx15minEntry 4 }

intervalEthTx15minCrcFramesEgress OBJECT-TYPE
    SYNTAX      Counter64String
    MAX-ACCESS  read-only
    STATUS      current 
    DESCRIPTION
        "Errored Frames (CRC Erors) Received egress from Mapper" 
    ::=  { intervalEthTx15minEntry 5 }

intervalEthTx15minValidFlag OBJECT-TYPE
    SYNTAX      TruthValue
    MAX-ACCESS  read-only
    STATUS      current 
    DESCRIPTION
        "" 
    ::=  { intervalEthTx15minEntry 6 }

intervalEthTx15minTimeStamp OBJECT-TYPE
    SYNTAX      DateAndTime
    MAX-ACCESS  read-only
    STATUS      current 
    DESCRIPTION
        "Timestamp" 
    ::=  { intervalEthTx15minEntry 7 }

intervalEthTx1dayTable OBJECT-TYPE
    SYNTAX      SEQUENCE OF IntervalEthTx1dayEntry
    MAX-ACCESS  not-accessible
    STATUS      current 
    DESCRIPTION
        "" 
    ::=  { performanceMonitoring 59 }

intervalEthTx1dayEntry OBJECT-TYPE
    SYNTAX      IntervalEthTx1dayEntry
    MAX-ACCESS  not-accessible
    STATUS      current 
    DESCRIPTION
        "" 
    INDEX       { entityIndex,intervalEthTx1dayNumber } 
    ::=  { intervalEthTx1dayTable  1  }

IntervalEthTx1dayEntry ::=  SEQUENCE
  { intervalEthTx1dayNumber Integer32,
    intervalEthTx1dayGoodFramesx Counter64String,
    intervalEthTx1dayPauseFrames Counter64String,
    intervalEthTx1dayBytes Counter64String,
    intervalEthTx1dayCrcFramesEgress Counter64String,
    intervalEthTx1dayValidFlag TruthValue,
    intervalEthTx1dayTimeStamp DateAndTime }


  
intervalEthTx1dayNumber OBJECT-TYPE
    SYNTAX      Integer32 (1..31)
    MAX-ACCESS  not-accessible
    STATUS      current 
    DESCRIPTION
        "Number 1day" 
    ::=  { intervalEthTx1dayEntry 1 }

intervalEthTx1dayGoodFramesx OBJECT-TYPE
    SYNTAX      Counter64String
    MAX-ACCESS  read-only
    STATUS      current 
    DESCRIPTION
        "Frames Transmitted" 
    ::=  { intervalEthTx1dayEntry 2 }

intervalEthTx1dayPauseFrames OBJECT-TYPE
    SYNTAX      Counter64String
    MAX-ACCESS  read-only
    STATUS      current 
    DESCRIPTION
        "PAUSE Frames Transmitted" 
    ::=  { intervalEthTx1dayEntry 3 }

intervalEthTx1dayBytes OBJECT-TYPE
    SYNTAX      Counter64String
    MAX-ACCESS  read-only
    STATUS      current 
    DESCRIPTION
        "Transmitted Bytes" 
    ::=  { intervalEthTx1dayEntry 4 }

intervalEthTx1dayCrcFramesEgress OBJECT-TYPE
    SYNTAX      Counter64String
    MAX-ACCESS  read-only
    STATUS      current 
    DESCRIPTION
        "Errored Frames (CRC Erors) Received egress from Mapper" 
    ::=  { intervalEthTx1dayEntry 5 }

intervalEthTx1dayValidFlag OBJECT-TYPE
    SYNTAX      TruthValue
    MAX-ACCESS  read-only
    STATUS      current 
    DESCRIPTION
        "" 
    ::=  { intervalEthTx1dayEntry 6 }

intervalEthTx1dayTimeStamp OBJECT-TYPE
    SYNTAX      DateAndTime
    MAX-ACCESS  read-only
    STATUS      current 
    DESCRIPTION
        "Timestamp" 
    ::=  { intervalEthTx1dayEntry 7 }

currentGfp15minTable OBJECT-TYPE
    SYNTAX      SEQUENCE OF CurrentGfp15minEntry
    MAX-ACCESS  not-accessible
    STATUS      current 
    DESCRIPTION
        "" 
    ::=  { performanceMonitoring 60 }

currentGfp15minEntry OBJECT-TYPE
    SYNTAX      CurrentGfp15minEntry
    MAX-ACCESS  not-accessible
    STATUS      current 
    DESCRIPTION
        "" 
    INDEX       { entityIndex } 
    ::=  { currentGfp15minTable  1  }

CurrentGfp15minEntry ::=  SEQUENCE
  { currentGfp15minCoreHecCorrectedFrames Unsigned32,
    currentGfp15minTypeHecCorrectedFrames Unsigned32,
    currentGfp15minTypeHecDiscardedFrames Unsigned32,
    currentGfp15minElapsedTime Integer32 }


  
currentGfp15minCoreHecCorrectedFrames OBJECT-TYPE
    SYNTAX      Unsigned32
    MAX-ACCESS  read-only
    STATUS      current 
    DESCRIPTION
        "Core HEC Corrected Frames" 
    ::=  { currentGfp15minEntry 1 }

currentGfp15minTypeHecCorrectedFrames OBJECT-TYPE
    SYNTAX      Unsigned32
    MAX-ACCESS  read-only
    STATUS      current 
    DESCRIPTION
        "Type Field HEC Corrected Frames" 
    ::=  { currentGfp15minEntry 2 }

currentGfp15minTypeHecDiscardedFrames OBJECT-TYPE
    SYNTAX      Unsigned32
    MAX-ACCESS  read-only
    STATUS      current 
    DESCRIPTION
        "Type Field HEC Discarded Frames" 
    ::=  { currentGfp15minEntry 3 }

currentGfp15minElapsedTime OBJECT-TYPE
    SYNTAX      Integer32 (0..9000)
    MAX-ACCESS  read-only
    STATUS      current 
    DESCRIPTION
        "Elapsed 15Min" 
    ::=  { currentGfp15minEntry 4 }

currentGfp1dayTable OBJECT-TYPE
    SYNTAX      SEQUENCE OF CurrentGfp1dayEntry
    MAX-ACCESS  not-accessible
    STATUS      current 
    DESCRIPTION
        "" 
    ::=  { performanceMonitoring 61 }

currentGfp1dayEntry OBJECT-TYPE
    SYNTAX      CurrentGfp1dayEntry
    MAX-ACCESS  not-accessible
    STATUS      current 
    DESCRIPTION
        "" 
    INDEX       { entityIndex } 
    ::=  { currentGfp1dayTable  1  }

CurrentGfp1dayEntry ::=  SEQUENCE
  { currentGfp1dayCoreHecCorrectedFrames Unsigned32,
    currentGfp1dayTypeHecCorrectedFrames Unsigned32,
    currentGfp1dayTypeHecDiscardedFrames Unsigned32,
    currentGfp1dayElapsedTime Integer32 }


  
currentGfp1dayCoreHecCorrectedFrames OBJECT-TYPE
    SYNTAX      Unsigned32
    MAX-ACCESS  read-only
    STATUS      current 
    DESCRIPTION
        "Core HEC Corrected Frames" 
    ::=  { currentGfp1dayEntry 1 }

currentGfp1dayTypeHecCorrectedFrames OBJECT-TYPE
    SYNTAX      Unsigned32
    MAX-ACCESS  read-only
    STATUS      current 
    DESCRIPTION
        "Type Field HEC Corrected Frames" 
    ::=  { currentGfp1dayEntry 2 }

currentGfp1dayTypeHecDiscardedFrames OBJECT-TYPE
    SYNTAX      Unsigned32
    MAX-ACCESS  read-only
    STATUS      current 
    DESCRIPTION
        "Type Field HEC Discarded Frames" 
    ::=  { currentGfp1dayEntry 3 }

currentGfp1dayElapsedTime OBJECT-TYPE
    SYNTAX      Integer32 (0..86400)
    MAX-ACCESS  read-only
    STATUS      current 
    DESCRIPTION
        "Elapsed 1Day" 
    ::=  { currentGfp1dayEntry 4 }

intervalGfp15minTable OBJECT-TYPE
    SYNTAX      SEQUENCE OF IntervalGfp15minEntry
    MAX-ACCESS  not-accessible
    STATUS      current 
    DESCRIPTION
        "" 
    ::=  { performanceMonitoring 62 }

intervalGfp15minEntry OBJECT-TYPE
    SYNTAX      IntervalGfp15minEntry
    MAX-ACCESS  not-accessible
    STATUS      current 
    DESCRIPTION
        "" 
    INDEX       { entityIndex,intervalGfp15minNumber } 
    ::=  { intervalGfp15minTable  1  }

IntervalGfp15minEntry ::=  SEQUENCE
  { intervalGfp15minNumber Integer32,
    intervalGfp15minCoreHecCorrectedFrames Unsigned32,
    intervalGfp15minTypeHecCorrectedFrames Unsigned32,
    intervalGfp15minTypeHecDiscardedFrames Unsigned32,
    intervalGfp15minValidFlag TruthValue,
    intervalGfp15minTimeStamp DateAndTime }


  
intervalGfp15minNumber OBJECT-TYPE
    SYNTAX      Integer32 (1..96)
    MAX-ACCESS  not-accessible
    STATUS      current 
    DESCRIPTION
        "Number 15min" 
    ::=  { intervalGfp15minEntry 1 }

intervalGfp15minCoreHecCorrectedFrames OBJECT-TYPE
    SYNTAX      Unsigned32
    MAX-ACCESS  read-only
    STATUS      current 
    DESCRIPTION
        "Core HEC Corrected Frames" 
    ::=  { intervalGfp15minEntry 2 }

intervalGfp15minTypeHecCorrectedFrames OBJECT-TYPE
    SYNTAX      Unsigned32
    MAX-ACCESS  read-only
    STATUS      current 
    DESCRIPTION
        "Type Field HEC Corrected Frames" 
    ::=  { intervalGfp15minEntry 3 }

intervalGfp15minTypeHecDiscardedFrames OBJECT-TYPE
    SYNTAX      Unsigned32
    MAX-ACCESS  read-only
    STATUS      current 
    DESCRIPTION
        "Type Field HEC Discarded Frames" 
    ::=  { intervalGfp15minEntry 4 }

intervalGfp15minValidFlag OBJECT-TYPE
    SYNTAX      TruthValue
    MAX-ACCESS  read-only
    STATUS      current 
    DESCRIPTION
        "" 
    ::=  { intervalGfp15minEntry 5 }

intervalGfp15minTimeStamp OBJECT-TYPE
    SYNTAX      DateAndTime
    MAX-ACCESS  read-only
    STATUS      current 
    DESCRIPTION
        "Timestamp" 
    ::=  { intervalGfp15minEntry 6 }

intervalGfp1dayTable OBJECT-TYPE
    SYNTAX      SEQUENCE OF IntervalGfp1dayEntry
    MAX-ACCESS  not-accessible
    STATUS      current 
    DESCRIPTION
        "" 
    ::=  { performanceMonitoring 63 }

intervalGfp1dayEntry OBJECT-TYPE
    SYNTAX      IntervalGfp1dayEntry
    MAX-ACCESS  not-accessible
    STATUS      current 
    DESCRIPTION
        "" 
    INDEX       { entityIndex,intervalGfp1dayNumber } 
    ::=  { intervalGfp1dayTable  1  }

IntervalGfp1dayEntry ::=  SEQUENCE
  { intervalGfp1dayNumber Integer32,
    intervalGfp1dayCoreHecCorrectedFrames Unsigned32,
    intervalGfp1dayTypeHecCorrectedFrames Unsigned32,
    intervalGfp1dayTypeHecDiscardedFrames Unsigned32,
    intervalGfp1dayValidFlag TruthValue,
    intervalGfp1dayTimeStamp DateAndTime }


  
intervalGfp1dayNumber OBJECT-TYPE
    SYNTAX      Integer32 (1..31)
    MAX-ACCESS  not-accessible
    STATUS      current 
    DESCRIPTION
        "Number 1day" 
    ::=  { intervalGfp1dayEntry 1 }

intervalGfp1dayCoreHecCorrectedFrames OBJECT-TYPE
    SYNTAX      Unsigned32
    MAX-ACCESS  read-only
    STATUS      current 
    DESCRIPTION
        "Core HEC Corrected Frames" 
    ::=  { intervalGfp1dayEntry 2 }

intervalGfp1dayTypeHecCorrectedFrames OBJECT-TYPE
    SYNTAX      Unsigned32
    MAX-ACCESS  read-only
    STATUS      current 
    DESCRIPTION
        "Type Field HEC Corrected Frames" 
    ::=  { intervalGfp1dayEntry 3 }

intervalGfp1dayTypeHecDiscardedFrames OBJECT-TYPE
    SYNTAX      Unsigned32
    MAX-ACCESS  read-only
    STATUS      current 
    DESCRIPTION
        "Type Field HEC Discarded Frames" 
    ::=  { intervalGfp1dayEntry 4 }

intervalGfp1dayValidFlag OBJECT-TYPE
    SYNTAX      TruthValue
    MAX-ACCESS  read-only
    STATUS      current 
    DESCRIPTION
        "" 
    ::=  { intervalGfp1dayEntry 5 }

intervalGfp1dayTimeStamp OBJECT-TYPE
    SYNTAX      DateAndTime
    MAX-ACCESS  read-only
    STATUS      current 
    DESCRIPTION
        "Timestamp" 
    ::=  { intervalGfp1dayEntry 6 }

currentDefectSeconds15minTable OBJECT-TYPE
    SYNTAX      SEQUENCE OF CurrentDefectSeconds15minEntry
    MAX-ACCESS  not-accessible
    STATUS      current 
    DESCRIPTION
        "" 
    ::=  { performanceMIB 64 }

currentDefectSeconds15minEntry OBJECT-TYPE
    SYNTAX      CurrentDefectSeconds15minEntry
    MAX-ACCESS  not-accessible
    STATUS      current 
    DESCRIPTION
        "" 
    INDEX       { entityIndex } 
    ::=  { currentDefectSeconds15minTable  1  }

CurrentDefectSeconds15minEntry ::=  SEQUENCE
  { currentDefectSeconds15minDS Unsigned32,
    currentDefectSeconds15minElapsedTime Integer32 }


  
currentDefectSeconds15minDS OBJECT-TYPE
    SYNTAX      Unsigned32
    MAX-ACCESS  read-only
    STATUS      current 
    DESCRIPTION
        "Defect Seconds" 
    ::=  { currentDefectSeconds15minEntry 1 }

currentDefectSeconds15minElapsedTime OBJECT-TYPE
    SYNTAX      Integer32 (0..9000)
    MAX-ACCESS  read-only
    STATUS      current 
    DESCRIPTION
        "Elapsed 15Min" 
    ::=  { currentDefectSeconds15minEntry 2 }

currentDefectSeconds1dayTable OBJECT-TYPE
    SYNTAX      SEQUENCE OF CurrentDefectSeconds1dayEntry
    MAX-ACCESS  not-accessible
    STATUS      current 
    DESCRIPTION
        "" 
    ::=  { performanceMIB 65 }

currentDefectSeconds1dayEntry OBJECT-TYPE
    SYNTAX      CurrentDefectSeconds1dayEntry
    MAX-ACCESS  not-accessible
    STATUS      current 
    DESCRIPTION
        "" 
    INDEX       { entityIndex } 
    ::=  { currentDefectSeconds1dayTable  1  }

CurrentDefectSeconds1dayEntry ::=  SEQUENCE
  { currentDefectSeconds1dayDS Unsigned32,
    currentDefectSeconds1dayElapsedTime Integer32 }


  
currentDefectSeconds1dayDS OBJECT-TYPE
    SYNTAX      Unsigned32
    MAX-ACCESS  read-only
    STATUS      current 
    DESCRIPTION
        "Defect Seconds" 
    ::=  { currentDefectSeconds1dayEntry 1 }

currentDefectSeconds1dayElapsedTime OBJECT-TYPE
    SYNTAX      Integer32 (0..86400)
    MAX-ACCESS  read-only
    STATUS      current 
    DESCRIPTION
        "Elapsed 1Day" 
    ::=  { currentDefectSeconds1dayEntry 2 }

intervalDefectSeconds15minTable OBJECT-TYPE
    SYNTAX      SEQUENCE OF IntervalDefectSeconds15minEntry
    MAX-ACCESS  not-accessible
    STATUS      current 
    DESCRIPTION
        "" 
    ::=  { performanceMIB 66 }

intervalDefectSeconds15minEntry OBJECT-TYPE
    SYNTAX      IntervalDefectSeconds15minEntry
    MAX-ACCESS  not-accessible
    STATUS      current 
    DESCRIPTION
        "" 
    INDEX       { entityIndex,intervalDefectSeconds15minNumber } 
    ::=  { intervalDefectSeconds15minTable  1  }

IntervalDefectSeconds15minEntry ::=  SEQUENCE
  { intervalDefectSeconds15minNumber Integer32,
    intervalDefectSeconds15minDS Unsigned32,
    intervalDefectSeconds15minValidFlag TruthValue,
    intervalDefectSeconds15minTimeStamp DateAndTime }


  
intervalDefectSeconds15minNumber OBJECT-TYPE
    SYNTAX      Integer32 (1..96)
    MAX-ACCESS  not-accessible
    STATUS      current 
    DESCRIPTION
        "Number 15min" 
    ::=  { intervalDefectSeconds15minEntry 1 }

intervalDefectSeconds15minDS OBJECT-TYPE
    SYNTAX      Unsigned32
    MAX-ACCESS  read-only
    STATUS      current 
    DESCRIPTION
        "Defect Seconds" 
    ::=  { intervalDefectSeconds15minEntry 2 }

intervalDefectSeconds15minValidFlag OBJECT-TYPE
    SYNTAX      TruthValue
    MAX-ACCESS  read-only
    STATUS      current 
    DESCRIPTION
        "" 
    ::=  { intervalDefectSeconds15minEntry 3 }

intervalDefectSeconds15minTimeStamp OBJECT-TYPE
    SYNTAX      DateAndTime
    MAX-ACCESS  read-only
    STATUS      current 
    DESCRIPTION
        "Timestamp" 
    ::=  { intervalDefectSeconds15minEntry 4 }

intervalDefectSeconds1dayTable OBJECT-TYPE
    SYNTAX      SEQUENCE OF IntervalDefectSeconds1dayEntry
    MAX-ACCESS  not-accessible
    STATUS      current 
    DESCRIPTION
        "" 
    ::=  { performanceMIB 67 }

intervalDefectSeconds1dayEntry OBJECT-TYPE
    SYNTAX      IntervalDefectSeconds1dayEntry
    MAX-ACCESS  not-accessible
    STATUS      current 
    DESCRIPTION
        "" 
    INDEX       { entityIndex,intervalDefectSeconds1dayNumber } 
    ::=  { intervalDefectSeconds1dayTable  1  }

IntervalDefectSeconds1dayEntry ::=  SEQUENCE
  { intervalDefectSeconds1dayNumber Integer32,
    intervalDefectSeconds1dayDS Unsigned32,
    intervalDefectSeconds1dayValidFlag TruthValue,
    intervalDefectSeconds1dayTimeStamp DateAndTime }


  
intervalDefectSeconds1dayNumber OBJECT-TYPE
    SYNTAX      Integer32 (1..31)
    MAX-ACCESS  not-accessible
    STATUS      current 
    DESCRIPTION
        "Number 1day" 
    ::=  { intervalDefectSeconds1dayEntry 1 }

intervalDefectSeconds1dayDS OBJECT-TYPE
    SYNTAX      Unsigned32
    MAX-ACCESS  read-only
    STATUS      current 
    DESCRIPTION
        "Defect Seconds" 
    ::=  { intervalDefectSeconds1dayEntry 2 }

intervalDefectSeconds1dayValidFlag OBJECT-TYPE
    SYNTAX      TruthValue
    MAX-ACCESS  read-only
    STATUS      current 
    DESCRIPTION
        "" 
    ::=  { intervalDefectSeconds1dayEntry 3 }

intervalDefectSeconds1dayTimeStamp OBJECT-TYPE
    SYNTAX      DateAndTime
    MAX-ACCESS  read-only
    STATUS      current 
    DESCRIPTION
        "Timestamp" 
    ::=  { intervalDefectSeconds1dayEntry 4 }

currentOtuFec15minTable OBJECT-TYPE
    SYNTAX      SEQUENCE OF CurrentOtuFec15minEntry
    MAX-ACCESS  not-accessible
    STATUS      current 
    DESCRIPTION
        "" 
    ::=  { performanceMonitoring 68 }

currentOtuFec15minEntry OBJECT-TYPE
    SYNTAX      CurrentOtuFec15minEntry
    MAX-ACCESS  not-accessible
    STATUS      current 
    DESCRIPTION
        "" 
    INDEX       { entityIndex } 
    ::=  { currentOtuFec15minTable  1  }

CurrentOtuFec15minEntry ::=  SEQUENCE
  { currentOtuFec15minES Unsigned32,
    currentOtuFec15minSES Unsigned32,
    currentOtuFec15minCE Counter64String,
    currentOtuFec15minUBE Counter64String,
    currentOtuFec15minElapsedTime Integer32 }


  
currentOtuFec15minES OBJECT-TYPE
    SYNTAX      Unsigned32
    MAX-ACCESS  read-only
    STATUS      current 
    DESCRIPTION
        "Errored Seconds FEC OTU Monitoring" 
    ::=  { currentOtuFec15minEntry 1 }

currentOtuFec15minSES OBJECT-TYPE
    SYNTAX      Unsigned32
    MAX-ACCESS  read-only
    STATUS      current 
    DESCRIPTION
        "Severely Errored Seconds FEC Monitoring" 
    ::=  { currentOtuFec15minEntry 2 }

currentOtuFec15minCE OBJECT-TYPE
    SYNTAX      Counter64String
    MAX-ACCESS  read-only
    STATUS      current 
    DESCRIPTION
        "Corrected Errors OTU FEC Monitoring [count of corrected anomalies]" 
    ::=  { currentOtuFec15minEntry 3 }

currentOtuFec15minUBE OBJECT-TYPE
    SYNTAX      Counter64String
    MAX-ACCESS  read-only
    STATUS      current 
    DESCRIPTION
        "Uncorrected Block Errors - OTU FEC Monitoring" 
    ::=  { currentOtuFec15minEntry 4 }

currentOtuFec15minElapsedTime OBJECT-TYPE
    SYNTAX      Integer32 (0..9000)
    MAX-ACCESS  read-only
    STATUS      current 
    DESCRIPTION
        "Elapsed 15Min" 
    ::=  { currentOtuFec15minEntry 5 }

currentOtuFec1dayTable OBJECT-TYPE
    SYNTAX      SEQUENCE OF CurrentOtuFec1dayEntry
    MAX-ACCESS  not-accessible
    STATUS      current 
    DESCRIPTION
        "" 
    ::=  { performanceMonitoring 69 }

currentOtuFec1dayEntry OBJECT-TYPE
    SYNTAX      CurrentOtuFec1dayEntry
    MAX-ACCESS  not-accessible
    STATUS      current 
    DESCRIPTION
        "" 
    INDEX       { entityIndex } 
    ::=  { currentOtuFec1dayTable  1  }

CurrentOtuFec1dayEntry ::=  SEQUENCE
  { currentOtuFec1dayES Unsigned32,
    currentOtuFec1daySES Unsigned32,
    currentOtuFec1dayCE Counter64String,
    currentOtuFec1dayUBE Counter64String,
    currentOtuFec1dayElapsedTime Integer32 }


  
currentOtuFec1dayES OBJECT-TYPE
    SYNTAX      Unsigned32
    MAX-ACCESS  read-only
    STATUS      current 
    DESCRIPTION
        "Errored Seconds FEC OTU Monitoring" 
    ::=  { currentOtuFec1dayEntry 1 }

currentOtuFec1daySES OBJECT-TYPE
    SYNTAX      Unsigned32
    MAX-ACCESS  read-only
    STATUS      current 
    DESCRIPTION
        "Severely Errored Seconds FEC Monitoring" 
    ::=  { currentOtuFec1dayEntry 2 }

currentOtuFec1dayCE OBJECT-TYPE
    SYNTAX      Counter64String
    MAX-ACCESS  read-only
    STATUS      current 
    DESCRIPTION
        "Corrected Errors OTU FEC Monitoring [count of corrected anomalies]" 
    ::=  { currentOtuFec1dayEntry 3 }

currentOtuFec1dayUBE OBJECT-TYPE
    SYNTAX      Counter64String
    MAX-ACCESS  read-only
    STATUS      current 
    DESCRIPTION
        "Uncorrected Block Errors - OTU FEC Monitoring" 
    ::=  { currentOtuFec1dayEntry 4 }

currentOtuFec1dayElapsedTime OBJECT-TYPE
    SYNTAX      Integer32 (0..86400)
    MAX-ACCESS  read-only
    STATUS      current 
    DESCRIPTION
        "Elapsed 1Day" 
    ::=  { currentOtuFec1dayEntry 5 }

intervalOtuFec15minTable OBJECT-TYPE
    SYNTAX      SEQUENCE OF IntervalOtuFec15minEntry
    MAX-ACCESS  not-accessible
    STATUS      current 
    DESCRIPTION
        "" 
    ::=  { performanceMonitoring 70 }

intervalOtuFec15minEntry OBJECT-TYPE
    SYNTAX      IntervalOtuFec15minEntry
    MAX-ACCESS  not-accessible
    STATUS      current 
    DESCRIPTION
        "" 
    INDEX       { entityIndex,intervalOtuFec15minNumber } 
    ::=  { intervalOtuFec15minTable  1  }

IntervalOtuFec15minEntry ::=  SEQUENCE
  { intervalOtuFec15minNumber Integer32,
    intervalOtuFec15minES Unsigned32,
    intervalOtuFec15minSES Unsigned32,
    intervalOtuFec15minCE Counter64String,
    intervalOtuFec15minUBE Counter64String,
    intervalOtuFec15minValidFlag TruthValue,
    intervalOtuFec15minTimeStamp DateAndTime }


  
intervalOtuFec15minNumber OBJECT-TYPE
    SYNTAX      Integer32 (1..96)
    MAX-ACCESS  not-accessible
    STATUS      current 
    DESCRIPTION
        "Number 15min" 
    ::=  { intervalOtuFec15minEntry 1 }

intervalOtuFec15minES OBJECT-TYPE
    SYNTAX      Unsigned32
    MAX-ACCESS  read-only
    STATUS      current 
    DESCRIPTION
        "Errored Seconds FEC OTU Monitoring" 
    ::=  { intervalOtuFec15minEntry 2 }

intervalOtuFec15minSES OBJECT-TYPE
    SYNTAX      Unsigned32
    MAX-ACCESS  read-only
    STATUS      current 
    DESCRIPTION
        "Severely Errored Seconds FEC Monitoring" 
    ::=  { intervalOtuFec15minEntry 3 }

intervalOtuFec15minCE OBJECT-TYPE
    SYNTAX      Counter64String
    MAX-ACCESS  read-only
    STATUS      current 
    DESCRIPTION
        "Corrected Errors OTU FEC Monitoring [count of corrected anomalies]" 
    ::=  { intervalOtuFec15minEntry 4 }

intervalOtuFec15minUBE OBJECT-TYPE
    SYNTAX      Counter64String
    MAX-ACCESS  read-only
    STATUS      current 
    DESCRIPTION
        "Uncorrected Block Errors - OTU FEC Monitoring" 
    ::=  { intervalOtuFec15minEntry 5 }

intervalOtuFec15minValidFlag OBJECT-TYPE
    SYNTAX      TruthValue
    MAX-ACCESS  read-only
    STATUS      current 
    DESCRIPTION
        "" 
    ::=  { intervalOtuFec15minEntry 6 }

intervalOtuFec15minTimeStamp OBJECT-TYPE
    SYNTAX      DateAndTime
    MAX-ACCESS  read-only
    STATUS      current 
    DESCRIPTION
        "Timestamp" 
    ::=  { intervalOtuFec15minEntry 7 }

intervalOtuFec1dayTable OBJECT-TYPE
    SYNTAX      SEQUENCE OF IntervalOtuFec1dayEntry
    MAX-ACCESS  not-accessible
    STATUS      current 
    DESCRIPTION
        "" 
    ::=  { performanceMonitoring 71 }

intervalOtuFec1dayEntry OBJECT-TYPE
    SYNTAX      IntervalOtuFec1dayEntry
    MAX-ACCESS  not-accessible
    STATUS      current 
    DESCRIPTION
        "" 
    INDEX       { entityIndex,intervalOtuFec1dayNumber } 
    ::=  { intervalOtuFec1dayTable  1  }

IntervalOtuFec1dayEntry ::=  SEQUENCE
  { intervalOtuFec1dayNumber Integer32,
    intervalOtuFec1dayES Unsigned32,
    intervalOtuFec1daySES Unsigned32,
    intervalOtuFec1dayCE Counter64String,
    intervalOtuFec1dayUBE Counter64String,
    intervalOtuFec1dayValidFlag TruthValue,
    intervalOtuFec1dayTimeStamp DateAndTime }


  
intervalOtuFec1dayNumber OBJECT-TYPE
    SYNTAX      Integer32 (1..31)
    MAX-ACCESS  not-accessible
    STATUS      current 
    DESCRIPTION
        "Number 1day" 
    ::=  { intervalOtuFec1dayEntry 1 }

intervalOtuFec1dayES OBJECT-TYPE
    SYNTAX      Unsigned32
    MAX-ACCESS  read-only
    STATUS      current 
    DESCRIPTION
        "Errored Seconds FEC OTU Monitoring" 
    ::=  { intervalOtuFec1dayEntry 2 }

intervalOtuFec1daySES OBJECT-TYPE
    SYNTAX      Unsigned32
    MAX-ACCESS  read-only
    STATUS      current 
    DESCRIPTION
        "Severely Errored Seconds FEC Monitoring" 
    ::=  { intervalOtuFec1dayEntry 3 }

intervalOtuFec1dayCE OBJECT-TYPE
    SYNTAX      Counter64String
    MAX-ACCESS  read-only
    STATUS      current 
    DESCRIPTION
        "Corrected Errors OTU FEC Monitoring [count of corrected anomalies]" 
    ::=  { intervalOtuFec1dayEntry 4 }

intervalOtuFec1dayUBE OBJECT-TYPE
    SYNTAX      Counter64String
    MAX-ACCESS  read-only
    STATUS      current 
    DESCRIPTION
        "Uncorrected Block Errors - OTU FEC Monitoring" 
    ::=  { intervalOtuFec1dayEntry 5 }

intervalOtuFec1dayValidFlag OBJECT-TYPE
    SYNTAX      TruthValue
    MAX-ACCESS  read-only
    STATUS      current 
    DESCRIPTION
        "" 
    ::=  { intervalOtuFec1dayEntry 6 }

intervalOtuFec1dayTimeStamp OBJECT-TYPE
    SYNTAX      DateAndTime
    MAX-ACCESS  read-only
    STATUS      current 
    DESCRIPTION
        "Timestamp" 
    ::=  { intervalOtuFec1dayEntry 7 }

currentGfpt15minTable OBJECT-TYPE
    SYNTAX      SEQUENCE OF CurrentGfpt15minEntry
    MAX-ACCESS  not-accessible
    STATUS      current 
    DESCRIPTION
        "" 
    ::=  { performanceMonitoring 72 }

currentGfpt15minEntry OBJECT-TYPE
    SYNTAX      CurrentGfpt15minEntry
    MAX-ACCESS  not-accessible
    STATUS      current 
    DESCRIPTION
        "" 
    INDEX       { entityIndex } 
    ::=  { currentGfpt15minTable  1  }

CurrentGfpt15minEntry ::=  SEQUENCE
  { currentGfpt15minDiscardedSuperblocks Unsigned32,
    currentGfpt15minElapsedTime Integer32 }


  
currentGfpt15minDiscardedSuperblocks OBJECT-TYPE
    SYNTAX      Unsigned32
    MAX-ACCESS  read-only
    STATUS      current 
    DESCRIPTION
        "Discarded Super-Blocks" 
    ::=  { currentGfpt15minEntry 1 }

currentGfpt15minElapsedTime OBJECT-TYPE
    SYNTAX      Integer32 (0..9000)
    MAX-ACCESS  read-only
    STATUS      current 
    DESCRIPTION
        "Elapsed 15Min" 
    ::=  { currentGfpt15minEntry 2 }

currentGfpt1dayTable OBJECT-TYPE
    SYNTAX      SEQUENCE OF CurrentGfpt1dayEntry
    MAX-ACCESS  not-accessible
    STATUS      current 
    DESCRIPTION
        "" 
    ::=  { performanceMonitoring 73 }

currentGfpt1dayEntry OBJECT-TYPE
    SYNTAX      CurrentGfpt1dayEntry
    MAX-ACCESS  not-accessible
    STATUS      current 
    DESCRIPTION
        "" 
    INDEX       { entityIndex } 
    ::=  { currentGfpt1dayTable  1  }

CurrentGfpt1dayEntry ::=  SEQUENCE
  { currentGfpt1dayDiscardedSuperblocks Unsigned32,
    currentGfpt1dayElapsedTime Integer32 }


  
currentGfpt1dayDiscardedSuperblocks OBJECT-TYPE
    SYNTAX      Unsigned32
    MAX-ACCESS  read-only
    STATUS      current 
    DESCRIPTION
        "Discarded Super-Blocks" 
    ::=  { currentGfpt1dayEntry 1 }

currentGfpt1dayElapsedTime OBJECT-TYPE
    SYNTAX      Integer32 (0..86400)
    MAX-ACCESS  read-only
    STATUS      current 
    DESCRIPTION
        "Elapsed 1Day" 
    ::=  { currentGfpt1dayEntry 2 }

intervalGfpt15minTable OBJECT-TYPE
    SYNTAX      SEQUENCE OF IntervalGfpt15minEntry
    MAX-ACCESS  not-accessible
    STATUS      current 
    DESCRIPTION
        "" 
    ::=  { performanceMonitoring 74 }

intervalGfpt15minEntry OBJECT-TYPE
    SYNTAX      IntervalGfpt15minEntry
    MAX-ACCESS  not-accessible
    STATUS      current 
    DESCRIPTION
        "" 
    INDEX       { entityIndex,intervalGfpt15minNumber } 
    ::=  { intervalGfpt15minTable  1  }

IntervalGfpt15minEntry ::=  SEQUENCE
  { intervalGfpt15minNumber Integer32,
    intervalGfpt15minDiscardedSuperblocks Unsigned32,
    intervalGfpt15minValidFlag TruthValue,
    intervalGfpt15minTimeStamp DateAndTime }


  
intervalGfpt15minNumber OBJECT-TYPE
    SYNTAX      Integer32 (1..96)
    MAX-ACCESS  not-accessible
    STATUS      current 
    DESCRIPTION
        "Number 15min" 
    ::=  { intervalGfpt15minEntry 1 }

intervalGfpt15minDiscardedSuperblocks OBJECT-TYPE
    SYNTAX      Unsigned32
    MAX-ACCESS  read-only
    STATUS      current 
    DESCRIPTION
        "Discarded Super-Blocks" 
    ::=  { intervalGfpt15minEntry 2 }

intervalGfpt15minValidFlag OBJECT-TYPE
    SYNTAX      TruthValue
    MAX-ACCESS  read-only
    STATUS      current 
    DESCRIPTION
        "" 
    ::=  { intervalGfpt15minEntry 3 }

intervalGfpt15minTimeStamp OBJECT-TYPE
    SYNTAX      DateAndTime
    MAX-ACCESS  read-only
    STATUS      current 
    DESCRIPTION
        "Timestamp" 
    ::=  { intervalGfpt15minEntry 4 }

intervalGfpt1dayTable OBJECT-TYPE
    SYNTAX      SEQUENCE OF IntervalGfpt1dayEntry
    MAX-ACCESS  not-accessible
    STATUS      current 
    DESCRIPTION
        "" 
    ::=  { performanceMonitoring 75 }

intervalGfpt1dayEntry OBJECT-TYPE
    SYNTAX      IntervalGfpt1dayEntry
    MAX-ACCESS  not-accessible
    STATUS      current 
    DESCRIPTION
        "" 
    INDEX       { entityIndex,intervalGfpt1dayNumber } 
    ::=  { intervalGfpt1dayTable  1  }

IntervalGfpt1dayEntry ::=  SEQUENCE
  { intervalGfpt1dayNumber Integer32,
    intervalGfpt1dayDiscardedSuperblocks Unsigned32,
    intervalGfpt1dayValidFlag TruthValue,
    intervalGfpt1dayTimeStamp DateAndTime }


  
intervalGfpt1dayNumber OBJECT-TYPE
    SYNTAX      Integer32 (1..31)
    MAX-ACCESS  not-accessible
    STATUS      current 
    DESCRIPTION
        "Number 1day" 
    ::=  { intervalGfpt1dayEntry 1 }

intervalGfpt1dayDiscardedSuperblocks OBJECT-TYPE
    SYNTAX      Unsigned32
    MAX-ACCESS  read-only
    STATUS      current 
    DESCRIPTION
        "Discarded Super-Blocks" 
    ::=  { intervalGfpt1dayEntry 2 }

intervalGfpt1dayValidFlag OBJECT-TYPE
    SYNTAX      TruthValue
    MAX-ACCESS  read-only
    STATUS      current 
    DESCRIPTION
        "" 
    ::=  { intervalGfpt1dayEntry 3 }

intervalGfpt1dayTimeStamp OBJECT-TYPE
    SYNTAX      DateAndTime
    MAX-ACCESS  read-only
    STATUS      current 
    DESCRIPTION
        "Timestamp" 
    ::=  { intervalGfpt1dayEntry 4 }

currentSubAggregate15minTable OBJECT-TYPE
    SYNTAX      SEQUENCE OF CurrentSubAggregate15minEntry
    MAX-ACCESS  not-accessible
    STATUS      current 
    DESCRIPTION
        "" 
    ::=  { performanceMonitoring 76 }

currentSubAggregate15minEntry OBJECT-TYPE
    SYNTAX      CurrentSubAggregate15minEntry
    MAX-ACCESS  not-accessible
    STATUS      current 
    DESCRIPTION
        "" 
    INDEX       { entityIndex } 
    ::=  { currentSubAggregate15minTable  1  }

CurrentSubAggregate15minEntry ::=  SEQUENCE
  { currentSubAggregate15minES Unsigned32,
    currentSubAggregate15minSES Unsigned32,
    currentSubAggregate15minElapsedTime Integer32 }


  
currentSubAggregate15minES OBJECT-TYPE
    SYNTAX      Unsigned32
    MAX-ACCESS  read-only
    STATUS      current 
    DESCRIPTION
        "Multiplexer Errored Seconds" 
    ::=  { currentSubAggregate15minEntry 1 }

currentSubAggregate15minSES OBJECT-TYPE
    SYNTAX      Unsigned32
    MAX-ACCESS  read-only
    STATUS      current 
    DESCRIPTION
        "Multiplexer Severely Errored Seconds" 
    ::=  { currentSubAggregate15minEntry 2 }

currentSubAggregate15minElapsedTime OBJECT-TYPE
    SYNTAX      Integer32 (0..9000)
    MAX-ACCESS  read-only
    STATUS      current 
    DESCRIPTION
        "Elapsed 15Min" 
    ::=  { currentSubAggregate15minEntry 3 }

currentSubAggregate1dayTable OBJECT-TYPE
    SYNTAX      SEQUENCE OF CurrentSubAggregate1dayEntry
    MAX-ACCESS  not-accessible
    STATUS      current 
    DESCRIPTION
        "" 
    ::=  { performanceMonitoring 77 }

currentSubAggregate1dayEntry OBJECT-TYPE
    SYNTAX      CurrentSubAggregate1dayEntry
    MAX-ACCESS  not-accessible
    STATUS      current 
    DESCRIPTION
        "" 
    INDEX       { entityIndex } 
    ::=  { currentSubAggregate1dayTable  1  }

CurrentSubAggregate1dayEntry ::=  SEQUENCE
  { currentSubAggregate1dayES Unsigned32,
    currentSubAggregate1daySES Unsigned32,
    currentSubAggregate1dayElapsedTime Integer32 }


  
currentSubAggregate1dayES OBJECT-TYPE
    SYNTAX      Unsigned32
    MAX-ACCESS  read-only
    STATUS      current 
    DESCRIPTION
        "Multiplexer Errored Seconds" 
    ::=  { currentSubAggregate1dayEntry 1 }

currentSubAggregate1daySES OBJECT-TYPE
    SYNTAX      Unsigned32
    MAX-ACCESS  read-only
    STATUS      current 
    DESCRIPTION
        "Multiplexer Severely Errored Seconds" 
    ::=  { currentSubAggregate1dayEntry 2 }

currentSubAggregate1dayElapsedTime OBJECT-TYPE
    SYNTAX      Integer32 (0..86400)
    MAX-ACCESS  read-only
    STATUS      current 
    DESCRIPTION
        "Elapsed 1Day" 
    ::=  { currentSubAggregate1dayEntry 3 }

intervalSubAggregate15minTable OBJECT-TYPE
    SYNTAX      SEQUENCE OF IntervalSubAggregate15minEntry
    MAX-ACCESS  not-accessible
    STATUS      current 
    DESCRIPTION
        "" 
    ::=  { performanceMonitoring 78 }

intervalSubAggregate15minEntry OBJECT-TYPE
    SYNTAX      IntervalSubAggregate15minEntry
    MAX-ACCESS  not-accessible
    STATUS      current 
    DESCRIPTION
        "" 
    INDEX       { entityIndex,intervalSubAggregate15minNumber } 
    ::=  { intervalSubAggregate15minTable  1  }

IntervalSubAggregate15minEntry ::=  SEQUENCE
  { intervalSubAggregate15minNumber Integer32,
    intervalSubAggregate15minES Unsigned32,
    intervalSubAggregate15minSES Unsigned32,
    intervalSubAggregate15minValidFlag TruthValue,
    intervalSubAggregate15minTimeStamp DateAndTime }


  
intervalSubAggregate15minNumber OBJECT-TYPE
    SYNTAX      Integer32 (1..96)
    MAX-ACCESS  not-accessible
    STATUS      current 
    DESCRIPTION
        "Number 15min" 
    ::=  { intervalSubAggregate15minEntry 1 }

intervalSubAggregate15minES OBJECT-TYPE
    SYNTAX      Unsigned32
    MAX-ACCESS  read-only
    STATUS      current 
    DESCRIPTION
        "Multiplexer Errored Seconds" 
    ::=  { intervalSubAggregate15minEntry 2 }

intervalSubAggregate15minSES OBJECT-TYPE
    SYNTAX      Unsigned32
    MAX-ACCESS  read-only
    STATUS      current 
    DESCRIPTION
        "Multiplexer Severely Errored Seconds" 
    ::=  { intervalSubAggregate15minEntry 3 }

intervalSubAggregate15minValidFlag OBJECT-TYPE
    SYNTAX      TruthValue
    MAX-ACCESS  read-only
    STATUS      current 
    DESCRIPTION
        "" 
    ::=  { intervalSubAggregate15minEntry 4 }

intervalSubAggregate15minTimeStamp OBJECT-TYPE
    SYNTAX      DateAndTime
    MAX-ACCESS  read-only
    STATUS      current 
    DESCRIPTION
        "Timestamp" 
    ::=  { intervalSubAggregate15minEntry 5 }

intervalSubAggregate1dayTable OBJECT-TYPE
    SYNTAX      SEQUENCE OF IntervalSubAggregate1dayEntry
    MAX-ACCESS  not-accessible
    STATUS      current 
    DESCRIPTION
        "" 
    ::=  { performanceMonitoring 79 }

intervalSubAggregate1dayEntry OBJECT-TYPE
    SYNTAX      IntervalSubAggregate1dayEntry
    MAX-ACCESS  not-accessible
    STATUS      current 
    DESCRIPTION
        "" 
    INDEX       { entityIndex,intervalSubAggregate1dayNumber } 
    ::=  { intervalSubAggregate1dayTable  1  }

IntervalSubAggregate1dayEntry ::=  SEQUENCE
  { intervalSubAggregate1dayNumber Integer32,
    intervalSubAggregate1dayES Unsigned32,
    intervalSubAggregate1daySES Unsigned32,
    intervalSubAggregate1dayValidFlag TruthValue,
    intervalSubAggregate1dayTimeStamp DateAndTime }


  
intervalSubAggregate1dayNumber OBJECT-TYPE
    SYNTAX      Integer32 (1..31)
    MAX-ACCESS  not-accessible
    STATUS      current 
    DESCRIPTION
        "Number 1day" 
    ::=  { intervalSubAggregate1dayEntry 1 }

intervalSubAggregate1dayES OBJECT-TYPE
    SYNTAX      Unsigned32
    MAX-ACCESS  read-only
    STATUS      current 
    DESCRIPTION
        "Multiplexer Errored Seconds" 
    ::=  { intervalSubAggregate1dayEntry 2 }

intervalSubAggregate1daySES OBJECT-TYPE
    SYNTAX      Unsigned32
    MAX-ACCESS  read-only
    STATUS      current 
    DESCRIPTION
        "Multiplexer Severely Errored Seconds" 
    ::=  { intervalSubAggregate1dayEntry 3 }

intervalSubAggregate1dayValidFlag OBJECT-TYPE
    SYNTAX      TruthValue
    MAX-ACCESS  read-only
    STATUS      current 
    DESCRIPTION
        "" 
    ::=  { intervalSubAggregate1dayEntry 4 }

intervalSubAggregate1dayTimeStamp OBJECT-TYPE
    SYNTAX      DateAndTime
    MAX-ACCESS  read-only
    STATUS      current 
    DESCRIPTION
        "Timestamp" 
    ::=  { intervalSubAggregate1dayEntry 5 }

currentOduTcmC15minTable OBJECT-TYPE
    SYNTAX      SEQUENCE OF CurrentOduTcmC15minEntry
    MAX-ACCESS  not-accessible
    STATUS      current 
    DESCRIPTION
        "" 
    ::=  { performanceMonitoring 80 }

currentOduTcmC15minEntry OBJECT-TYPE
    SYNTAX      CurrentOduTcmC15minEntry
    MAX-ACCESS  not-accessible
    STATUS      current 
    DESCRIPTION
        "" 
    INDEX       { entityIndex } 
    ::=  { currentOduTcmC15minTable  1  }

CurrentOduTcmC15minEntry ::=  SEQUENCE
  { currentOduTcmC15minES Unsigned32,
    currentOduTcmC15minSES Unsigned32,
    currentOduTcmC15minBbe Counter64String,
    currentOduTcmC15minUAS Unsigned32,
    currentOduTcmC15minElapsedTime Integer32 }


  
currentOduTcmC15minES OBJECT-TYPE
    SYNTAX      Unsigned32
    MAX-ACCESS  read-only
    STATUS      current 
    DESCRIPTION
        "Errored Seconds ODU Tandem Connection Monitoring - Instance C" 
    ::=  { currentOduTcmC15minEntry 1 }

currentOduTcmC15minSES OBJECT-TYPE
    SYNTAX      Unsigned32
    MAX-ACCESS  read-only
    STATUS      current 
    DESCRIPTION
        "Severely Errored Seconds ODU Tandem Connection Monitoring - Instance C" 
    ::=  { currentOduTcmC15minEntry 2 }

currentOduTcmC15minBbe OBJECT-TYPE
    SYNTAX      Counter64String
    MAX-ACCESS  read-only
    STATUS      current 
    DESCRIPTION
        "Background Block Erros ODU Tandem Connection Monitoring - Instance C" 
    ::=  { currentOduTcmC15minEntry 3 }

currentOduTcmC15minUAS OBJECT-TYPE
    SYNTAX      Unsigned32
    MAX-ACCESS  read-only
    STATUS      current 
    DESCRIPTION
        "Unavailable Seconds ODU Tandem Connection Monitoring - Instance B" 
    ::=  { currentOduTcmC15minEntry 4 }

currentOduTcmC15minElapsedTime OBJECT-TYPE
    SYNTAX      Integer32 (0..9000)
    MAX-ACCESS  read-only
    STATUS      current 
    DESCRIPTION
        "Elapsed 15Min" 
    ::=  { currentOduTcmC15minEntry 5 }

currentOduTcmC1dayTable OBJECT-TYPE
    SYNTAX      SEQUENCE OF CurrentOduTcmC1dayEntry
    MAX-ACCESS  not-accessible
    STATUS      current 
    DESCRIPTION
        "" 
    ::=  { performanceMonitoring 81 }

currentOduTcmC1dayEntry OBJECT-TYPE
    SYNTAX      CurrentOduTcmC1dayEntry
    MAX-ACCESS  not-accessible
    STATUS      current 
    DESCRIPTION
        "" 
    INDEX       { entityIndex } 
    ::=  { currentOduTcmC1dayTable  1  }

CurrentOduTcmC1dayEntry ::=  SEQUENCE
  { currentOduTcmC1dayES Unsigned32,
    currentOduTcmC1daySES Unsigned32,
    currentOduTcmC1dayBbe Counter64String,
    currentOduTcmC1dayUAS Unsigned32,
    currentOduTcmC1dayElapsedTime Integer32 }


  
currentOduTcmC1dayES OBJECT-TYPE
    SYNTAX      Unsigned32
    MAX-ACCESS  read-only
    STATUS      current 
    DESCRIPTION
        "Errored Seconds ODU Tandem Connection Monitoring - Instance C" 
    ::=  { currentOduTcmC1dayEntry 1 }

currentOduTcmC1daySES OBJECT-TYPE
    SYNTAX      Unsigned32
    MAX-ACCESS  read-only
    STATUS      current 
    DESCRIPTION
        "Severely Errored Seconds ODU Tandem Connection Monitoring - Instance C" 
    ::=  { currentOduTcmC1dayEntry 2 }

currentOduTcmC1dayBbe OBJECT-TYPE
    SYNTAX      Counter64String
    MAX-ACCESS  read-only
    STATUS      current 
    DESCRIPTION
        "Background Block Erros ODU Tandem Connection Monitoring - Instance C" 
    ::=  { currentOduTcmC1dayEntry 3 }

currentOduTcmC1dayUAS OBJECT-TYPE
    SYNTAX      Unsigned32
    MAX-ACCESS  read-only
    STATUS      current 
    DESCRIPTION
        "Unavailable Seconds ODU Tandem Connection Monitoring - Instance B" 
    ::=  { currentOduTcmC1dayEntry 4 }

currentOduTcmC1dayElapsedTime OBJECT-TYPE
    SYNTAX      Integer32 (0..86400)
    MAX-ACCESS  read-only
    STATUS      current 
    DESCRIPTION
        "Elapsed 1Day" 
    ::=  { currentOduTcmC1dayEntry 5 }

intervalOduTcmC15minTable OBJECT-TYPE
    SYNTAX      SEQUENCE OF IntervalOduTcmC15minEntry
    MAX-ACCESS  not-accessible
    STATUS      current 
    DESCRIPTION
        "" 
    ::=  { performanceMonitoring 82 }

intervalOduTcmC15minEntry OBJECT-TYPE
    SYNTAX      IntervalOduTcmC15minEntry
    MAX-ACCESS  not-accessible
    STATUS      current 
    DESCRIPTION
        "" 
    INDEX       { entityIndex,intervalOduTcmC15minNumber } 
    ::=  { intervalOduTcmC15minTable  1  }

IntervalOduTcmC15minEntry ::=  SEQUENCE
  { intervalOduTcmC15minNumber Integer32,
    intervalOduTcmC15minES Unsigned32,
    intervalOduTcmC15minSES Unsigned32,
    intervalOduTcmC15minBbe Counter64String,
    intervalOduTcmC15minUAS Unsigned32,
    intervalOduTcmC15minValidFlag TruthValue,
    intervalOduTcmC15minTimeStamp DateAndTime }


  
intervalOduTcmC15minNumber OBJECT-TYPE
    SYNTAX      Integer32 (1..96)
    MAX-ACCESS  not-accessible
    STATUS      current 
    DESCRIPTION
        "Number 15min" 
    ::=  { intervalOduTcmC15minEntry 1 }

intervalOduTcmC15minES OBJECT-TYPE
    SYNTAX      Unsigned32
    MAX-ACCESS  read-only
    STATUS      current 
    DESCRIPTION
        "Errored Seconds ODU Tandem Connection Monitoring - Instance C" 
    ::=  { intervalOduTcmC15minEntry 2 }

intervalOduTcmC15minSES OBJECT-TYPE
    SYNTAX      Unsigned32
    MAX-ACCESS  read-only
    STATUS      current 
    DESCRIPTION
        "Severely Errored Seconds ODU Tandem Connection Monitoring - Instance C" 
    ::=  { intervalOduTcmC15minEntry 3 }

intervalOduTcmC15minBbe OBJECT-TYPE
    SYNTAX      Counter64String
    MAX-ACCESS  read-only
    STATUS      current 
    DESCRIPTION
        "Background Block Erros ODU Tandem Connection Monitoring - Instance C" 
    ::=  { intervalOduTcmC15minEntry 4 }

intervalOduTcmC15minUAS OBJECT-TYPE
    SYNTAX      Unsigned32
    MAX-ACCESS  read-only
    STATUS      current 
    DESCRIPTION
        "Unavailable Seconds ODU Tandem Connection Monitoring - Instance B" 
    ::=  { intervalOduTcmC15minEntry 5 }

intervalOduTcmC15minValidFlag OBJECT-TYPE
    SYNTAX      TruthValue
    MAX-ACCESS  read-only
    STATUS      current 
    DESCRIPTION
        "" 
    ::=  { intervalOduTcmC15minEntry 6 }

intervalOduTcmC15minTimeStamp OBJECT-TYPE
    SYNTAX      DateAndTime
    MAX-ACCESS  read-only
    STATUS      current 
    DESCRIPTION
        "Timestamp" 
    ::=  { intervalOduTcmC15minEntry 7 }

intervalOduTcmC1dayTable OBJECT-TYPE
    SYNTAX      SEQUENCE OF IntervalOduTcmC1dayEntry
    MAX-ACCESS  not-accessible
    STATUS      current 
    DESCRIPTION
        "" 
    ::=  { performanceMonitoring 83 }

intervalOduTcmC1dayEntry OBJECT-TYPE
    SYNTAX      IntervalOduTcmC1dayEntry
    MAX-ACCESS  not-accessible
    STATUS      current 
    DESCRIPTION
        "" 
    INDEX       { entityIndex,intervalOduTcmC1dayNumber } 
    ::=  { intervalOduTcmC1dayTable  1  }

IntervalOduTcmC1dayEntry ::=  SEQUENCE
  { intervalOduTcmC1dayNumber Integer32,
    intervalOduTcmC1dayES Unsigned32,
    intervalOduTcmC1daySES Unsigned32,
    intervalOduTcmC1dayBbe Counter64String,
    intervalOduTcmC1dayUAS Unsigned32,
    intervalOduTcmC1dayValidFlag TruthValue,
    intervalOduTcmC1dayTimeStamp DateAndTime }


  
intervalOduTcmC1dayNumber OBJECT-TYPE
    SYNTAX      Integer32 (1..31)
    MAX-ACCESS  not-accessible
    STATUS      current 
    DESCRIPTION
        "Number 1day" 
    ::=  { intervalOduTcmC1dayEntry 1 }

intervalOduTcmC1dayES OBJECT-TYPE
    SYNTAX      Unsigned32
    MAX-ACCESS  read-only
    STATUS      current 
    DESCRIPTION
        "Errored Seconds ODU Tandem Connection Monitoring - Instance C" 
    ::=  { intervalOduTcmC1dayEntry 2 }

intervalOduTcmC1daySES OBJECT-TYPE
    SYNTAX      Unsigned32
    MAX-ACCESS  read-only
    STATUS      current 
    DESCRIPTION
        "Severely Errored Seconds ODU Tandem Connection Monitoring - Instance C" 
    ::=  { intervalOduTcmC1dayEntry 3 }

intervalOduTcmC1dayBbe OBJECT-TYPE
    SYNTAX      Counter64String
    MAX-ACCESS  read-only
    STATUS      current 
    DESCRIPTION
        "Background Block Erros ODU Tandem Connection Monitoring - Instance C" 
    ::=  { intervalOduTcmC1dayEntry 4 }

intervalOduTcmC1dayUAS OBJECT-TYPE
    SYNTAX      Unsigned32
    MAX-ACCESS  read-only
    STATUS      current 
    DESCRIPTION
        "Unavailable Seconds ODU Tandem Connection Monitoring - Instance B" 
    ::=  { intervalOduTcmC1dayEntry 5 }

intervalOduTcmC1dayValidFlag OBJECT-TYPE
    SYNTAX      TruthValue
    MAX-ACCESS  read-only
    STATUS      current 
    DESCRIPTION
        "" 
    ::=  { intervalOduTcmC1dayEntry 6 }

intervalOduTcmC1dayTimeStamp OBJECT-TYPE
    SYNTAX      DateAndTime
    MAX-ACCESS  read-only
    STATUS      current 
    DESCRIPTION
        "Timestamp" 
    ::=  { intervalOduTcmC1dayEntry 7 }

currentPhysConvHighSpeed15minTable OBJECT-TYPE
    SYNTAX      SEQUENCE OF CurrentPhysConvHighSpeed15minEntry
    MAX-ACCESS  not-accessible
    STATUS      current 
    DESCRIPTION
        "" 
    ::=  { performanceMonitoring 84 }

currentPhysConvHighSpeed15minEntry OBJECT-TYPE
    SYNTAX      CurrentPhysConvHighSpeed15minEntry
    MAX-ACCESS  not-accessible
    STATUS      current 
    DESCRIPTION
        "" 
    INDEX       { entityIndex } 
    ::=  { currentPhysConvHighSpeed15minTable  1  }

CurrentPhysConvHighSpeed15minEntry ::=  SEQUENCE
  { currentPhysConvHighSpeed15minES Unsigned32,
    currentPhysConvHighSpeed15minCV Counter64String,
    currentPhysConvHighSpeed15minSE Unsigned32,
    currentPhysConvHighSpeed15minElapsedTime Integer32 }


  
currentPhysConvHighSpeed15minES OBJECT-TYPE
    SYNTAX      Unsigned32
    MAX-ACCESS  read-only
    STATUS      current 
    DESCRIPTION
        "Errored Seconds Physical Coding Layer" 
    ::=  { currentPhysConvHighSpeed15minEntry 1 }

currentPhysConvHighSpeed15minCV OBJECT-TYPE
    SYNTAX      Counter64String
    MAX-ACCESS  read-only
    STATUS      current 
    DESCRIPTION
        "Coding Violations Physical Coding Layer" 
    ::=  { currentPhysConvHighSpeed15minEntry 2 }

currentPhysConvHighSpeed15minSE OBJECT-TYPE
    SYNTAX      Unsigned32
    MAX-ACCESS  read-only
    STATUS      current 
    DESCRIPTION
        "Sync Header Errors Physical Coding Layer" 
    ::=  { currentPhysConvHighSpeed15minEntry 3 }

currentPhysConvHighSpeed15minElapsedTime OBJECT-TYPE
    SYNTAX      Integer32 (0..9000)
    MAX-ACCESS  read-only
    STATUS      current 
    DESCRIPTION
        "Elapsed 15Min" 
    ::=  { currentPhysConvHighSpeed15minEntry 4 }

currentPhysConvHighSpeed1dayTable OBJECT-TYPE
    SYNTAX      SEQUENCE OF CurrentPhysConvHighSpeed1dayEntry
    MAX-ACCESS  not-accessible
    STATUS      current 
    DESCRIPTION
        "" 
    ::=  { performanceMonitoring 85 }

currentPhysConvHighSpeed1dayEntry OBJECT-TYPE
    SYNTAX      CurrentPhysConvHighSpeed1dayEntry
    MAX-ACCESS  not-accessible
    STATUS      current 
    DESCRIPTION
        "" 
    INDEX       { entityIndex } 
    ::=  { currentPhysConvHighSpeed1dayTable  1  }

CurrentPhysConvHighSpeed1dayEntry ::=  SEQUENCE
  { currentPhysConvHighSpeed1dayES Unsigned32,
    currentPhysConvHighSpeed1dayCV Counter64String,
    currentPhysConvHighSpeed1daySE Unsigned32,
    currentPhysConvHighSpeed1dayElapsedTime Integer32 }


  
currentPhysConvHighSpeed1dayES OBJECT-TYPE
    SYNTAX      Unsigned32
    MAX-ACCESS  read-only
    STATUS      current 
    DESCRIPTION
        "Errored Seconds Physical Coding Layer" 
    ::=  { currentPhysConvHighSpeed1dayEntry 1 }

currentPhysConvHighSpeed1dayCV OBJECT-TYPE
    SYNTAX      Counter64String
    MAX-ACCESS  read-only
    STATUS      current 
    DESCRIPTION
        "Coding Violations Physical Coding Layer" 
    ::=  { currentPhysConvHighSpeed1dayEntry 2 }

currentPhysConvHighSpeed1daySE OBJECT-TYPE
    SYNTAX      Unsigned32
    MAX-ACCESS  read-only
    STATUS      current 
    DESCRIPTION
        "Sync Header Errors Physical Coding Layer" 
    ::=  { currentPhysConvHighSpeed1dayEntry 3 }

currentPhysConvHighSpeed1dayElapsedTime OBJECT-TYPE
    SYNTAX      Integer32 (0..86400)
    MAX-ACCESS  read-only
    STATUS      current 
    DESCRIPTION
        "Elapsed 1Day" 
    ::=  { currentPhysConvHighSpeed1dayEntry 4 }

intervalPhysConvHighSpeed15minTable OBJECT-TYPE
    SYNTAX      SEQUENCE OF IntervalPhysConvHighSpeed15minEntry
    MAX-ACCESS  not-accessible
    STATUS      current 
    DESCRIPTION
        "" 
    ::=  { performanceMonitoring 86 }

intervalPhysConvHighSpeed15minEntry OBJECT-TYPE
    SYNTAX      IntervalPhysConvHighSpeed15minEntry
    MAX-ACCESS  not-accessible
    STATUS      current 
    DESCRIPTION
        "" 
    INDEX       { entityIndex,intervalPhysConvHighSpeed15minNumber } 
    ::=  { intervalPhysConvHighSpeed15minTable  1  }

IntervalPhysConvHighSpeed15minEntry ::=  SEQUENCE
  { intervalPhysConvHighSpeed15minNumber Integer32,
    intervalPhysConvHighSpeed15minES Unsigned32,
    intervalPhysConvHighSpeed15minCV Counter64String,
    intervalPhysConvHighSpeed15minSE Unsigned32,
    intervalPhysConvHighSpeed15minValidFlag TruthValue,
    intervalPhysConvHighSpeed15minTimeStamp DateAndTime }


  
intervalPhysConvHighSpeed15minNumber OBJECT-TYPE
    SYNTAX      Integer32 (1..96)
    MAX-ACCESS  not-accessible
    STATUS      current 
    DESCRIPTION
        "Number 15min" 
    ::=  { intervalPhysConvHighSpeed15minEntry 1 }

intervalPhysConvHighSpeed15minES OBJECT-TYPE
    SYNTAX      Unsigned32
    MAX-ACCESS  read-only
    STATUS      current 
    DESCRIPTION
        "Errored Seconds Physical Coding Layer" 
    ::=  { intervalPhysConvHighSpeed15minEntry 2 }

intervalPhysConvHighSpeed15minCV OBJECT-TYPE
    SYNTAX      Counter64String
    MAX-ACCESS  read-only
    STATUS      current 
    DESCRIPTION
        "Coding Violations Physical Coding Layer" 
    ::=  { intervalPhysConvHighSpeed15minEntry 3 }

intervalPhysConvHighSpeed15minSE OBJECT-TYPE
    SYNTAX      Unsigned32
    MAX-ACCESS  read-only
    STATUS      current 
    DESCRIPTION
        "Sync Header Errors Physical Coding Layer" 
    ::=  { intervalPhysConvHighSpeed15minEntry 4 }

intervalPhysConvHighSpeed15minValidFlag OBJECT-TYPE
    SYNTAX      TruthValue
    MAX-ACCESS  read-only
    STATUS      current 
    DESCRIPTION
        "" 
    ::=  { intervalPhysConvHighSpeed15minEntry 5 }

intervalPhysConvHighSpeed15minTimeStamp OBJECT-TYPE
    SYNTAX      DateAndTime
    MAX-ACCESS  read-only
    STATUS      current 
    DESCRIPTION
        "Timestamp" 
    ::=  { intervalPhysConvHighSpeed15minEntry 6 }

intervalPhysConvHighSpeed1dayTable OBJECT-TYPE
    SYNTAX      SEQUENCE OF IntervalPhysConvHighSpeed1dayEntry
    MAX-ACCESS  not-accessible
    STATUS      current 
    DESCRIPTION
        "" 
    ::=  { performanceMonitoring 87 }

intervalPhysConvHighSpeed1dayEntry OBJECT-TYPE
    SYNTAX      IntervalPhysConvHighSpeed1dayEntry
    MAX-ACCESS  not-accessible
    STATUS      current 
    DESCRIPTION
        "" 
    INDEX       { entityIndex,intervalPhysConvHighSpeed1dayNumber } 
    ::=  { intervalPhysConvHighSpeed1dayTable  1  }

IntervalPhysConvHighSpeed1dayEntry ::=  SEQUENCE
  { intervalPhysConvHighSpeed1dayNumber Integer32,
    intervalPhysConvHighSpeed1dayES Unsigned32,
    intervalPhysConvHighSpeed1dayCV Counter64String,
    intervalPhysConvHighSpeed1daySE Unsigned32,
    intervalPhysConvHighSpeed1dayValidFlag TruthValue,
    intervalPhysConvHighSpeed1dayTimeStamp DateAndTime }


  
intervalPhysConvHighSpeed1dayNumber OBJECT-TYPE
    SYNTAX      Integer32 (1..31)
    MAX-ACCESS  not-accessible
    STATUS      current 
    DESCRIPTION
        "Number 1day" 
    ::=  { intervalPhysConvHighSpeed1dayEntry 1 }

intervalPhysConvHighSpeed1dayES OBJECT-TYPE
    SYNTAX      Unsigned32
    MAX-ACCESS  read-only
    STATUS      current 
    DESCRIPTION
        "Errored Seconds Physical Coding Layer" 
    ::=  { intervalPhysConvHighSpeed1dayEntry 2 }

intervalPhysConvHighSpeed1dayCV OBJECT-TYPE
    SYNTAX      Counter64String
    MAX-ACCESS  read-only
    STATUS      current 
    DESCRIPTION
        "Coding Violations Physical Coding Layer" 
    ::=  { intervalPhysConvHighSpeed1dayEntry 3 }

intervalPhysConvHighSpeed1daySE OBJECT-TYPE
    SYNTAX      Unsigned32
    MAX-ACCESS  read-only
    STATUS      current 
    DESCRIPTION
        "Sync Header Errors Physical Coding Layer" 
    ::=  { intervalPhysConvHighSpeed1dayEntry 4 }

intervalPhysConvHighSpeed1dayValidFlag OBJECT-TYPE
    SYNTAX      TruthValue
    MAX-ACCESS  read-only
    STATUS      current 
    DESCRIPTION
        "" 
    ::=  { intervalPhysConvHighSpeed1dayEntry 5 }

intervalPhysConvHighSpeed1dayTimeStamp OBJECT-TYPE
    SYNTAX      DateAndTime
    MAX-ACCESS  read-only
    STATUS      current 
    DESCRIPTION
        "Timestamp" 
    ::=  { intervalPhysConvHighSpeed1dayEntry 6 }

-- vendor types


-- containers

f7Containers   OBJECT IDENTIFIER ::= { fspR7VendorTypes 1 }
f7ContainerFanSlot   OBJECT IDENTIFIER ::= { f7Containers 1 }
f7ContainerModuleSlot   OBJECT IDENTIFIER ::= { f7Containers 2 }
f7ContainerSfpSlot   OBJECT IDENTIFIER ::= { f7Containers 3 }

-- power supplies

f7Shelfs   OBJECT IDENTIFIER ::= { fspR7VendorTypes 2 }

-- fan units

f7FanUnits   OBJECT IDENTIFIER ::= { fspR7VendorTypes 3 }
f7FanUnitsFan   OBJECT IDENTIFIER ::= { f7FanUnits 1 }

-- modules

f7Modules   OBJECT IDENTIFIER ::= { fspR7VendorTypes 4 }
f7eqpSh1hu   OBJECT IDENTIFIER ::= { f7Modules 1 }
f7eqpSh1huDc   OBJECT IDENTIFIER ::= { f7Modules 2 }
f7eqpSh3hu   OBJECT IDENTIFIER ::= { f7Modules 3 }
f7eqpSh7hu   OBJECT IDENTIFIER ::= { f7Modules 4 }
f7eqpUnknown   OBJECT IDENTIFIER ::= { f7Modules 5 }
f7eqpNcu   OBJECT IDENTIFIER ::= { f7Modules 6 }
f7eqpNcutif   OBJECT IDENTIFIER ::= { f7Modules 7 }
f7eqpScu   OBJECT IDENTIFIER ::= { f7Modules 8 }
f7eqpScue   OBJECT IDENTIFIER ::= { f7Modules 9 }
f7eqpR6cu   OBJECT IDENTIFIER ::= { f7Modules 10 }
f7eqpPsu1huac   OBJECT IDENTIFIER ::= { f7Modules 11 }
f7eqpPsu7huac   OBJECT IDENTIFIER ::= { f7Modules 12 }
f7eqpPsu7hudc   OBJECT IDENTIFIER ::= { f7Modules 13 }
f7eqpFcu7hu   OBJECT IDENTIFIER ::= { f7Modules 14 }
f7eqp2clsmd   OBJECT IDENTIFIER ::= { f7Modules 15 }
f7eqp2absmc   OBJECT IDENTIFIER ::= { f7Modules 16 }
f7eqp2bsmd   OBJECT IDENTIFIER ::= { f7Modules 17 }
f7eqp1Gsmud   OBJECT IDENTIFIER ::= { f7Modules 18 }
f7eqp4gsmd   OBJECT IDENTIFIER ::= { f7Modules 19 }
f7eqp8gsmd   OBJECT IDENTIFIER ::= { f7Modules 20 }
f7eqp1csmuc   OBJECT IDENTIFIER ::= { f7Modules 21 }
f7eqp1csmuewc   OBJECT IDENTIFIER ::= { f7Modules 22 }
f7eqp4csmd   OBJECT IDENTIFIER ::= { f7Modules 23 }
f7eqp4csmud   OBJECT IDENTIFIER ::= { f7Modules 24 }
f7eqp4csmc   OBJECT IDENTIFIER ::= { f7Modules 25 }
f7eqpOsfm   OBJECT IDENTIFIER ::= { f7Modules 26 }
f7eqp1pm   OBJECT IDENTIFIER ::= { f7Modules 27 }
f7eqp2pm   OBJECT IDENTIFIER ::= { f7Modules 28 }
f7eqp40csmd   OBJECT IDENTIFIER ::= { f7Modules 29 }
f7eqpDcm   OBJECT IDENTIFIER ::= { f7Modules 30 }
f7eqpEdfas   OBJECT IDENTIFIER ::= { f7Modules 31 }
f7eqpEdfasgc   OBJECT IDENTIFIER ::= { f7Modules 32 }
f7eqpEdfadgc   OBJECT IDENTIFIER ::= { f7Modules 33 }
f7eqpRaman   OBJECT IDENTIFIER ::= { f7Modules 34 }
f7eqp4tcc2g5   OBJECT IDENTIFIER ::= { f7Modules 35 }
f7eqp4tcc2g5d   OBJECT IDENTIFIER ::= { f7Modules 36 }
f7eqp4tcc10gd   OBJECT IDENTIFIER ::= { f7Modules 37 }
f7eqp4tcc10gc   OBJECT IDENTIFIER ::= { f7Modules 38 }
f7eqpWcc10gd   OBJECT IDENTIFIER ::= { f7Modules 39 }
f7eqpWcc10gc   OBJECT IDENTIFIER ::= { f7Modules 40 }
f7eqpWcc2g7   OBJECT IDENTIFIER ::= { f7Modules 41 }
f7eqpWcc2g7d   OBJECT IDENTIFIER ::= { f7Modules 42 }
f7eqp2tcm2g5   OBJECT IDENTIFIER ::= { f7Modules 43 }
f7eqp2tca2g5   OBJECT IDENTIFIER ::= { f7Modules 44 }
f7eqp8tca10gd   OBJECT IDENTIFIER ::= { f7Modules 45 }
f7eqp8tca10gc   OBJECT IDENTIFIER ::= { f7Modules 46 }
f7eqpWca10gd   OBJECT IDENTIFIER ::= { f7Modules 47 }
f7eqpWca10gc   OBJECT IDENTIFIER ::= { f7Modules 48 }
f7eqp4tca4gd   OBJECT IDENTIFIER ::= { f7Modules 49 }
f7eqp4tca4gc   OBJECT IDENTIFIER ::= { f7Modules 50 }
f7eqpwca2g5   OBJECT IDENTIFIER ::= { f7Modules 51 }
f7eqp4tca1g3d   OBJECT IDENTIFIER ::= { f7Modules 52 }
f7eqp4tca1g3c   OBJECT IDENTIFIER ::= { f7Modules 53 }
f7eqp8tce2g5d   OBJECT IDENTIFIER ::= { f7Modules 54 }
f7eqp8tce2g5c   OBJECT IDENTIFIER ::= { f7Modules 55 }
f7eqpWcelsd   OBJECT IDENTIFIER ::= { f7Modules 56 }
f7eqpWcelsc   OBJECT IDENTIFIER ::= { f7Modules 57 }
f7eqpVsm   OBJECT IDENTIFIER ::= { f7Modules 58 }
f7eqpRsmolm   OBJECT IDENTIFIER ::= { f7Modules 59 }
f7eqpRsmsf   OBJECT IDENTIFIER ::= { f7Modules 60 }
f7eqpOscm   OBJECT IDENTIFIER ::= { f7Modules 61 }
f7eqp2oscm   OBJECT IDENTIFIER ::= { f7Modules 62 }
f7eqpDrm   OBJECT IDENTIFIER ::= { f7Modules 63 }
f7eqpXfpG   OBJECT IDENTIFIER ::= { f7Modules 64 }
f7eqpsfpd   OBJECT IDENTIFIER ::= { f7Modules 65 }
f7eqpSfpc   OBJECT IDENTIFIER ::= { f7Modules 66 }
f7eqpSfpg   OBJECT IDENTIFIER ::= { f7Modules 67 }
f7eqpSfpe   OBJECT IDENTIFIER ::= { f7Modules 68 }
f7eqpSh1hudcm   OBJECT IDENTIFIER ::= { f7Modules 69 }
f7eqpCustomc   OBJECT IDENTIFIER ::= { f7Modules 70 }
f7eqpCustomd   OBJECT IDENTIFIER ::= { f7Modules 71 }
f7eqpPsu1hudc   OBJECT IDENTIFIER ::= { f7Modules 72 }
f7eqpWcc2g7c   OBJECT IDENTIFIER ::= { f7Modules 73 }
f7eqp1csmuEwD   OBJECT IDENTIFIER ::= { f7Modules 74 }
f7eqp1csmuG   OBJECT IDENTIFIER ::= { f7Modules 75 }
f7eqp3BsmC   OBJECT IDENTIFIER ::= { f7Modules 76 }
f7eqpF2kSh5hu   OBJECT IDENTIFIER ::= { f7Modules 77 }
f7eqpF2kSh6hu   OBJECT IDENTIFIER ::= { f7Modules 78 }
f7eqp2Tca2g5s   OBJECT IDENTIFIER ::= { f7Modules 79 }
f7eqp8Csmuc   OBJECT IDENTIFIER ::= { f7Modules 80 }
f7eqpEdfaDgcb   OBJECT IDENTIFIER ::= { f7Modules 81 }
f7eqpOscm2n   OBJECT IDENTIFIER ::= { f7Modules 82 }
f7eqp4Tcc10gtd   OBJECT IDENTIFIER ::= { f7Modules 83 }
f7eqp4Tca4g   OBJECT IDENTIFIER ::= { f7Modules 84 }
f7eqpDcg   OBJECT IDENTIFIER ::= { f7Modules 85 }
f7eqp2Tcm2g5d   OBJECT IDENTIFIER ::= { f7Modules 86 }
f7eqp2Tcm2g5c   OBJECT IDENTIFIER ::= { f7Modules 87 }
f7eqpWcm2g5d   OBJECT IDENTIFIER ::= { f7Modules 88 }
f7eqpWcm2g5c   OBJECT IDENTIFIER ::= { f7Modules 89 }
f7eqpEdfmSgc   OBJECT IDENTIFIER ::= { f7Modules 90 }
f7eqpF2kDemiV2   OBJECT IDENTIFIER ::= { f7Modules 91 }
f7eqpPsm955   OBJECT IDENTIFIER ::= { f7Modules 92 }
f7Plugs   OBJECT IDENTIFIER ::= { fspR7VendorTypes 5 }
f7SFPCL   OBJECT IDENTIFIER ::= { f7Plugs 1 }
f7SFPHS   OBJECT IDENTIFIER ::= { f7Plugs 2 }
f7SFP2G1   OBJECT IDENTIFIER ::= { f7Plugs 3 }
f7SFP2G5   OBJECT IDENTIFIER ::= { f7Plugs 4 }
f7SFP4G   OBJECT IDENTIFIER ::= { f7Plugs 5 }
f7XFP10G   OBJECT IDENTIFIER ::= { f7Plugs 6 }

-- ports

f7Ports   OBJECT IDENTIFIER ::= { fspR7VendorTypes 6 }
f7OTU1   OBJECT IDENTIFIER ::= { f7Ports 1 }
f7OTU2   OBJECT IDENTIFIER ::= { f7Ports 2 }
f710GBE   OBJECT IDENTIFIER ::= { f7Ports 3 }
f7OC192   OBJECT IDENTIFIER ::= { f7Ports 4 }
f7OC48   OBJECT IDENTIFIER ::= { f7Ports 5 }
f7STM16   OBJECT IDENTIFIER ::= { f7Ports 6 }
f7STM64   OBJECT IDENTIFIER ::= { f7Ports 7 }
f710GFC   OBJECT IDENTIFIER ::= { f7Ports 8 }
f710GFP   OBJECT IDENTIFIER ::= { f7Ports 9 }
f7Error   OBJECT IDENTIFIER ::= { fspR7VendorTypes 7 }

END
