--
-- Version: 5.01.33
-- Date of Last Update: 5/7/2003
-- Modified by: Wai Tai (since 12/2001)
-- Third Author: Srinivas Tummala (6/2001 to 11/2001)
-- Second Author: Wai Tai (since 4/2000 to 5/2001)
-- Original Author: Rasta A. Mansour (9/1999)
--
-- Description: This MIB describes the manageable elements for the
--		LuxN optical fiber transmission product.  This MIB
--		is based on SNMPv1 MIB-2 specification.
--
-- Copyright (c) 2001 to 2003 - LuxN, Inc.
-- All Rights Reserved
--
-- History of Changes:
--

LUXN-MIB DEFINITIONS ::= BEGIN

        IMPORTS
                enterprises, Counter,
                Gauge, IpAddress        FROM RFC1155-SMI

                DisplayString		FROM RFC1213-MIB

                OBJECT-TYPE             FROM RFC-1212

                TRAP-TYPE               FROM RFC-1215;


        -- Full OID: iso org(3) dod(6) internet(1) private(4)
        -- enterprises (1)  1.3.6.1.4.1.4253

        luxN            OBJECT IDENTIFIER ::= { enterprises 4253 }


        -- groups in luxN mib

        configuration   OBJECT IDENTIFIER ::= { luxN 1 }
        performance     OBJECT IDENTIFIER ::= { luxN 2 }
        faults          OBJECT IDENTIFIER ::= { luxN 3 }
        security        OBJECT IDENTIFIER ::= { luxN 4 }
        accounting      OBJECT IDENTIFIER ::= { luxN 5 }

        -- subgroups in the configuration group

        manufacturing   OBJECT IDENTIFIER ::= { configuration 1 }
        cp              OBJECT IDENTIFIER ::= { configuration 2 }
        cc              OBJECT IDENTIFIER ::= { configuration 3 }
        mux             OBJECT IDENTIFIER ::= { configuration 4 }
        ps              OBJECT IDENTIFIER ::= { configuration 5 }
        download        OBJECT IDENTIFIER ::= { configuration 6 }
        fadm            OBJECT IDENTIFIER ::= { configuration 7 }
        oppm            OBJECT IDENTIFIER ::= { configuration 8 }
        mcm             OBJECT IDENTIFIER ::= { configuration 9 }
        fn              OBJECT IDENTIFIER ::= { configuration 10 }
        csim            OBJECT IDENTIFIER ::= { configuration 11 }
        rpsm            OBJECT IDENTIFIER ::= { configuration 12 }
        rsdm            OBJECT IDENTIFIER ::= { configuration 13 }
        rtdm            OBJECT IDENTIFIER ::= { configuration 14 }
        osam            OBJECT IDENTIFIER ::= { configuration 15 }
		rsm             OBJECT IDENTIFIER ::= { configuration 16 }
		upsm            OBJECT IDENTIFIER ::= { configuration 17 }
        systemConfig    OBJECT IDENTIFIER ::= { configuration 21 }
        topology        OBJECT IDENTIFIER ::= { configuration 22 }
        routing         OBJECT IDENTIFIER ::= { configuration 23 }
		ring			OBJECT IDENTIFIER ::= { configuration 24 }


        -- subgroups of the performance group

        current1           OBJECT IDENTIFIER ::= { performance 1 }
        historical         OBJECT IDENTIFIER ::= { performance 2 }
        specialConditions  OBJECT IDENTIFIER ::= { performance 3 }

        -- subgroups of the current subgroup

        systemPerf      OBJECT IDENTIFIER ::= { current1 1 }
        downloadPerf    OBJECT IDENTIFIER ::= { current1 2 }
        cpPerf          OBJECT IDENTIFIER ::= { current1 3 }
        ccPerf          OBJECT IDENTIFIER ::= { current1 4 }
        muxPerf         OBJECT IDENTIFIER ::= { current1 5 }
        psPerf          OBJECT IDENTIFIER ::= { current1 6 }
        fadmPerf        OBJECT IDENTIFIER ::= { current1 7 }
        oppmPerf        OBJECT IDENTIFIER ::= { current1 8 }
        mcmPerf         OBJECT IDENTIFIER ::= { current1 9 }	
        fnPerf          OBJECT IDENTIFIER ::= { current1 10 }
        csimPerf        OBJECT IDENTIFIER ::= { current1 11 }
        rpsmPerf        OBJECT IDENTIFIER ::= { current1 12 }
        rsdmPerf        OBJECT IDENTIFIER ::= { current1 13 }
        rtdmPerf        OBJECT IDENTIFIER ::= { current1 14 }
        osamPerf        OBJECT IDENTIFIER ::= { current1 15 }
		rsmPerf         OBJECT IDENTIFIER ::= { current1 16 }
		upsmPerf        OBJECT IDENTIFIER ::= { current1 17 }
		routingPerf	    OBJECT IDENTIFIER ::= { current1 21 }


        -- subgroups of the historical subgroup

        systemHist      OBJECT IDENTIFIER ::= { historical 1 }
        downloadHist    OBJECT IDENTIFIER ::= { historical 2 }
        cpHist          OBJECT IDENTIFIER ::= { historical 3 }
        ccHist          OBJECT IDENTIFIER ::= { historical 4 }
        muxHist         OBJECT IDENTIFIER ::= { historical 5 }
        psHist          OBJECT IDENTIFIER ::= { historical 6 }
        fadmHist        OBJECT IDENTIFIER ::= { historical 7 }
        oppmHist        OBJECT IDENTIFIER ::= { historical 8 }
        mcmHist         OBJECT IDENTIFIER ::= { historical 9 }
        fnHist          OBJECT IDENTIFIER ::= { historical 10 }
        csimHist        OBJECT IDENTIFIER ::= { historical 11 }
        rpsmHist        OBJECT IDENTIFIER ::= { historical 12 }
        rsdmHist        OBJECT IDENTIFIER ::= { historical 13 }
        rtdmHist        OBJECT IDENTIFIER ::= { historical 14 } 
        osamHist        OBJECT IDENTIFIER ::= { historical 15 }
		rsmHist         OBJECT IDENTIFIER ::= { historical 16 }
		upsmHist        OBJECT IDENTIFIER ::= { historical 17 } 

        -- subgroups of the specialConditions subgroup

        systemCond      OBJECT IDENTIFIER ::= { specialConditions 1 }
        downloadCond    OBJECT IDENTIFIER ::= { specialConditions 2 }
        cpCond          OBJECT IDENTIFIER ::= { specialConditions 3 }
        ccCond          OBJECT IDENTIFIER ::= { specialConditions 4 }
        muxCond         OBJECT IDENTIFIER ::= { specialConditions 5 }
        psCond          OBJECT IDENTIFIER ::= { specialConditions 6 }
        fadmCond        OBJECT IDENTIFIER ::= { specialConditions 7 }
        oppmCond        OBJECT IDENTIFIER ::= { specialConditions 8 }
        mcmCond         OBJECT IDENTIFIER ::= { specialConditions 9 }
        fnCond          OBJECT IDENTIFIER ::= { specialConditions 10 }
        rpsmCond        OBJECT IDENTIFIER ::= { specialConditions 12 }
        rsdmCond        OBJECT IDENTIFIER ::= { specialConditions 13 }
        rtdmCond        OBJECT IDENTIFIER ::= { specialConditions 14 } 
        osamCond        OBJECT IDENTIFIER ::= { specialConditions 15 }
		rsmCond         OBJECT IDENTIFIER ::= { specialConditions 16 }
		upsmCond        OBJECT IDENTIFIER ::= { specialConditions 17 } 

        -- subgroups of the faults group

        eventLog        OBJECT IDENTIFIER ::= { faults 1 }
        userLog         OBJECT IDENTIFIER ::= { faults 2 }
        diagnostics     OBJECT IDENTIFIER ::= { faults 3 }
        alarmLog        OBJECT IDENTIFIER ::= { faults 4 }

        -- subgroups of the security group

        userSecMgmt     OBJECT IDENTIFIER ::= { security 1 }
        systemSecMgmt   OBJECT IDENTIFIER ::= { security 2 }

        -- subgroups of the accounting group

        cpAcct          OBJECT IDENTIFIER ::= { accounting 1 }
        ccAcct          OBJECT IDENTIFIER ::= { accounting 2 }
        mcmAcct         OBJECT IDENTIFIER ::= { accounting 3 }

        --
        -- Global Data types
        --

        -- Textual conventions for the FlagType data type
        --
        -- on means enabled
        -- off means disabled
        --

        FlagType        ::= INTEGER { on(1), off(2) }

        --
        -- Global Data types
        --

        -- Textual conventions for the ResetType data type
        --
        -- Other is used for only get purpose
        -- Reset means set the flag to OFF or FALSE or whatever
        -- means reset

        ResetType        ::= INTEGER { other(1), reset(2) }

        -- Textual conventions for the RebootType data type
        --
        -- Other is used for only get purpose
        -- warmboot means to reboot the particular card chosen
        --

        RebootType        ::= INTEGER { other(1), warmboot(2) }


        -- Textual conventions for the Boolean data type
        --
        -- True or 'Y' is 1, False or 'N' is 2
        --

        Boolean         ::= INTEGER { true(1), false(2) }


        -- Textual conventions for the CardLocation data type
        --
        -- 1 means local, 2 means remote
        --

        CardLocation    ::= INTEGER { local(1), remote(2) }


        -- Textual conventions for the CardShelf data type
        --
        -- There could be up to 2 shelves per Chassis
        --

        CardShelf       ::= INTEGER (1..2)


        -- Textual conventions for the CardSlot data type
        --
        -- There could be up to 17 card slots per shelf
        --

        CardSlot        ::= INTEGER (1..17)


        -- Textual conventions for the ShelfInput data type
        --

        ShelfInput       ::= INTEGER (0..2)


        -- Textual conventions for the SlotInput data type
        --

        SlotInput        ::= INTEGER (0..17)


        -- Textual conventions for the CardName data type
        --
        -- Card name may be any alpha-numeric character string
        -- up to 32 characters.

        CardName        ::= DisplayString (SIZE (0..32))

        -- Textual conventions for the LinkName data type
        --
        -- Link name may be any alpha-numeric character string
        -- up to 40 characters.

        LinkName        ::= DisplayString (SIZE (0..40))

        -- Textual conventions for the CardType data type
        --
        -- There could be up to 20 different card type
        -- 

        CardType        ::= INTEGER	{
					ocmu(2),
					ocmi(3),
					ofcm(4),
					ofcd(5),
					fadm(6),
					oppm(7),
					mcm(8),
					oli(9),
					w4cd(10),
					w2cmd(13),
					rsdm(16),
					rpsm(17),
					rtdm(18),
					fadmb(19),
					osam(20),
					w4cm(21),
					rsm(22),
					upsm(23),
					ocme(24),
					oci(25),
					oxc(26),
					ocm10g(27),
					osamlp(29),
					osamhp(30)
					}

        -- Textual conventions for the CardStatus data type
        --
        -- The status' are: Critical, Major, Minor, and Normal.
        --
        -- Critical means that the device is experiencing a
        -- service outage.
        -- Major means that a service affecting fault exists.
        -- Minor means that a fault exists but it is not service
        -- affecting.
        -- Normal means all is well and the card is functioning
        -- acknowledged means that a fault of critical minor or major severity exists
        -- and is acknowledged by the user!

        -- properly.
        --

        CardStatus      ::= INTEGER { critical(1), major(2),
					minor(3), normal(4), acknowledged(5) }

        -- Textual conventions for the CardState data type
        --
        -- The states are: online, offline, empty, loopback, diag
        --
        -- online means the card is in the slot and working.
        -- offline means the card is in the slot but currently
	-- not working.
        -- empty means that the slot is empty (no card)
        -- loopback means the card is put in the loopback mode.
        -- diag means the card is put in the diagnostic test mode.
        --

        CardState       ::= INTEGER { empty(1), online(2), offline(3),
                                      loopback(4), diag(5) }


        -- Textual conventions for the RedundancyMode data type
        --
        -- Several cards, like CP or PS can have a redundant pair.
	-- This data type is used to indicate the state of those cards.
        --

        RedundancyMode  ::= INTEGER { active(1), standby(2) }


        -- Textual conventions for the Node Name data type
        --
        -- 
        -- Node name may be any alpha-numeric character string
        -- up to 32 characters.

        NodeName  ::= DisplayString(SIZE(0..32))


        -- Textual conventions for the Port Index data type
        --
        -- 
        -- There could be up 16 ports per card
	  --
	
	  PortIndex  ::= INTEGER(1..16)



        -- Textual conventions for the CardCycleMode data type
        --
        -- Each card can be cycled according to the following modes:
        --
        -- Request the card to be coldbooted (full initialization).
        -- Request the card to be warmbooted (new executable software
	-- loaded)
        -- Request the card to go offline
        -- Request the card to come back online
        -- Request the card to go into loopback mode
        -- Request the card to go into diagnostic mode
        --

        CardCycleMode   ::= INTEGER { coldboot(1), warmboot(2),
			offline(3), online(4), loopback(5), diag(6) }


        -- Textual conventions for the TrapStatus data type
        --
        -- The status' are: Critical, Major, Minor, Normal, and Clear.
        --
        -- Critical means that the device is experiencing a service outage.
        -- Major means that a service affecting fault exists.
        -- Minor means that a fault exists but it is not service affecting.
        -- Normal means all is well and the card is functioning properly.
	-- This trap status is treated as informational.
        -- Clear means that all previous alarms are cleared, and the
	-- current system status is Normal.
        --

        TrapStatus      ::= INTEGER { critical(1), major(2), minor(3),
                                      normal(4), clear(5) }


        -- Textual conventions for the CardState data type
        -- Textual conventions for the HistoryMode data type
        --
        -- Two types of historical counters are maintained.  One counter is
        -- the daily counter set.  It aggregates the 15 minute performance
        -- counters into one daily sum counter.  At the end of the day,
        -- this counter is reset.  The second counter is the perpetual
        -- longterm counter.  This counter aggregates the 15 minute
        -- performance counters for an indefinite amount of time.  When
	-- the counter exceeds the maximum value, it will wrap around.
	--

        HistoryMode     ::= INTEGER { daily(1), longterm(2) }


        -- Textual conventions for the EventBuffer data type
        --
        -- There could be up to 1000 event log entries
	-- maintained by the system in FIFO order.
        --

        EventBuffer     ::= INTEGER (1..1000)

        -- Textual conventions for the UserBuffer data type
        --
        -- There could be up to 100 user action log entries
	-- maintained by the system in FIFO order.
        --

        UserBuffer     ::= INTEGER (1..100)


        -- Textual conventions for the LogonID data type
        --
        -- Logon ID is in printable ASCII character set, and up to 15
	-- chars.
        -- A NULL value indicates no valid Logon ID is specified.
        --

        LogonID         ::= DisplayString ( SIZE (0..15) )


        -- Textual conventions for the HashedPasswd data type
        --
        -- Passwords maintained by the embedded LuxN application are
	-- hashed (one-way encrypted) to protect them from
	-- unauthorized view.  A simple hashing (message digest)
	-- algorithm like the one below can be used to hide the
	-- passwords.  LuxN passwords are only used to compare
	-- against, so it's OK to hash them.
        --
        -- Let N be the length of the clear text password, up to 10
	-- bytes. Let M be Twice maximum password length.  Exactly
	-- 20 bytes.  Let R be the number of rounds of hashing.  Say
	-- 10.  Let the password be stored in an array P with
	-- dimension M.  Note, array P is indexed from 1 and not
	-- from 0 in the discussion below.
        --
        -- The following algorithm (due to Rasta Mansour) hashes
	-- the array P in a one-way manner with a very low
	-- probability of collision.
        --
        --      Fill the array P with the Password of Length N up
	--      to the value of M.  Simple cyclic copy of the clear
	--	text password will do.
        --
        --      Execute the following rounds of the alogrithm below
	--	on the array P.
        --
        --      For i=1 to R do
        --              For j=1 to M do
        --                      Let k = ((j + i) mod M) + 1
        --                      Let P[j] = (P[j] + (k * P[k])) mod 256
        --                      if (P[j] == 0)
        --                              Let P[j] = k + N
        --
        --                      Let k = ((k * N) mod M) + 1
        --                      Let c = P[j]
        --                      Let P[j] = P[k]
        --                      Let P[k] = c
        --

        HashedPasswd    ::= OCTET STRING ( SIZE (1..20) )

	EncryptedCommunity	::= DisplayString ( SIZE (0..32) )


        -- Textual conventions for the FileName data type
        --
        -- file name may be any alpha-numeric character string up
	-- to 32 characters.
        --

        FileName        ::= DisplayString (SIZE (0..32))


        -- Textual conventions for the EntityName data type
        --
        -- EntityName is in printable ASCII character set, and up
	-- to 15 chars.
        -- A NULL value indicates no valid name is specified.
        --

        EntityName      ::= DisplayString ( SIZE (0..15) )


        -- Textual conventions for the Date and Time data type
        --
        --      field   Octets  Contents                Range
        --      -----   ------  --------------------    --------
        --        1       1-2   year                    0..65535
        --                (in big endian order)
        --        2        3    month                   1..12
        --        3        4    day                     1..31
        --        4        5    hour                    0..23
        --        5        6    minutes                 0..59
        --        6        7    seconds                 0..59
        --        7        8    deci-seconds            0..9
        --                 (100 milliseconds)
        --        8        9    direction from UTC      "+" | "-"
        --        9       10    hours from UTC          0..11
        --       10       11    minutes from UTC        0..59
        --
        -- Note, if only local time is known, then timezone information
        -- (fields 8-10) is not present.
        --
        -- If only date is known, then the time part (fields 5-11) is not
        -- present.
        --

        DateAndTime     ::= DisplayString ( SIZE( 0..20 ) )


        -- Textual conventions for the VersionString data type
        --
        -- A version string is in the form:
        --
        --  'V' major_num '.' minor_num '.' alpha_num
        --
        -- Where, major_num and minor_num can be any 3 digit number.  The
        -- alpha_num is any lower case alpha character.  An example of a
        -- version string in this syntax is: V1.05.c.
        --
        -- The rules for assignment (creation) of a version string are as
        -- follows:
        --
        -- 1.  If the interface or the functionality has significantly changed,
        --     the major_num is incremented.
        -- 2.  If bugs are fixed but the functionality and the interface are
        --     generally the same, the minor_num is incremented.
        -- 3.  For interium releases, specially during in-house testing, or
        --     as experimental engineering bug fix release to a client, the
        --     alpha_num is incremented.
        --

        VersionString   ::= DisplayString (SIZE (0..12))


        -- Textual conventions for the SerialString data type
        --
        -- Serial number may be any alpha numeric printable character string
        -- up to 17 characters.
        --

        SerialString    ::= DisplayString (SIZE (0..17))


        -- Textual conventions for the ModelString data type
        --
        -- Model Type may be any alpha numeric printable character string
        -- up to 10 characters.
        --

        ModelString     ::= DisplayString (SIZE (0..10))

        -- Textual conventions for the ModelNum data type
        --
        -- Model number may be any alpha numeric printable character string
        -- up to 15 characters.
        --

        ModelNum     ::= DisplayString (SIZE (0..15))

		-- For SW download support

		-- Textual conventions for the FtpMode data type
		FtpMode			::= INTEGER { active(1), passive(2) }
	
		-- Textual conventions for the DownloadType data type
		DownloadType		::= DisplayString (SIZE (0..32))

		-- Textual conventions for the DownloadLocation data type
		DownloadLocation	::= INTEGER { local(1), remote(2), both(3) }

		-- Textual conventions for the DownloadShelf data type
		DownloadShelf		::= INTEGER (0..2)

		-- Textual conventions for the DownloadSlot data type
		DownloadSlot		::= INTEGER (0..17)

		-- Textual conventions for the OSMode data type
		OSMode				::= DisplayString (SIZE (0..10))

		-- Textual conventions for the ReleaseDate data type
		ReleaseDate			::= DisplayString (SIZE (0..10))

		-- Textual conventions for the OSMode data type
		OSState				::= INTEGER { operating(1), backup(2) }
		
		-- Textual conventions for the UpdateOSMode data type
		UpdateOSMode		::= INTEGER { toggle(1), revert(2) }

		-- Textual conventions for the DownloadStatus data type
		DownloadStatus		::= INTEGER { idle(1), ftp-inprogress(2),
							mod-inprogress(3) }

		-- Textual conventions for the RingID name data type
        RingIdName			::= DisplayString (SIZE (0..16))

		-- Textual conventions for the PathID name data type
        PathIdName			::= DisplayString (SIZE (0..16))

        -- The elements in the manufacturing subgroup of the configuration group

        mfgName         OBJECT-TYPE
                SYNTAX  DisplayString (SIZE (0..30))
                ACCESS  read-only
                STATUS  mandatory
                DESCRIPTION
                        "Manufacturing name of the device.  Up to 30 characters"
                ::= { manufacturing 1 }

        mfgDate         OBJECT-TYPE
                SYNTAX  DateAndTime
                ACCESS  read-only
                STATUS  mandatory
                DESCRIPTION
                        "Date and Time of manufacturing of the chassis"
                ::= { manufacturing 2 }

        mfgSerialNum    OBJECT-TYPE
                SYNTAX  SerialString
                ACCESS  read-only
                STATUS  mandatory
                DESCRIPTION
                        "Serial # of the Chassis."
                ::= { manufacturing 3 }

        mfgModelType    OBJECT-TYPE
                SYNTAX  ModelString
                ACCESS  not-accessible
                STATUS  mandatory
                DESCRIPTION
                        "Model type of the chassis. Up to 10 characters"
                ::= { manufacturing 4 }

        mfgDefaultID    OBJECT-TYPE
                SYNTAX  LogonID
                ACCESS  read-only
                STATUS  mandatory
                DESCRIPTION
                        "Default one-time user ID.  This ID should be used
                         for the first time access to the system.  This ID
                         will not be accepted once a real user ID is added."
                ::= { manufacturing 5 }

        mfgDfltPasswd   OBJECT-TYPE
                SYNTAX  HashedPasswd
                ACCESS  read-only
                STATUS  mandatory
                DESCRIPTION
                        "Default one-time password to go with the default
                         user ID.  The password may contain non-printable
                         characters up to 10 ASCII characters.  Passwords
                         are hashed and are for comparison only"
                ::= { manufacturing 6 }


        mfgNumShelves   OBJECT-TYPE
                SYNTAX  CardShelf
                ACCESS  read-only 
                STATUS  mandatory
                DESCRIPTION
                        "Number of shelves in the chassis.  This number
                         reflects the number of rows of the table below.
                         This number is automatically adjusted everytime
                         a row is added to the table below."
                ::= { manufacturing 9 }

        mfgShelfTable   OBJECT-TYPE
                SYNTAX  SEQUENCE OF MfgShelfEntry
                ACCESS  not-accessible
                STATUS  mandatory
                DESCRIPTION
                        "This table represents the number of shelves and the
                         number of slots per shelf in the chassis."
                ::= { manufacturing 10 }

        mfgShelfEntry   OBJECT-TYPE
                SYNTAX  MfgShelfEntry
                ACCESS  not-accessible
                STATUS  mandatory
                DESCRIPTION
                        "Specifies the index for each row in the table below"
                INDEX { mfgShelfID }
                ::= { mfgShelfTable 1 }

        MfgShelfEntry   ::=
                SEQUENCE {
                        mfgShelfID      CardShelf,
                        mfgNumSlots     INTEGER
                }

        mfgShelfID      OBJECT-TYPE
                SYNTAX  CardShelf
                ACCESS  read-only
                STATUS  mandatory
                DESCRIPTION
                        "Integer ID of each shelf in the chassis.  The shelf number
			 is always one for both WS3208 and WS3217.  In the case of
			 of WS3234, the bottom shelf is 1 while the top shelf is 2.
			 As for WS6400, the order of numbering is from the top shelf
			 to the bottom shelf.  In other words, the top shelf is
			 assigned 1."
                ::= { mfgShelfEntry 1 }

        mfgNumSlots     OBJECT-TYPE
                SYNTAX  CardSlot
                ACCESS  read-only 
                STATUS  mandatory
                DESCRIPTION
                        "total number of slots in a given shelf."
                ::= { mfgShelfEntry 2 }

        mfgCRCChecksum  OBJECT-TYPE
                SYNTAX  DisplayString (SIZE (0..8))
                ACCESS  read-only
                STATUS  mandatory
                DESCRIPTION
                        "32 bit CRC of the manufacturing section.  This CRC
                         is automatically calculated everytime information
                         is updated from the manufacturing section.  The
                         manufacturing section is static once the chassis
                         leaves the LuxN manufacturing premise."
                ::= { manufacturing 11 }

        mfgChassisType     OBJECT-TYPE
                SYNTAX  INTEGER { wavstation1(1),
				  wavstation2(2),
				  wavfarer2(3),
				  wavportal2(4),
				  ws3208(5)
				}
                ACCESS  read-only
                STATUS  mandatory
                DESCRIPTION
                        "Type of chassis."
                ::= { manufacturing 12 }

        mfgPsType     OBJECT-TYPE
                SYNTAX  INTEGER { dcOny(1), 
					acOnly(2),
					mixedDcAc(3),
					unknown(4)
				}
                ACCESS  read-only
                STATUS  mandatory
                DESCRIPTION
                        "Type of power supplies."
                ::= { manufacturing 13 }


        -- The elements in the cp subgroup of the configuration group

        cpIpAddress     OBJECT-TYPE
                SYNTAX  IpAddress
                ACCESS  read-write
                STATUS  mandatory
                DESCRIPTION
                        "IP Address of the Active Communication Processor"
                ::= { cp 1 }

        cpNetMask       OBJECT-TYPE
                SYNTAX  IpAddress
                ACCESS  read-write
                STATUS  mandatory
                DESCRIPTION
                        "Net mask for the Active Communication Processor"
                ::= { cp 2 }

        cpMIBVersion    OBJECT-TYPE
                SYNTAX  VersionString
                ACCESS  read-only
                STATUS  mandatory
                DESCRIPTION
                        "Version of the LuxN MIB implemented by this device.
                         This value may be reset everytime a new CP code
                         is downloaded."
                ::= { cp 3 }

        cpBootPromVer   OBJECT-TYPE
                SYNTAX  VersionString
                ACCESS  read-only
                STATUS  mandatory
                DESCRIPTION
                        "The current version string of the Boot PROM code"
                ::= { cp 4 }

        cpROMSize       OBJECT-TYPE
                SYNTAX  INTEGER (1..16384)
                ACCESS  read-only
                STATUS  mandatory
                DESCRIPTION
                        "Total Size of the ROM in Kilobyes"
                ::= { cp 5 }

        cpNumSubDiv     OBJECT-TYPE
                SYNTAX  INTEGER (1..20)
                ACCESS  read-only
                STATUS  mandatory
                DESCRIPTION
                        "Number of the subdivisions of the ROM."
                ::= { cp 6 }

        cpSubDivTable   OBJECT-TYPE
                SYNTAX  SEQUENCE OF CpSubDivEntry
                ACCESS  not-accessible
                STATUS  mandatory
                DESCRIPTION
                        "This table represents the number of sub divisions
                         and the size of each subdivision in ROM memory"
                ::= { cp 7 }

        cpSubDivEntry   OBJECT-TYPE
                SYNTAX  CpSubDivEntry
                ACCESS  not-accessible
                STATUS  mandatory
                DESCRIPTION
                        "Specifies the index for each row in the table below"
                INDEX { cpSubDivIndex }
                ::= { cpSubDivTable 1 }

        CpSubDivEntry   ::=
                SEQUENCE {
                        cpSubDivIndex   INTEGER,
                        cpSubDivDescr   DisplayString,
                        cpSubDivSize    INTEGER,
                        cpSubDivOffset  OCTET STRING,
                     	cpSubDivImgVersion    DisplayString,
                     	cpSubDivImgDBVersion  DisplayString 
                }

        cpSubDivIndex   OBJECT-TYPE
                SYNTAX  INTEGER (1..20)
                ACCESS  read-only
                STATUS  mandatory
                DESCRIPTION
                        "Integer ID of each sub division in the ROM.  The order
                         of numbering is from the top of the ROM to the bottom
                         of the ROM."
                ::= { cpSubDivEntry 1 }

        cpSubDivDescr   OBJECT-TYPE
                SYNTAX  DisplayString (SIZE (0..20))
                ACCESS  read-only
                STATUS  mandatory
                DESCRIPTION
                        "Display Name of each Sub Division in ROM"
                ::= { cpSubDivEntry 2 }

        cpSubDivSize    OBJECT-TYPE
                SYNTAX  INTEGER (1..3145728)
                ACCESS  read-only
                STATUS  mandatory
                DESCRIPTION
                        "Size of each sub division in ROM in bytes"
                ::= { cpSubDivEntry 3 }

        cpSubDivOffset  OBJECT-TYPE
                SYNTAX  OCTET STRING (SIZE (0..8))
                ACCESS  read-only
                STATUS  mandatory
                DESCRIPTION
                        "Starting address of each sub division in the ROM
                         in HEX notation."
                ::= { cpSubDivEntry 4 }

     	  cpSubDivImgVersion    OBJECT-TYPE
                SYNTAX  DisplayString 
                ACCESS  read-only 
                STATUS  mandatory
                DESCRIPTION
                        "Display Version of each Images in ROM."
                ::= { cpSubDivEntry 5 }

     	  cpSubDivImgDBVersion  OBJECT-TYPE
                SYNTAX  DisplayString 
                ACCESS  read-only
                STATUS  mandatory
                DESCRIPTION
                        "Display Database Version of each Images in ROM."
                ::= { cpSubDivEntry  6 }

        cpTable         OBJECT-TYPE
                SYNTAX  SEQUENCE OF CpEntry
                ACCESS  not-accessible
                STATUS  mandatory
                DESCRIPTION
                        "This table represents the information for each
                         active or standby communication processor"
                ::= { cp 8 }

        cpEntry         OBJECT-TYPE
                SYNTAX  CpEntry
                ACCESS  not-accessible
                STATUS  mandatory
                DESCRIPTION
                        "Specifies the index for each row in the table below"
                INDEX { cpCardShelf, cpCardSlot }
                ::= { cpTable 1 }

        CpEntry         ::=
                SEQUENCE {
                        cpCardShelf     CardShelf,
                        cpCardSlot      INTEGER,
                        cpMode          RedundancyMode,
                        cpDsgntdMode    RedundancyMode,
                        cpState         CardState,
                        cpMacAddr       OCTET STRING,
                        cpName          CardName,
                        cpMfgDate       DateAndTime,
                        cpSerialNum     SerialString,
                        cpModelType     INTEGER,
                        cpFWVersionID   VersionString,
                        cpSetState      INTEGER,
                        cpHWName        DisplayString
                }


        cpCardShelf     OBJECT-TYPE
                SYNTAX  CardShelf
                ACCESS  read-only
                STATUS  mandatory
                DESCRIPTION
                        "The shelf the card is in."
                ::= { cpEntry 1 }

        cpCardSlot      OBJECT-TYPE
                SYNTAX  CardSlot
                ACCESS  read-only
                STATUS  mandatory
                DESCRIPTION
                        "The slot within the shelf the card is in."
                ::= { cpEntry 2 }


        cpMode          OBJECT-TYPE
                SYNTAX  RedundancyMode
                ACCESS  read-only
                STATUS  mandatory
                DESCRIPTION
                        "Type of the communication processor.  The valid types
                         are Active or Standby."
                ::= { cpEntry 3 }

        cpDsgntdMode    OBJECT-TYPE
                SYNTAX  RedundancyMode
                ACCESS  read-only
                STATUS  mandatory
                DESCRIPTION
                        "Designation Type of the communication processor.  The
                         valid types are Active or Standby."
                ::= { cpEntry 4 }

        cpState         OBJECT-TYPE
                SYNTAX  CardState
                ACCESS  read-only
                STATUS  mandatory
                DESCRIPTION
                        "The state of the CP card."
                ::= { cpEntry 5 }

        cpMacAddr       OBJECT-TYPE
                SYNTAX  OCTET STRING (SIZE (0..6))
                ACCESS  read-only
                STATUS  mandatory
                DESCRIPTION
                        "MAC address of the Communication processor in HEX"
                ::= { cpEntry 6 }



        cpName          OBJECT-TYPE
                SYNTAX  DisplayString (SIZE (0..32))
                ACCESS  read-write
                STATUS  mandatory
                DESCRIPTION
                        "Display (Network) name of the Communication processor"
                ::= { cpEntry 7 }

        cpMfgDate       OBJECT-TYPE
                SYNTAX  DateAndTime
                ACCESS  read-only
                STATUS  mandatory
                DESCRIPTION
                        "Date and Time of manufacturing of the CP card"
                ::= { cpEntry 8 }

        cpSerialNum     OBJECT-TYPE
                SYNTAX  SerialString
                ACCESS  read-only
                STATUS  mandatory
                DESCRIPTION
                        "Serial # of the CP card."
                ::= { cpEntry 9 }

        cpModelType     OBJECT-TYPE
                SYNTAX  INTEGER { mpmMod(1) }
                ACCESS  read-only
                STATUS  mandatory
                DESCRIPTION
                        "Model type of the CP."
                ::= { cpEntry 10 }

        cpFWVersionID     OBJECT-TYPE
                SYNTAX  VersionString
                ACCESS  read-only
                STATUS  mandatory
                DESCRIPTION
                        "The current version string of the CP FW code"
                ::= { cpEntry 11 }

        cpSetState      OBJECT-TYPE
                SYNTAX  RebootType   
		ACCESS  read-write
                STATUS  mandatory
                DESCRIPTION
                        "Instruct the CP to do a warmboot. A get on this will
			 always return an other." 
                ::= { cpEntry 12 }


        cpHWName       OBJECT-TYPE
                SYNTAX  DisplayString (SIZE (0..32))
                ACCESS  read-only
                STATUS  mandatory
                DESCRIPTION
                        "Display Hardware name of the CP Card."
                ::= { cpEntry 13 }



        cpSetMode       OBJECT-TYPE
                SYNTAX  RedundancyMode
                ACCESS  read-write
                STATUS  mandatory
                DESCRIPTION
                        "Toggle the Active/Standby mode of the active CP."
                ::= { cp 9 }

        cpSNMPTrapHost1 OBJECT-TYPE
                SYNTAX  IpAddress
                ACCESS  read-write
                STATUS  mandatory
                DESCRIPTION
                        "IP Address of the first SNMP Trap host.  A NULL IP
                         address means no TRAP should be sent to this address.
			 Duplicate IP addresses will be rejected."
                ::= { cp 10 }

        cpSNMPTrapHost2 OBJECT-TYPE
                SYNTAX  IpAddress
                ACCESS  read-write
                STATUS  mandatory
                DESCRIPTION
                        "IP Address of the second SNMP Trap host.  A NULL IP
                         address means no TRAP should be sent to this address.
			 Duplicate IP addresses will be rejected."
                ::= { cp 11 }

        cpSNMPTrapHost3 OBJECT-TYPE
                SYNTAX  IpAddress
                ACCESS  read-write
                STATUS  mandatory
                DESCRIPTION
                        "IP Address of the third SNMP Trap host.  A NULL IP
                         address means no TRAP should be sent to this address.
			 Duplicate IP addresses will be rejected."
                ::= { cp 12 }

        cpSNMPSendTrap  OBJECT-TYPE
                SYNTAX  Boolean
                ACCESS  read-write
                STATUS  mandatory
                DESCRIPTION
                        "If set to true, traps will be sent out.  If set to
                         false, traps will not be sent out.  This variable
                         is reset to true (enable) on each boot cycle."
                ::= { cp 13 }

        cpGateway OBJECT-TYPE
                SYNTAX  IpAddress
                ACCESS  read-write
                STATUS  mandatory
                DESCRIPTION
                        "Gateway IP Address of the Active Communication Processor.  A
			 NULL IP address means Gateway hasn't been configured."
                ::= { cp 14 }

        cpMaxSessions OBJECT-TYPE
                SYNTAX  INTEGER (1..6)
                ACCESS  read-write
                STATUS  mandatory
                DESCRIPTION
                        "Maximum allowed Telnet Sessions on the Active Communication
			 Processor. Valid values are 1 to 6."
                ::= { cp 15 }

        cpSessionTimeout OBJECT-TYPE
                SYNTAX  INTEGER 
                ACCESS  read-write
                STATUS  mandatory
                DESCRIPTION
                        "Maximum timeout (in seconds) that can be set for a
			 Telnet session on the Active Communication Processor.
			 Valid values are greater than 30 secs."                
		::= { cp 16 }

        cpDate	OBJECT-TYPE
                    SYNTAX  DateAndTime 
                    ACCESS  read-write
                    STATUS  mandatory
                    DESCRIPTION
		        "Current Date on the Active Communication Processor.
		         The format is in the form of mm-dd-yy in which mm
		         is the two digit month, dd is the two digit day of
		         the month, and yy is the two digit year."
                    ::= { cp 17 }

        cpTime	OBJECT-TYPE
                    SYNTAX  DateAndTime 
                    ACCESS  read-write
                    STATUS  mandatory
                    DESCRIPTION
		        "Current Time on the Active Communication Processor.
		         The format is in the form of hh:mm:ss in which
		         hh is the hour, mm is the minute and ss is the
		         second.  The valid values for hour goes from 0
		         to 23. In order to work with LuxN NMS, it needs to be
				 set to GMT time"
                    ::= { cp 18 }

        cpGetCommunity	OBJECT-TYPE
                    SYNTAX  EncryptedCommunity 
                    ACCESS  read-write
                    STATUS  mandatory
                    DESCRIPTION
		        "User configurable SNMP Get Community String."
                    ::= { cp 19 }

        cpSetCommunity	OBJECT-TYPE
                    SYNTAX  EncryptedCommunity
                    ACCESS  read-write
                    STATUS  mandatory
                    DESCRIPTION
		        "User Configurable SNMP Set Community String."
                    ::= { cp 20 }

        cpSystemName	OBJECT-TYPE
                    SYNTAX  DisplayString(SIZE(0..59)) 
                    ACCESS  read-write
                    STATUS  mandatory
                    DESCRIPTION
		        "User Configurable System Name."
                    ::= { cp 21 }

        cpSNMPTrapCommunity1	OBJECT-TYPE
                    SYNTAX  EncryptedCommunity 
                    ACCESS  read-write
                    STATUS  mandatory
                    DESCRIPTION
		        "User configurable trap community string for first trap host.
		         Will return an error if the corresponding trap host is
		         invalid or not set."
                    ::= { cp 22 }

        cpSNMPTrapCommunity2	OBJECT-TYPE
                    SYNTAX  EncryptedCommunity 
                    ACCESS  read-write
                    STATUS  mandatory
                    DESCRIPTION
		        "User configurable trap community string for second trap host.
		         Will return an error if the corresponding trap host is
		         invalid or not set."
                    ::= { cp 23 }

        cpSNMPTrapCommunity3	OBJECT-TYPE
                    SYNTAX  EncryptedCommunity 
                    ACCESS  read-write
                    STATUS  mandatory
                    DESCRIPTION
		        "User configurable trap community string for third trap host.
		         Will return an error if the corresponding trap host is
		         invalid or not set."
                    ::= { cp 24 }

        cpHttp  OBJECT-TYPE
			        SYNTAX	INTEGER {enabled(1), disabled(2)}
			        ACCESS	read-write
			        STATUS  mandatory
			        DESCRIPTION
                        "HTTP server enabled or not."
			        ::= { cp 25 }

        cpIMNIpAddress     OBJECT-TYPE
                SYNTAX  IpAddress
                ACCESS  read-write
                STATUS  mandatory
                DESCRIPTION
                        "IMN Ip address. Use for IP/IWM"
                ::= { cp 26 }

		cpUpsrMode	OBJECT-TYPE
                SYNTAX  INTEGER
				{
					enable(1),
					disable(2)
				}
                ACCESS  read-write
                STATUS  mandatory
                DESCRIPTION
                        "UPSR mode:  enable and disable."
                ::= { cp 27 }

		cpAutoModuleUpdate	OBJECT-TYPE
                SYNTAX  INTEGER
				{
					enable(1),
					disable(2)
				}
                ACCESS  read-write
                STATUS  mandatory
                DESCRIPTION
                        "Flag to automatically enable/disable module update."
                ::= { cp 28 }

        cpSNMPTrapHost4 OBJECT-TYPE
                SYNTAX  IpAddress
                ACCESS  read-write
                STATUS  mandatory
                DESCRIPTION
                        "IP Address of the fourth SNMP Trap host.  A NULL IP
                         address means no TRAP should be sent to this address.
			 Duplicate IP addresses will be rejected."
                ::= { cp 29 }

        cpSNMPTrapHost5 OBJECT-TYPE
                SYNTAX  IpAddress
                ACCESS  read-write
                STATUS  mandatory
                DESCRIPTION
                        "IP Address of the fifth SNMP Trap host.  A NULL IP
                         address means no TRAP should be sent to this address.
			 Duplicate IP addresses will be rejected."
                ::= { cp 30 }


        cpSNMPTrapCommunity4	OBJECT-TYPE
                    SYNTAX  EncryptedCommunity 
                    ACCESS  read-write
                    STATUS  mandatory
                    DESCRIPTION
		        "User configurable trap community string for fourth trap host.
		         Will return an error if the corresponding trap host is
		         invalid or not set."
                    ::= { cp 31 }

        cpSNMPTrapCommunity5	OBJECT-TYPE
                    SYNTAX  EncryptedCommunity 
                    ACCESS  read-write
                    STATUS  mandatory
                    DESCRIPTION
		        "User configurable trap community string for fifth trap host.
		         Will return an error if the corresponding trap host is
		         invalid or not set."
                    ::= { cp 32 }

		cpSNMPTrapHostPort1		OBJECT-TYPE
                SYNTAX  INTEGER(0..65534)
                ACCESS  read-write
                STATUS  mandatory
                DESCRIPTION
                        "User configurable trap port for the first trap host.
						 Default value is 162"
                ::= { cp 33 }


		cpSNMPTrapHostPort2		OBJECT-TYPE
                SYNTAX  INTEGER(0..65534)
                ACCESS  read-write
                STATUS  mandatory
                DESCRIPTION
                        "User configurable trap port for the second trap host.
						 Default value is 162"
                ::= { cp 34 }

		cpSNMPTrapHostPort3		OBJECT-TYPE
                SYNTAX  INTEGER(0..65534)
                ACCESS  read-write
                STATUS  mandatory
                DESCRIPTION
                        "User configurable trap port for the third trap host.
						 Default value is 162"
                ::= { cp 35 }

		cpSNMPTrapHostPort4		OBJECT-TYPE
                SYNTAX  INTEGER(0..65534)
                ACCESS  read-write
                STATUS  mandatory
                DESCRIPTION
                        "User configurable trap port for the fourth trap host.
						 Default value is 162"
                ::= { cp 36 }

		cpSNMPTrapHostPort5		OBJECT-TYPE
                SYNTAX  INTEGER(0..65534)
                ACCESS  read-write
                STATUS  mandatory
                DESCRIPTION
                        "User configurable trap port for the fifth trap host.
						 Default value is 162"
                ::= { cp 37 }



        -- The elements in the cc subgroup of the configuration group

        ccBootPromVer   OBJECT-TYPE
                SYNTAX  VersionString
                ACCESS  read-only
                STATUS  mandatory
                DESCRIPTION
                        "The current version string of the CC Boot PROM code"
                ::= { cc 1 }

        ccROMSize       OBJECT-TYPE
                SYNTAX  INTEGER (0..1024)
                ACCESS  read-only
                STATUS  mandatory
                DESCRIPTION
                        "Total Size of the CC ROM in Kilobyes"
                ::= { cc 2 }

        ccNumSubDiv     OBJECT-TYPE
                SYNTAX  INTEGER (0..20)
                ACCESS  read-only
                STATUS  mandatory
                DESCRIPTION
                        "Number of the subdivisions of the ROM."
                ::= { cc 3 }

        ccSubDivTable   OBJECT-TYPE
                SYNTAX  SEQUENCE OF CcSubDivEntry
                ACCESS  not-accessible
                STATUS  mandatory
                DESCRIPTION
                        "This table represents the number of sub divisions
                         and the size of each subdivision in ROM memory"
                ::= { cc 4 }

        ccSubDivEntry   OBJECT-TYPE
                SYNTAX  CcSubDivEntry
                ACCESS  not-accessible
                STATUS  mandatory
                DESCRIPTION
                        "Specifies the index for each row in the table below"
                INDEX { ccSubDivIndex }
                ::= { ccSubDivTable 1 }

        CcSubDivEntry   ::=
                SEQUENCE {
                        ccSubDivIndex   INTEGER,
                        ccSubDivDescr   DisplayString,
                        ccSubDivSize    INTEGER,
                        ccSubDivOffset  OCTET STRING
                }

        ccSubDivIndex   OBJECT-TYPE
                SYNTAX  INTEGER (1..20)
                ACCESS  read-only
                STATUS  mandatory
                DESCRIPTION
                        "Integer ID of each sub division in the ROM.  The order
                         of numbering is from the top of the ROM to the bottom
                         of the ROM."
                ::= { ccSubDivEntry 1 }

        ccSubDivDescr   OBJECT-TYPE
                SYNTAX  DisplayString (SIZE (0..20))
                ACCESS  read-only
                STATUS  mandatory
                DESCRIPTION
                        "Display Name of each Sub Division in ROM"
                ::= { ccSubDivEntry 2 }

        ccSubDivSize    OBJECT-TYPE
                SYNTAX  INTEGER (1..1024)
                ACCESS  read-only
                STATUS  mandatory
                DESCRIPTION
                        "Size of each sub division in ROM in kilobytes"
                ::= { ccSubDivEntry 3 }

        ccSubDivOffset  OBJECT-TYPE
                SYNTAX  OCTET STRING (SIZE (0..8))
                ACCESS  read-only
                STATUS  mandatory
                DESCRIPTION
                        "Starting address of each sub division in the ROM
                         in HEX notation."
                ::= { ccSubDivEntry 4 }

        ccNumber        OBJECT-TYPE
                SYNTAX  INTEGER
                ACCESS  read-only
                STATUS  mandatory
                DESCRIPTION
                        "Number of CC rows in the following table.  This number
                         is automatically updated whenever a new row is added
                         to the table below."
                ::= { cc 5 }

        ccTable         OBJECT-TYPE
                SYNTAX  SEQUENCE OF CcEntry
                ACCESS  not-accessible
                STATUS  mandatory
                DESCRIPTION
                        "This table represents the information for each
                         channel card"
                ::= { cc 6 }

        ccEntry         OBJECT-TYPE
                SYNTAX  CcEntry
                ACCESS  not-accessible
                STATUS  mandatory
                DESCRIPTION
                        "Specifies the index for each row in the table below"
                INDEX { ccCardLocation, ccCardShelf, ccCardSlot }
                ::= { ccTable 1 }

        CcEntry         ::=
                SEQUENCE {
                        ccCardLocation              CardLocation,
                        ccCardShelf                 CardShelf,
                        ccCardSlot                  INTEGER,
                        ccMfgDate                   DateAndTime,
                        ccSerialNum                 SerialString,
                        ccModelType                 INTEGER,
                        ccName                      CardName,
                        ccFWVersionID               VersionString,
                        ccMfgBiasCurrent            INTEGER,
                        ccMfgModulation             INTEGER,
                        ccMfgApc                    INTEGER,
                        ccMfgIwmModulation          INTEGER,
                        ccMfgRefClock               INTEGER,
                        ccMfgClockDiv               INTEGER,
                        ccBandwidth                 INTEGER,
                        ccSetState                  INTEGER,
                        connMuxChassis              INTEGER,
                        connMuxShelf                INTEGER,
                        connMuxSlot                 INTEGER,
                        connMuxPort                 INTEGER,
                        connDemuxChassis            INTEGER,
                        connDemuxShelf              INTEGER,
                        connDemuxSlot               INTEGER,
                        connDemuxPort               INTEGER,
                        ccModelNum                  DisplayString,
                        ccLinkITUNum                DisplayString,
                        ccLinkWavelength            DisplayString,
                        ccLaserType                 INTEGER,
                        ccRecvDiode                 INTEGER,
                        ccLinkAutoDisable           INTEGER,
                        ccLinkName                  LinkName,
                        ccCsimModule                INTEGER,
                        ccHWName                    CardName,
                        ccBackpackModule            INTEGER,
                        ccBackpackRxITUNumber       DisplayString,
                        ccBackpackTxITUNumber       DisplayString,
                        ccBackpackRxInsertionLoss   DisplayString,
                        ccBackpackTxInsertionLoss   DisplayString,
                        ccBackpackRxExpressLoss     DisplayString,
                        ccBackpackTxExpressLoss     DisplayString,
						ccSwitchByShelfSlot			DisplayString,
						ccPathID					PathIdName,
						ccCpeDisableThreshold		INTEGER,
						ccCpeReEnableThreshold		INTEGER,
						connTxNonMuxDmuxCardType	INTEGER,
						connTxNonMuxDmuxPort		INTEGER,
						connTxNonMuxDmuxShelf		INTEGER,
						connTxNonMuxDmuxSlot		INTEGER,
						connRxNonMuxDmuxCardType	INTEGER,
						connRxNonMuxDmuxPort		INTEGER,	
						connRxNonMuxDmuxShelf		INTEGER,
						connRxNonMuxDmuxSlot		INTEGER,
						ccUpsrMode					INTEGER,
						ccPairShelf					INTEGER,
						ccPairSlot					INTEGER,
						ccAdminState				INTEGER,
						ccRegenPairShelf			INTEGER,
						ccRegenPairSlot				INTEGER
                }

        ccCardLocation  OBJECT-TYPE
                SYNTAX  CardLocation
                ACCESS  read-only
                STATUS  mandatory
                DESCRIPTION
                        "Location of the card.  Valid values are: Local in
                         the same chassis, or remote to this chassis"
                ::= { ccEntry 1 }

        ccCardShelf     OBJECT-TYPE
                SYNTAX  CardShelf
                ACCESS  read-only
                STATUS  mandatory
                DESCRIPTION
                        "The shelf the card is in.  Valid values are: 1 to 10"
                ::= { ccEntry 2 }

        ccCardSlot      OBJECT-TYPE
                SYNTAX  SlotInput
                ACCESS  read-write
                STATUS  mandatory
                DESCRIPTION
                        "The slot within the shelf the module is in.  The range
                         of valid values range from 1 through 17 depending on
                         the chassis type and the shelf the module is in.
                         To delete this card, set this variable to 0."
                ::= { ccEntry 3 }

        ccMfgDate       OBJECT-TYPE
                SYNTAX  DateAndTime
                ACCESS  read-only
                STATUS  mandatory
                DESCRIPTION
                        "Date and Time of manufacturing of the CC card"
                ::= { ccEntry 4 }

        ccSerialNum     OBJECT-TYPE
                SYNTAX  SerialString
                ACCESS  read-only
                STATUS  mandatory
                DESCRIPTION
                        "Serial # of the CC card."
                ::= { ccEntry 5 }

        ccModelType     OBJECT-TYPE
                SYNTAX  INTEGER
		    { 	ocmu(2),
				ocmItu(3),
				oli(9),
				ocme(24),
				ocm10g(27)
		    }
                ACCESS  read-only
                STATUS  mandatory
                DESCRIPTION
                        "Model type of the chanel card."
                ::= { ccEntry 6 }

        ccName          OBJECT-TYPE
                SYNTAX  CardName
                ACCESS  read-write
                STATUS  mandatory
                DESCRIPTION
                        "User configurable name of the channel card"
                ::= { ccEntry 7 }

        ccFWVersionID     OBJECT-TYPE
                SYNTAX  VersionString
                ACCESS  read-only
                STATUS  mandatory
                DESCRIPTION
                        "The current version string of the CC FW code"
                ::= { ccEntry 8 }

        ccMfgBiasCurrent  OBJECT-TYPE
                SYNTAX  INTEGER
                ACCESS  read-only
                STATUS  mandatory
                DESCRIPTION
                        "Bias current for the optical laser.  This is the
                         preset manufacturing value"
                ::= { ccEntry 9 }

        ccMfgModulation  OBJECT-TYPE
                SYNTAX  INTEGER
                ACCESS  read-only
                STATUS  mandatory
                DESCRIPTION
                        "The frequency modulation for the optical laser.  This
                         value is the preset manufacturing value."
                ::= { ccEntry 10 }

        ccMfgApc        OBJECT-TYPE
                SYNTAX  INTEGER
                ACCESS  read-only
                STATUS  mandatory
                DESCRIPTION
                        "The APC value.  This value is the preset
                         manufacturing value"
                ::= { ccEntry 11 }

        ccMfgIwmModulation  OBJECT-TYPE
                SYNTAX  INTEGER
                ACCESS  read-only
                STATUS  mandatory
                DESCRIPTION
                        "The frequency modulation for the IWM channel.  This
                         value is the preset manufacturing value"
                ::= { ccEntry 12 }

        ccMfgRefClock   OBJECT-TYPE
                SYNTAX  INTEGER { en1660(1),
    				  en1944(2),
    				  en1953(3)
        			} 
                ACCESS  not-accessible
                STATUS  mandatory
                DESCRIPTION
                        "The value of the reference clock in decimal notation.
                         For a given value, like 1660-EN, the actual value is
                         16.60-EN.  In otherwords, assume a two digit decimal
                         point, plus any appropriate scaling factor.  This
                         value is the preset manufacturing value."
                ::= { ccEntry 13 }

        ccMfgClockDiv   OBJECT-TYPE
                SYNTAX  INTEGER { dout-1250(1), dout-622(2), dout-155(3) }
                ACCESS  not-accessible
                STATUS  mandatory
                DESCRIPTION
                        "The clock divisor.  Values are 1250, 622 or 155 in the
                         appropriate clock frequency scale."
                ::= { ccEntry 14 }

        ccBandwidth     OBJECT-TYPE
                SYNTAX  INTEGER {
		    			oc3(1),
					oc12(2),
					oc48(3),
					gbEthernet(4),
					fibreChannel(5),
					oc192(6),
					gbE10(9),
					fibreChannelX2(10)
				}
                ACCESS  read-write
                STATUS  mandatory
                DESCRIPTION
                        "The bandwidth of the channel card. "
                ::= { ccEntry 15 }

        ccSetState      OBJECT-TYPE
                SYNTAX  INTEGER { other(1),
				warmboot(2),
				enableLoopback(3),
				disableLoopback(4)
				}                
		ACCESS  read-write
                STATUS  mandatory
                DESCRIPTION
                        "Instruct the CC to do a warmboot or loopback.  A get
			 on this will always return an other." 
                ::= { ccEntry 16 }

 

	connMuxChassis     OBJECT-TYPE
                SYNTAX  INTEGER
                ACCESS  not-accessible
                STATUS  mandatory
                DESCRIPTION
                        "The connected mux chassis."
                ::= { ccEntry 17 }


	connMuxShelf     OBJECT-TYPE
                SYNTAX  ShelfInput
                ACCESS  read-only
                STATUS  mandatory
                DESCRIPTION
                        "The connected mux shelf."
                ::= { ccEntry 18 }

	connMuxSlot      OBJECT-TYPE
                SYNTAX  SlotInput
                ACCESS  read-only
                STATUS  mandatory
                DESCRIPTION
                        "The connected mux slot."
                ::= { ccEntry 19 }

        connMuxPort      OBJECT-TYPE
                SYNTAX  INTEGER
                ACCESS  read-only
                STATUS  mandatory
                DESCRIPTION
                        "The connected mux port. "
                ::= { ccEntry 20 }

       connDemuxChassis     OBJECT-TYPE
                SYNTAX  INTEGER
                ACCESS  not-accessible
                STATUS  mandatory
                DESCRIPTION
                        "The connected demux chassis."
                ::= { ccEntry 21 }

       connDemuxShelf     OBJECT-TYPE
                SYNTAX  ShelfInput
                ACCESS  read-only
                STATUS  mandatory
                DESCRIPTION
                        "The connected demux shelf."
                ::= { ccEntry 22 }

        connDemuxSlot      OBJECT-TYPE
                SYNTAX  SlotInput
                ACCESS  read-only
                STATUS  mandatory
                DESCRIPTION
                        "The connected demux slot."
                ::= { ccEntry 23 }

        connDemuxPort      OBJECT-TYPE
                SYNTAX  INTEGER
                ACCESS  read-only
                STATUS  mandatory
                DESCRIPTION
                        "The connected demux port. " 
                ::= { ccEntry 24 }

        ccModelNum     OBJECT-TYPE
                SYNTAX  DisplayString
                ACCESS  read-only
                STATUS  mandatory
                DESCRIPTION
                        "Model number of the CC card. Up to 15 characters"
                ::= { ccEntry 25 }

        ccLinkITUNum 	OBJECT-TYPE
                SYNTAX  DisplayString
                ACCESS  read-only
                STATUS  mandatory
                DESCRIPTION
                        "Link ITU number of the CC card. Up to 15 characters"
                ::= { ccEntry 26 }

        ccLinkWavelength	OBJECT-TYPE
                SYNTAX  DisplayString (SIZE (0..15))
                ACCESS  read-only
                STATUS  mandatory
                DESCRIPTION
                        "Link Wavelength of the CC card"
                ::= { ccEntry 27 }

        ccLaserType 	OBJECT-TYPE
                SYNTAX  INTEGER { uncooled(1),
				cooled(2)}                
			ACCESS  read-only 
                STATUS  mandatory
                DESCRIPTION
                        "Laser Type of the Channel Card." 
                ::= { ccEntry 28 }

        ccRecvDiode	OBJECT-TYPE
                SYNTAX  INTEGER { apd(1),
				pin(2)}                
		ACCESS  read-only 
                STATUS  mandatory
                DESCRIPTION
                        "Receive Diode of the Channel Card." 
                ::= { ccEntry 29 }

        ccLinkAutoDisable 	OBJECT-TYPE
                SYNTAX  INTEGER
		    { 	enable(1),
			disable(2)
		    }		     
		ACCESS  read-write
                STATUS  mandatory
                DESCRIPTION
                        "Flag to enable/disable the CPE link when the
			 threshold value crosses the lower hysteresis
			 limit.  The default value is disable." 
                ::= { ccEntry 30 }

        ccLinkName      OBJECT-TYPE
                SYNTAX  LinkName
                ACCESS  read-write
                STATUS  mandatory
                DESCRIPTION
                        "Link name for fiber between the local and the
			 remote cc card."
                ::= { ccEntry 31 }


        ccCsimModule      OBJECT-TYPE
                SYNTAX  INTEGER
		    { installed(1),
		      notinstalled(2),
		      preconfigured(3)
		    }		     
                ACCESS  read-only
                STATUS  mandatory
                DESCRIPTION
                        "Whether colorSIM module is physically present,
			 not installed or preconfigured."
                ::= { ccEntry 32 }

        ccHWName       OBJECT-TYPE
                SYNTAX  CardName
                ACCESS  read-only
                STATUS  mandatory
                DESCRIPTION
                        "Display Hardware name of the CC Card."
                ::= { ccEntry 33 }

        ccBackpackModule			OBJECT-TYPE
                SYNTAX  INTEGER
				{	installed(1), notInstalled(2) }
                ACCESS  read-only
                STATUS  mandatory
                DESCRIPTION
                        "Presence of Backpack module, installed or not Installed."
                ::= { ccEntry 34 }

        ccBackpackRxITUNumber 		OBJECT-TYPE
                SYNTAX  DisplayString
                ACCESS  read-only
                STATUS  mandatory
                DESCRIPTION
                        "Rx ITU number of backpack."
                ::= { ccEntry 35 }

        ccBackpackTxITUNumber 		OBJECT-TYPE
                SYNTAX  DisplayString
                ACCESS  read-only
                STATUS  mandatory
                DESCRIPTION
                        "Tx ITU number of backpack."
                ::= { ccEntry 36 }

        ccBackpackRxInsertionLoss 	OBJECT-TYPE
                SYNTAX  DisplayString
                ACCESS  read-only
                STATUS  mandatory
                DESCRIPTION
                        "Rx Insertion loss of backpack."
                ::= { ccEntry 37 }

        ccBackpackTxInsertionLoss 	OBJECT-TYPE
                SYNTAX  DisplayString
                ACCESS  read-only
                STATUS  mandatory
                DESCRIPTION
                        "Tx Insertion loss of backpack."
                ::= { ccEntry 38 }

        ccBackpackRxExpressLoss 	OBJECT-TYPE
                SYNTAX  DisplayString
                ACCESS  read-only
                STATUS  mandatory
                DESCRIPTION
                        "Rx Express loss of backpack."
                ::= { ccEntry 39 }

        ccBackpackTxExpressLoss 	OBJECT-TYPE
                SYNTAX  DisplayString
                ACCESS  read-only
                STATUS  mandatory
                DESCRIPTION
                        "Tx Express loss of backpack."
                ::= { ccEntry 40 }

		ccSwitchByShelfSlot		OBJECT-TYPE
                SYNTAX  DisplayString (SIZE (0..10))
                ACCESS  read-write
                STATUS  mandatory
                DESCRIPTION
                        "Initiate manual UPSR switching by shelf and slot."
                ::= { ccEntry 41 }

		ccPathID 		OBJECT-TYPE
                SYNTAX  PathIdName
                ACCESS  read-write
                STATUS  mandatory
                DESCRIPTION
                        "Upsr Path ID name that this card is associated with.  
						 Set input equal NULL will remove the card off the path 
						 and also remove the path if there is no card left 
						 associate with that path."
                ::= { ccEntry 42 }

		ccCpeDisableThreshold OBJECT-TYPE
                SYNTAX  INTEGER
                ACCESS  read-write
                STATUS  mandatory
                DESCRIPTION
				"CPE Disable Threshold (Link Rx Power) in dBm.  The limit 
				is from -32 to -8, but input should be an absolute value 
				if using mib browser."
                ::= { ccEntry 43 }

		ccCpeReEnableThreshold OBJECT-TYPE
                SYNTAX  INTEGER
                ACCESS  read-write
                STATUS  mandatory
                DESCRIPTION
				"CPE Re-enable threshold (Link Rx Power) in dBm.  The limit 
				is from -31 to -7, but input should be an absolute value 
				if using mib browser."
                ::= { ccEntry 44 }

       connTxNonMuxDmuxCardType      OBJECT-TYPE
                SYNTAX  INTEGER (0..30)
                ACCESS  read-only
                STATUS  mandatory
                DESCRIPTION
                        "Type of module connected to Tx port of OCM.  
						Valid values are ocmu(2),
						ocmItu(3), ocm10g(27), osam(20), fadm(6), oppm(7), fadmb(19)
						A zero will be used for no connections."
                ::= { ccEntry 45}

        connTxNonMuxDmuxPort    OBJECT-TYPE
                SYNTAX  INTEGER
                ACCESS  read-only
                STATUS  mandatory
                DESCRIPTION
                        "Conn port for CC's Tx port.Possible values based on 
				 card types that can connect to OCM are:
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx "
						 
                ::= { ccEntry 46}

        connTxNonMuxDmuxShelf    OBJECT-TYPE
                SYNTAX  ShelfInput
                ACCESS  read-only
                STATUS  mandatory
                DESCRIPTION
                        "The shelf the card conn to Tx port of OCM. Valid values are: 1 to 10."
                ::= { ccEntry 47 }

        connTxNonMuxDmuxSlot     OBJECT-TYPE
                SYNTAX  SlotInput
                ACCESS  read-only
                STATUS  mandatory
                DESCRIPTION
                        "The slot within the shelf the card conn to Tx port of OCM."
                ::= { ccEntry 48  }

       connRxNonMuxDmuxCardType      OBJECT-TYPE
                SYNTAX  INTEGER (0..30)
                ACCESS  read-only
                STATUS  mandatory
                DESCRIPTION
                        "Type of module connected to Rx port of OCM.  
						Valid values are ocmu(2),
						ocmItu(3), ocm10g(27), osam(20), fadm(6), oppm(7), fadmb(19)
						A zero will be used for no connections."
                ::= { ccEntry 49}

        connRxNonMuxDmuxPort    OBJECT-TYPE
                SYNTAX  INTEGER
                ACCESS  read-only
                STATUS  mandatory
                DESCRIPTION
                        "Conn port for CC's Rx port.Possible values based on 
				 card types that can connect to OCM are:
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx "
						 
                ::= { ccEntry 50}

        connRxNonMuxDmuxShelf    OBJECT-TYPE
                SYNTAX  ShelfInput
                ACCESS  read-only
                STATUS  mandatory
                DESCRIPTION
                        "The shelf the card conn to Rx port of OCM. Valid values are: 1 to 10."
                ::= { ccEntry 51 }

        connRxNonMuxDmuxSlot     OBJECT-TYPE
                SYNTAX  SlotInput
                ACCESS  read-only
                STATUS  mandatory
                DESCRIPTION
                        "The slot within the shelf the card conn to Rx port of OCM."
                ::= { ccEntry 52  }

		ccUpsrMode		OBJECT-TYPE
                SYNTAX  INTEGER
					{	primary(1), 
						backup(2),
						na(3)
					}
                ACCESS  read-write
                STATUS  mandatory
                DESCRIPTION
                        "UPSR mode for CC card:  primary or backup.
						 If not in upsr configuration, value is na"
                ::= { ccEntry 53}

		ccPairShelf		OBJECT-TYPE
                SYNTAX  INTEGER
                ACCESS  read-write
                STATUS  mandatory
                DESCRIPTION
                        "The shelf of other CC card in pair."
                ::= { ccEntry 54 }

		ccPairSlot		OBJECT-TYPE
                SYNTAX  INTEGER
                ACCESS  read-write
                STATUS  mandatory
                DESCRIPTION
                        "The slot of other CC card in pair.
				Input 0 to unpair OCMs and delete RSM connections if any."
                ::= { ccEntry 55 }


        ccAdminState     OBJECT-TYPE
                SYNTAX  INTEGER
						{ disable(1),
						  enable(2),
						  na(3)
						}
                ACCESS  read-write
                STATUS  mandatory
                DESCRIPTION
                        "Administrative control over that cc card. Default value is enable.
						 When disabled, no alarms/events gets
						 generated. For remote CC, the default value is disabled"
                ::= {  ccEntry 56}

		ccRegenPairShelf		OBJECT-TYPE
                SYNTAX  INTEGER
                ACCESS  read-write
                STATUS  mandatory
                DESCRIPTION
                        "The shelf of other CC card in OCM regeneration pair."
                ::= { ccEntry 57 }

		ccRegenPairSlot		OBJECT-TYPE
                SYNTAX  INTEGER
                ACCESS  read-write
                STATUS  mandatory
                DESCRIPTION
                        "The slot of other CC card in OCM regeneration pair.
				Input 0 to unpair OCMs involved"
                ::= { ccEntry 58 }


	
        -- The elements in the mux subgroup of the configuration group

        muxBootPromVer  OBJECT-TYPE
                SYNTAX  VersionString
                ACCESS  read-only
                STATUS  mandatory
                DESCRIPTION
                        "The current version string of the Mux Boot PROM code"
                ::= { mux 1 }

        muxROMSize      OBJECT-TYPE
                SYNTAX  INTEGER (0..1024)
                ACCESS  read-only
                STATUS  mandatory
                DESCRIPTION
                        "Total Size of the ROM in Kilobyes"
                ::= { mux 2 }

        muxNumSubDiv    OBJECT-TYPE
                SYNTAX  INTEGER (0..20)
                ACCESS  read-only
                STATUS  mandatory
                DESCRIPTION
                        "Number of the subdivisions of the ROM."
                ::= { mux 3 }

        muxSubDivTable  OBJECT-TYPE
                SYNTAX  SEQUENCE OF MuxSubDivEntry
                ACCESS  not-accessible
                STATUS  mandatory
                DESCRIPTION
                        "This table represents the number of sub divisions
                         and the size of each subdivision in ROM memory"
                ::= { mux 4 }

        muxSubDivEntry  OBJECT-TYPE
                SYNTAX  MuxSubDivEntry
                ACCESS  not-accessible
                STATUS  mandatory
                DESCRIPTION
                        "Specifies the index for each row in the table below"
                INDEX { muxSubDivIndex }
                ::= { muxSubDivTable 1 }

        MuxSubDivEntry  ::=
                SEQUENCE {
                        muxSubDivIndex  INTEGER,
                        muxSubDivDescr  DisplayString,
                        muxSubDivSize   INTEGER,
                        muxSubDivOffset OCTET STRING
                }

        muxSubDivIndex  OBJECT-TYPE
                SYNTAX  INTEGER (0..20)
                ACCESS  read-only
                STATUS  mandatory
                DESCRIPTION
                        "Integer ID of each sub division in the ROM.  The order
                         of numbering is from the top of the ROM to the bottom
                         of the ROM."
                ::= { muxSubDivEntry 1 }

        muxSubDivDescr  OBJECT-TYPE
                SYNTAX  DisplayString (SIZE (0..20))
                ACCESS  read-only
                STATUS  mandatory
                DESCRIPTION
                        "Display Name of each Sub Division in ROM"
                ::= { muxSubDivEntry 2 }

        muxSubDivSize   OBJECT-TYPE
                SYNTAX  INTEGER (0..1024)
                ACCESS  read-only
                STATUS  mandatory
                DESCRIPTION
                        "Size of each sub division in ROM in kilobytes"
                ::= { muxSubDivEntry 3 }

        muxSubDivOffset OBJECT-TYPE
                SYNTAX  OCTET STRING (SIZE (0..8))
                ACCESS  read-only
                STATUS  mandatory
                DESCRIPTION
                        "Starting address of each sub division in the ROM
                         in HEX notation."
                ::= { muxSubDivEntry 4 }

        muxNumber       OBJECT-TYPE
                SYNTAX  INTEGER
                ACCESS  read-only
                STATUS  mandatory
                DESCRIPTION
                        "Number of MUX rows in the following table.  This number
                         is automatically updated whenever a new row is added
                         to the table below."
                ::= { mux 5 }

        muxTable        OBJECT-TYPE
                SYNTAX  SEQUENCE OF MuxEntry
                ACCESS  not-accessible
                STATUS  mandatory
                DESCRIPTION
                        "This table represents the information for each
                         MUX card"
                ::= { mux 6 }

        muxEntry        OBJECT-TYPE
                SYNTAX  MuxEntry
                ACCESS  not-accessible
                STATUS  mandatory
                DESCRIPTION
                        "Specifies the index for each row in the table below"
                INDEX { muxCardLocation, muxCardShelf, muxCardSlot }
                ::= { muxTable 1 }

        MuxEntry        ::=
                SEQUENCE {
                        muxCardLocation			CardLocation,
                        muxCardShelf			CardShelf,
                        muxCardSlot				INTEGER,
                        muxModelNum				DisplayString,
                        muxMfgDate				DateAndTime,
                        muxSerialNum			SerialString,
                        muxModelType			INTEGER,
                        muxName					CardName,
                        muxFWVersionID			VersionString,
                        muxSetState				RebootType,
                        muxNumPorts				INTEGER,
                        muxUpgradeFlag			INTEGER,
                        muxHWName				CardName,
						muxPathID				PathIdName,
						muxAdminState			INTEGER
                }

        muxCardLocation OBJECT-TYPE
                SYNTAX  CardLocation
                ACCESS  read-only
                STATUS  mandatory
                DESCRIPTION
                        "Location of the module.  Valid values are: Local in
                         the same chassis, or remote to this chassis"
                ::= { muxEntry 1 }

        muxCardShelf    OBJECT-TYPE
                SYNTAX  CardShelf
                ACCESS  read-only
                STATUS  mandatory
                DESCRIPTION
                        "The shelf the card is in."
                ::= { muxEntry 2 }

        muxCardSlot     OBJECT-TYPE
                SYNTAX  SlotInput
                ACCESS  read-write
                STATUS  mandatory
                DESCRIPTION
                        "The slot within the shelf the module is in.  The range
                         of valid values range from 1 through 17 depending on
                         the chassis type and the shelf the module is in.
                         To delete this card, set this variable to 0."
                ::= { muxEntry 3 }

        muxModelNum      OBJECT-TYPE
                SYNTAX  DisplayString
                ACCESS  read-only
                STATUS  mandatory
                DESCRIPTION
                        "Model number for module."  
                ::= { muxEntry 4 }

        muxMfgDate      OBJECT-TYPE
                SYNTAX  DateAndTime
                ACCESS  read-only
                STATUS  mandatory
                DESCRIPTION
                        "Date and Time of manufacturing of the module"
                ::= { muxEntry 5 }

        muxSerialNum    OBJECT-TYPE
                SYNTAX  SerialString
                ACCESS  read-only
                STATUS  mandatory
                DESCRIPTION
                        "Serial # of the module."
                ::= { muxEntry 6 }

        muxModelType    OBJECT-TYPE
                SYNTAX  INTEGER { mux(4), demux(5), w4cd(10), w2cmd(13), w4cm(21) }
                ACCESS  read-only
                STATUS  mandatory
                DESCRIPTION
                        "Model type of the module"
                ::= { muxEntry 7 }

        muxName         OBJECT-TYPE
                SYNTAX  CardName
                ACCESS  read-write
                STATUS  mandatory
                DESCRIPTION
                        "User configurable name of the module"
                ::= { muxEntry 8 }

        muxFWVersionID    OBJECT-TYPE
                SYNTAX  VersionString
                ACCESS  read-only
                STATUS  mandatory
                DESCRIPTION
                        "The current version string of the FW code"
                ::= { muxEntry 9 }

	 muxSetState      OBJECT-TYPE
                SYNTAX  RebootType
                ACCESS  read-write
                STATUS  mandatory
                DESCRIPTION
                        "Instruct the mux to do a warmboot. A get on this will
			 always return an other." 
                ::= { muxEntry 10 }


        muxNumPorts    OBJECT-TYPE
                SYNTAX  INTEGER
                ACCESS  read-only
                STATUS  mandatory
                DESCRIPTION
                        "Total port numbers on each MUX card. Should be six"
                ::= { muxEntry 11 }

        muxUpgradeFlag    OBJECT-TYPE
                SYNTAX  INTEGER { upgradable(1), notUpgradable(2) }
                ACCESS  read-only
                STATUS  mandatory
                DESCRIPTION
                        "The MUX card's status is upgradable or not."
                ::= { muxEntry 12 }

        muxHWName       OBJECT-TYPE
                SYNTAX  CardName
                ACCESS  read-only
                STATUS  mandatory
                DESCRIPTION
                        "Display Hardware name of the mux/dmux Card."
                ::= { muxEntry 13 }

		muxPathID		OBJECT-TYPE
                SYNTAX  PathIdName
                ACCESS  read-write
                STATUS  mandatory
                DESCRIPTION
                        "Upsr Path ID name that this card is associated with.  
						 Set input equal NULL will remove the card off the path 
						 and also remove the path if there is no card left 
						 associate with that path."
                ::= { muxEntry 14 }

        muxAdminState     OBJECT-TYPE
                SYNTAX  INTEGER
						{ disable(1),
						  enable(2),
						  na(3)
						}
                ACCESS  read-write
                STATUS  mandatory
                DESCRIPTION
                        "Administrative control over that mux card. Default value is enable.
						 When disabled, no alarms/events gets
						 generated."
                ::= {  muxEntry 15}

        muxPortNumber	OBJECT-TYPE
                SYNTAX  INTEGER
                ACCESS  read-only
                STATUS  mandatory
                DESCRIPTION
                        "Number of MUX's port rows in the following table.  This 
                         number is automatically updated whenever a new row is 
                         added to the table below.Basically a product of
						 # of mux cards and # of ports on each card. Hence it 
						 would have a value of 6, 12, 18 etc.."
                ::= { mux 7 }

        muxPortTable        OBJECT-TYPE
                SYNTAX  SEQUENCE OF MuxPortEntry
                ACCESS  not-accessible
                STATUS  mandatory
                DESCRIPTION
                        "This table represents the information for each
                         MUX card's port."
                ::= { mux 8 }

        muxPortEntry	OBJECT-TYPE
                SYNTAX  MuxPortEntry
                ACCESS  not-accessible
                STATUS  mandatory
                DESCRIPTION
                        "Specifies the index for each row in the table below"
                INDEX { muxPortCardLocation, muxPortCardShelf, muxPortCardSlot,
			muxPortIndex }
                ::= { muxPortTable 1 }

        MuxPortEntry        ::=
                SEQUENCE {
                        muxPortCardLocation		CardLocation,
                        muxPortCardShelf		CardShelf,
                        muxPortCardSlot			SlotInput,
						muxPortIndex			INTEGER,
                        muxWavelength			INTEGER,
                        muxInsertLoss			DisplayString,
                        muxConnCardType			INTEGER,
                        muxConnLocation			CardLocation,
                        muxConnShelf			ShelfInput,
                        muxConnSlot				SlotInput,
                        muxConnPort				INTEGER,
						muxPortType				INTEGER,
						muxConnChassisID		DisplayString,
						muxConnSystemName		DisplayString,
						muxConnIpAddress		IpAddress 
                }

        muxPortCardLocation OBJECT-TYPE
                SYNTAX  CardLocation
                ACCESS  read-only 
                STATUS  mandatory
                DESCRIPTION
                        "Location of the MUX's port.  Valid values are: Local in
                         the same chassis, or remote to this chassis"
                ::= { muxPortEntry 1 }

        muxPortCardShelf    OBJECT-TYPE
                SYNTAX  CardShelf
                ACCESS  read-only 
                STATUS  mandatory
                DESCRIPTION
                        "The shelf the card is in.  Valid values are: 1 to 2."
                ::= { muxPortEntry 2 }

        muxPortCardSlot     OBJECT-TYPE
                SYNTAX  SlotInput
                ACCESS  read-only 
                STATUS  mandatory
                DESCRIPTION
                        "The slot within the shelf the card is in."
                ::= { muxPortEntry 3 }

        muxPortIndex	OBJECT-TYPE
                SYNTAX  INTEGER 
                ACCESS  read-only 
                STATUS  mandatory
                DESCRIPTION
                        "Port's index. Ports 1 through 4 can be use
						 for connection with OCM family or MCM only"
                ::= { muxPortEntry 4 }

        muxWavelength	OBJECT-TYPE
                SYNTAX  INTEGER 
                ACCESS  read-only
                STATUS  mandatory
                DESCRIPTION
                        "Port's wavelength: either ITU number or actual
			 wavelength in nm."
                ::= { muxPortEntry 5 }

        muxInsertLoss	OBJECT-TYPE
                SYNTAX  DisplayString 
                ACCESS  read-only
                STATUS  mandatory
                DESCRIPTION
                        "mux Port insertion Loss range."
                ::= { muxPortEntry 6 }

        muxConnCardType	OBJECT-TYPE
                SYNTAX  INTEGER (0..30)
                ACCESS  read-write
                STATUS  mandatory
                DESCRIPTION
                        "Type of connection.  Valid values are ocmu(2),
			 ocmItu(3), ocm10g(27), mux(4), demux(5), mcm(8), w4cd(10), w2cmd(13),
			 and w4cm(21).
			 A zero will be used for no connections."
                ::= { muxPortEntry 7 }


        muxConnLocation    OBJECT-TYPE
                SYNTAX  CardLocation
                ACCESS  read-write
                STATUS  mandatory
                DESCRIPTION
                        "The chassis's location of the card conn to."
                ::= { muxPortEntry 8 }

        muxConnShelf    OBJECT-TYPE
                SYNTAX  ShelfInput
                ACCESS  read-write
                STATUS  mandatory
                DESCRIPTION
                        "The shelf the card conn to. Valid values are: 1 to 2."
                ::= { muxPortEntry 9 }

        muxConnSlot     OBJECT-TYPE
                SYNTAX  SlotInput
                ACCESS  read-write
                STATUS  mandatory
                DESCRIPTION
                        "The slot within the shelf the card conn to."
                ::= { muxPortEntry 10 }

        muxConnPort		OBJECT-TYPE
                SYNTAX  INTEGER
                ACCESS  read-write
                STATUS  mandatory
                DESCRIPTION
                        "Conn port for MUX/DMUX's port.Possible values based on 
				 card types that can connect to FADM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx 
				 UPSM/OPPM: 1=Link A Tx, 2=Link A Rx, 3=Link B Tx,
				 4=Link B Rx, 5=Local Tx, 6=Local Rx."
                ::= { muxPortEntry 11 }

		muxPortType		OBJECT-TYPE 
                SYNTAX  INTEGER { mux(1), demux(2) }
                ACCESS  read-only 
                STATUS  mandatory
                DESCRIPTION
                        "Type of the MUX's port."
                ::= { muxPortEntry 12 }

		muxConnChassisID OBJECT-TYPE
                SYNTAX  DisplayString(SIZE(0..16))
                ACCESS  read-write
                STATUS  mandatory
                DESCRIPTION
                        "Chassis ID of the connected node.  User config. If local connection,
						a set on it would return an error; would be automatically be set to
						the chassis Id of the local node"
			::= { muxPortEntry 13}

        muxConnSystemName OBJECT-TYPE
                SYNTAX  DisplayString(SIZE(0..32))
                ACCESS  read-write
                STATUS  mandatory
                DESCRIPTION
                        "System Name of the connected node.  User config. If local connection,
						a set on it would return an error; would be automatically be set to
						the sysetem name of the local node."
			
				::= { muxPortEntry 14}

        muxConnIpAddress OBJECT-TYPE
                SYNTAX  IpAddress
                ACCESS  read-write
                STATUS  mandatory
                DESCRIPTION
                        "IpAddress of the connected node.  User config. If local
						 connection, a set on it would return an error; would be automatically
						 be set to the IP address of the node "
				::= { muxPortEntry 15}


        -- The elements in the ps subgroup of the configuration group

        psNumber        OBJECT-TYPE
                SYNTAX  INTEGER
                ACCESS  read-only
                STATUS  mandatory
                DESCRIPTION
                        "Number of PS (power supply) rows in the following table.
			 This number is automatically updated whenever a new row is added
                         to the table below."
                ::= { ps 1 }

        psTable         OBJECT-TYPE
                SYNTAX  SEQUENCE OF PsEntry
                ACCESS  not-accessible
                STATUS  mandatory
                DESCRIPTION
                        "This table represents the information for each
                         PS module."
                ::= { ps 2 }

        psEntry OBJECT-TYPE
                SYNTAX  PsEntry
                ACCESS  not-accessible
                STATUS  mandatory
                DESCRIPTION
                        "Specifies the index for each row in the table below"
                INDEX { psID }
                ::= { psTable 1 }

        PsEntry         ::=
                SEQUENCE {
                        psID			INTEGER,
						psMode          RedundancyMode,
                        psMfgDate       DateAndTime,
                        psSerialNum     SerialString,
                        psModelType     ModelString
                }

        psID    OBJECT-TYPE
                SYNTAX  INTEGER  (1..4)
                ACCESS  not-accessible
                STATUS  mandatory
                DESCRIPTION
                        "The module ID the ps module is in.  Valid values are: 1 to 4"
                ::= { psEntry 1 }


        psMode          OBJECT-TYPE
                SYNTAX  RedundancyMode
                ACCESS  not-accessible
                STATUS  mandatory
                DESCRIPTION
                        "Mode of the PS module.  Valid values are: active or
                         standby"
                ::= { psEntry 2 }

        psMfgDate       OBJECT-TYPE
                SYNTAX  DateAndTime
                ACCESS  not-accessible
                STATUS  mandatory
                DESCRIPTION
                        "Date and Time of manufacturing of the PS module."
                ::= { psEntry 3 }

        psSerialNum     OBJECT-TYPE
                SYNTAX  SerialString
                ACCESS  not-accessible
                STATUS  mandatory
                DESCRIPTION
                        "Serial # of the PS module. Not Supported Yet."
                ::= { psEntry 4 }

        psModelType     OBJECT-TYPE
                SYNTAX  ModelString
                ACCESS  not-accessible
                STATUS  mandatory
                DESCRIPTION
                        "Model type of the PS module. Up to 10 characters.
			 Not Supported Yet."
                ::= { psEntry 5 }


    	-- The elements in the download subgroup of the configuration group

		dlFtpTable 		OBJECT-TYPE
                SYNTAX  SEQUENCE OF DlFtpEntry
                ACCESS  not-accessible
                STATUS  mandatory
                DESCRIPTION
                        "This table represents the information for each
                         FTP server"
                ::= { download 1 }

    	dlFtpEntry      OBJECT-TYPE
                SYNTAX  DlFtpEntry
                ACCESS  not-accessible
                STATUS  mandatory
                DESCRIPTION
                        "Specifies the index for each row in the table below"
                INDEX { dlFtpIp }
                ::= { dlFtpTable 1 }

  		DlFtpEntry      ::=
                SEQUENCE {
                        dlFtpIp         IpAddress,
                        dlFtpLogonID    LogonID,
                        dlFtpPasswd     DisplayString,
						dlFtpMode	    FtpMode
                }

   		dlFtpIp         OBJECT-TYPE
                SYNTAX  IpAddress
                ACCESS  read-write
                STATUS  mandatory
                DESCRIPTION
                        "The IP address of the FTP server."
                ::= { dlFtpEntry 1 }

   		dlFtpLogonID    OBJECT-TYPE
                SYNTAX  LogonID
                ACCESS  read-write
                STATUS  mandatory
                DESCRIPTION
                        "The FTP user ID for this FTP server.  Up to 15 chars."
                ::= { dlFtpEntry 2 }

  		dlFtpPasswd     OBJECT-TYPE
                SYNTAX  DisplayString (SIZE(0..20))
                ACCESS  read-write
                STATUS  mandatory
                DESCRIPTION
                        "Password for the above FTP Logon ID.  This password
                         is NOT hashed.  Proper security access is required
                         to set and view this element.  Most FTP connections,
                         however, are using anonymous logon ID with no
                         special password requirements."
                ::= { dlFtpEntry 3 }

		dlFtpMode		OBJECT-TYPE
                SYNTAX  FtpMode
                ACCESS  read-write
                STATUS  mandatory
                DESCRIPTION
                        "FTP server modes.  The choices are: active or passive,
				active may be necessary for users behind a firewall."
                ::= { dlFtpEntry 4 }


  		dlPreQualTable 	OBJECT-TYPE
                SYNTAX  SEQUENCE OF DlPreQualEntry
                ACCESS  not-accessible
                STATUS  mandatory
                DESCRIPTION
                        "This table represents the information for each
                         PreQual table."
                ::= { download 2 }

		dlPreQualEntry	OBJECT-TYPE
                SYNTAX  DlPreQualEntry
                ACCESS  not-accessible
                STATUS  mandatory
                DESCRIPTION
                        "Specifies the index for each row in the table below"
                INDEX { dlPreQualTypeVersion }
                ::= { dlPreQualTable 1 }

 		DlPreQualEntry      ::=
                SEQUENCE {
                        dlPreQualTypeVersion	DisplayString,
                        dlPreQualResult			INTEGER
                }

        
		dlPreQualTypeVersion	OBJECT-TYPE
                SYNTAX  DisplayString (SIZE(0..255))
                ACCESS  read-write
                STATUS  mandatory
                DESCRIPTION
                        "The Image type and version to be prequalified 
				before downloading.  The string format is : 
				type,version.  The prequal action will be 
				taken after setting version."
						
                ::= { dlPreQualEntry 1 }
        
		dlPreQualResult	OBJECT-TYPE
                SYNTAX  INTEGER	
				{ 
						compatible(1), 
						incompatible(2),
						unknown-version(3)
				}
                ACCESS  read-only
                STATUS  mandatory
                DESCRIPTION
                        "The result after comparing type and version of the 
				selected download image with the compatibility
				matrix.  The result is either compatible, incompatible 
				or unknown version.  (Not available at this time).  
				The default is compatible."  
                ::= { dlPreQualEntry 2 }

		dlDownloadTable	OBJECT-TYPE
                SYNTAX  SEQUENCE OF DlDownloadEntry
                ACCESS  not-accessible
                STATUS  mandatory
                DESCRIPTION
                        "This table represents the information for 
                         download and activation."
                ::= { download 3 }

 		dlDownloadEntry	OBJECT-TYPE
                SYNTAX  DlDownloadEntry
                ACCESS  not-accessible
                STATUS  mandatory
                DESCRIPTION
                        "Specifies the index for each row in the table below"
                INDEX { dlType, dlLocation, dlShelf, dlSlot }
                ::= { dlDownloadTable 1 }

		DlDownloadEntry      ::=
                SEQUENCE 
				{
                        dlType			DownloadType,
                        dlLocation		DownloadLocation,
                        dlShelf			DownloadShelf,
                        dlSlot			DownloadSlot,
						dlFilename		DisplayString,
						dlActivate		INTEGER
                }

  		dlType  		OBJECT-TYPE
                SYNTAX  DownloadType
                ACCESS  read-write
                STATUS  mandatory
                DESCRIPTION
                        "The Image type to be downloaded or to be activated."
                ::= { dlDownloadEntry 1 }

 		dlLocation     	OBJECT-TYPE
                SYNTAX  DownloadLocation
                ACCESS  read-write
                STATUS  mandatory
                DESCRIPTION
                        "The location to be downloaded or to be activated.  
				The choices are:  local, remote or both.  (Only local and 
				remote are supported at this time, LuxnOS has only local 
				choice and is not supported yet."
                ::= { dlDownloadEntry 2 }

		dlShelf			OBJECT-TYPE
                SYNTAX  DownloadShelf
                ACCESS  read-write
                STATUS  mandatory
                DESCRIPTION
                        "The destination shelf."
                ::= { dlDownloadEntry 3 }

		dlSlot  		OBJECT-TYPE
                SYNTAX  DownloadSlot
                ACCESS  read-write
                STATUS  mandatory
                DESCRIPTION
                        "The slot within the selected shelf."
                ::= { dlDownloadEntry 4 }

		dlFilename  	OBJECT-TYPE
                SYNTAX  DisplayString (SIZE(0..255))
                ACCESS  read-write 
                STATUS  mandatory
                DESCRIPTION
                        "The filename to be downloaded including the 
				pathname, up to 255 characters.  The download 
				action will be taken after setting the filename."
                ::= { dlDownloadEntry 5 }
		
 		dlActivate		OBJECT-TYPE
                SYNTAX  INTEGER { no(1), yes(2)}
                ACCESS  read-write
                STATUS  mandatory
                DESCRIPTION
                        "Answer yes to activate the downloaded type at the 
				selected location."
                ::= { dlDownloadEntry 6 }

		dlOSTable      	OBJECT-TYPE
                SYNTAX  SEQUENCE OF DlOSEntry
                ACCESS  not-accessible
                STATUS  mandatory
                DESCRIPTION
                        "This table represents the information for 
                         LuxnOS table."
                ::= { download 4 }

  		dlOSEntry      	OBJECT-TYPE
                SYNTAX  DlOSEntry
                ACCESS  not-accessible
                STATUS  mandatory
                DESCRIPTION
                        "Specifies the index for each row in the table below"
                INDEX { dlOSIndex }
                ::= { dlOSTable 1 }

  		DlOSEntry      ::=
                SEQUENCE {
                        dlOSIndex		INTEGER,
                        dlOSVersion		VersionString,
                        dlOSState		OSState,
                        dlOSRelDate		ReleaseDate
                }

		dlOSIndex  		OBJECT-TYPE
                SYNTAX  INTEGER (1..2)
                ACCESS  not-accessible
                STATUS  mandatory
                DESCRIPTION
                        "The Integer ID for each LuxnOS."
                ::= { dlOSEntry 1 }

		dlOSVersion  	OBJECT-TYPE
                SYNTAX  VersionString
                ACCESS  not-accessible
                STATUS  mandatory
                DESCRIPTION
                        "Display the LuxnOS version."
                ::= { dlOSEntry 2 }

		dlOSState  		OBJECT-TYPE
                SYNTAX  OSState
                ACCESS  not-accessible
                STATUS  mandatory
                DESCRIPTION
                        "Display the LuxnOS state: operating(1) is the current 
				operating LuxnOS, backup(2)is the backup LuxnOS."
                ::= { dlOSEntry 3 }

		dlOSRelDate  	OBJECT-TYPE
                SYNTAX  ReleaseDate
                ACCESS  not-accessible
                STATUS  mandatory
                DESCRIPTION
                        "Display the release date of the LuxnOS."
                ::= { dlOSEntry 4 }

		dlUpdateOS		OBJECT-TYPE
                SYNTAX  UpdateOSMode
                ACCESS  not-accessible
                STATUS  mandatory
                DESCRIPTION
                        "Display and select Update LuxnOS Mode: toggle(1) to
				toggle between operating and backup LuxnOS, revert(2)
				to copy LuxnOS from the backup to the operating area.
				The action will be taken after setting UpdateOS ."
                ::= { download 5 }
        

        -- The elements in the OADM subgroup of the configuration group

        fadmBootPromVer  OBJECT-TYPE
                SYNTAX  VersionString
                ACCESS  not-accessible
                STATUS  mandatory
                DESCRIPTION
                        "The current version string of the OADM Boot PROM code"
                ::= { fadm 1 }

        fadmROMSize      OBJECT-TYPE
                SYNTAX  INTEGER (1..1024)
                ACCESS  not-accessible
                STATUS  mandatory
                DESCRIPTION
                        "Total Size of the ROM in Kilobyes"
                ::= { fadm 2 }

        fadmNumSubDiv    OBJECT-TYPE
                SYNTAX  INTEGER (1..20)
                ACCESS  not-accessible
                STATUS  mandatory
                DESCRIPTION
                        "Number of the subdivisions of the ROM."
                ::= { fadm 3 }

        fadmSubDivTable  OBJECT-TYPE
                SYNTAX  SEQUENCE OF FadmSubDivEntry
                ACCESS  not-accessible
                STATUS  mandatory
                DESCRIPTION
                        "This table represents the number of sub divisions
                         and the size of each subdivision in ROM memory"
                ::= { fadm 4 }

        fadmSubDivEntry  OBJECT-TYPE
                SYNTAX  FadmSubDivEntry
                ACCESS  not-accessible
                STATUS  mandatory
                DESCRIPTION
                        "Specifies the index for each row in the table below"
                INDEX { fadmSubDivIndex }
                ::= { fadmSubDivTable 1 }

        FadmSubDivEntry  ::=
                SEQUENCE {
                        fadmSubDivIndex  INTEGER,
                        fadmSubDivDescr  DisplayString,
                        fadmSubDivSize   INTEGER,
                        fadmSubDivOffset OCTET STRING
                }

        fadmSubDivIndex  OBJECT-TYPE
                SYNTAX  INTEGER (1..20)
                ACCESS  not-accessible
                STATUS  mandatory
                DESCRIPTION
                        "Integer ID of each sub division in the ROM.  The order
                         of numbering is from the top of the ROM to the bottom
                         of the ROM."
                ::= { fadmSubDivEntry 1 }

        fadmSubDivDescr  OBJECT-TYPE
                SYNTAX  DisplayString (SIZE (0..20))
                ACCESS  not-accessible
                STATUS  mandatory
                DESCRIPTION
                        "Display Name of each Sub Division in ROM"
                ::= { fadmSubDivEntry 2 }

        fadmSubDivSize   OBJECT-TYPE
                SYNTAX  INTEGER (1..1024)
                ACCESS  not-accessible
                STATUS  mandatory
                DESCRIPTION
                        "Size of each sub division in ROM in kilobytes"
                ::= { fadmSubDivEntry 3 }

        fadmSubDivOffset OBJECT-TYPE
                SYNTAX  OCTET STRING (SIZE (0..8))
                ACCESS  not-accessible
                STATUS  mandatory
                DESCRIPTION
                        "Starting address of each sub division in the ROM
                         in HEX notation."
                ::= { fadmSubDivEntry 4 }

        fadmNumber		OBJECT-TYPE
                SYNTAX  INTEGER
                ACCESS  read-only
                STATUS  mandatory
                DESCRIPTION
                        "Number of FADM rows in the following table.  This number
                         is automatically updated whenever a new row is added
                         to the table below."
                ::= { fadm 5 }

        fadmTable        OBJECT-TYPE
                SYNTAX  SEQUENCE OF FadmEntry
                ACCESS  not-accessible
                STATUS  mandatory
                DESCRIPTION
                        "This table represents the information for each
                         OADM module"
                ::= { fadm 6 }

        fadmEntry        OBJECT-TYPE
                SYNTAX  FadmEntry
                ACCESS  not-accessible
                STATUS  mandatory
                DESCRIPTION
                        "Specifies the index for each row in the table below"
                INDEX { fadmCardLocation, fadmCardShelf, fadmCardSlot }
                ::= { fadmTable 1 }

        FadmEntry        ::=
                SEQUENCE {
                        fadmCardLocation		CardLocation,
                        fadmCardShelf			CardShelf,
                        fadmCardSlot			INTEGER,
                        fadmMfgDate				DateAndTime,
                        fadmSerialNum			SerialString,
                        fadmModelType			INTEGER,
                        fadmName				CardName,
                        fadmFWVersionID			VersionString,
                        fadmSetState			RebootType,
                        fadmNumPorts			INTEGER,
                        fadmUpgradeFlag			INTEGER,
                        fadmModelNum			DisplayString,
                        fadmITUNumber1			INTEGER,
                        fadmITUNumber2			INTEGER,
                        fadmInsertionLoss1		DisplayString,
                        fadmInsertionLoss2		DisplayString,
                        fadmExpressLoss			DisplayString,
                        fadmHWName				CardName,
						fadmPathID				PathIdName,
						fadmAdminState	        INTEGER											 
                }

        fadmCardLocation OBJECT-TYPE
                SYNTAX  CardLocation
                ACCESS  read-only
                STATUS  mandatory
                DESCRIPTION
                        "Location of the FADM Module."
                ::= { fadmEntry 1 }

        fadmCardShelf    OBJECT-TYPE
                SYNTAX  CardShelf
                ACCESS  read-only
                STATUS  mandatory
                DESCRIPTION
                        "The shelf of the Module is in.  Valid values
			 are: 1, 2 or 3 depending on the chassis type."
                ::= { fadmEntry 2 }

        fadmCardSlot     OBJECT-TYPE
                SYNTAX  SlotInput
                ACCESS  read-write
                STATUS  mandatory
                DESCRIPTION
                        "The slot within the shelf the module is in.  The range
			 of valid values range from 1 through 21 depending on
			 the chassis type and the shelf the module is in.
                         To delete this card, set this variable to 0."
                ::= { fadmEntry 3 }


        fadmMfgDate      OBJECT-TYPE
                SYNTAX  DateAndTime
                ACCESS  read-only
                STATUS  mandatory
                DESCRIPTION
                        "Date and Time of manufacturing of the FADM card"
                ::= { fadmEntry 4 }

        fadmSerialNum    OBJECT-TYPE
                SYNTAX  SerialString
                ACCESS  read-only
                STATUS  mandatory
                DESCRIPTION
                        "Serial # of the FADM card."
                ::= { fadmEntry 5 }

        fadmModelType    OBJECT-TYPE
                SYNTAX  INTEGER { 
					fadm(6),
					fadm-b(19)
				}
                ACCESS  read-only
                STATUS  mandatory
                DESCRIPTION
                        "Model type of the FADM"
                ::= { fadmEntry 6 }

        fadmName		OBJECT-TYPE
                SYNTAX  CardName
                ACCESS  read-write
                STATUS  mandatory
                DESCRIPTION
                        "Display (Network) name of the FADM Card"
                ::= { fadmEntry 7 }

        fadmFWVersionID    OBJECT-TYPE
                SYNTAX  VersionString
                ACCESS  read-only
                STATUS  mandatory
                DESCRIPTION
                        "The current version string of the FADM FW code"
                ::= { fadmEntry 8 }

        fadmSetState     OBJECT-TYPE
                SYNTAX  RebootType
                ACCESS  read-write
                STATUS  mandatory
                DESCRIPTION
                        "Instruct the fadm to do a warmboot. A get on this will
			 always return an other." 
                ::= { fadmEntry 9 }


        fadmNumPorts    OBJECT-TYPE
                SYNTAX  INTEGER
                ACCESS  read-only
                STATUS  mandatory
                DESCRIPTION
                        "Total port numbers of FADM module."
                ::= { fadmEntry 10 }

        fadmUpgradeFlag    OBJECT-TYPE
                SYNTAX  INTEGER { upgradeable(1), notUpgradeable(2) }
                ACCESS  read-only
                STATUS  mandatory
                DESCRIPTION
                        "The FADM module's status is upgradeable or not."
                ::= { fadmEntry 11 }

        fadmModelNum    OBJECT-TYPE
                SYNTAX  DisplayString
                ACCESS  read-only
                STATUS  mandatory
                DESCRIPTION
                        "Model # of the FADM card. Up to 15 characters"
                ::= { fadmEntry 12 }

        fadmITUNumber1 OBJECT-TYPE
                SYNTAX  INTEGER 
                ACCESS  read-only
                STATUS  mandatory
                DESCRIPTION
                        "Port 1's ITU wavelength."
                ::= { fadmEntry 13 }

        fadmITUNumber2 OBJECT-TYPE
                SYNTAX  INTEGER 
                ACCESS  read-only
                STATUS  mandatory
                DESCRIPTION
                        "Port 2's ITU wavelength.  Port 2 is only
			 applicable to fadmb.  For fadm, it will
			 always contain the value as Port 1."
                ::= { fadmEntry 14 }

        fadmInsertionLoss1 OBJECT-TYPE
                SYNTAX  DisplayString 
                ACCESS  read-only
                STATUS  mandatory
                DESCRIPTION
                        "Port 1's insertion loss in dB."
                ::= { fadmEntry 15 }

        fadmInsertionLoss2 OBJECT-TYPE
                SYNTAX  DisplayString 
                ACCESS  read-only
                STATUS  mandatory
                DESCRIPTION
                        "Port 2's insertion loss in dB.  Port 2 is only
			 applicable to fadmb.  For fadm, the value shown
			 isn't applicable."
                ::= { fadmEntry 16 }

        fadmExpressLoss OBJECT-TYPE
                SYNTAX  DisplayString 
                ACCESS  read-only
                STATUS  mandatory
                DESCRIPTION
                        "Internal express port's insertion loss in dB."
                ::= { fadmEntry 17 }

        fadmHWName       OBJECT-TYPE
                SYNTAX  CardName
                ACCESS  read-only
                STATUS  mandatory
                DESCRIPTION
                        "Display Hardware name of the FADM Card."
                ::= { fadmEntry 18 }

		fadmPathID		OBJECT-TYPE
                SYNTAX  PathIdName
                ACCESS  read-write
                STATUS  mandatory
                DESCRIPTION
                        "Upsr Path ID name that this card is associated with.  
						 Set input equal NULL will remove the card off the path 
						 and also remove the path if there is no card left 
						 associate with that path."
                ::= { fadmEntry 19 }

       fadmAdminState     OBJECT-TYPE
                SYNTAX  INTEGER
						{ disable(1),
						  enable(2),
						  na(3)
						}
                ACCESS  read-write
                STATUS  mandatory
                DESCRIPTION
                        "Administrative control over that fadm card. Default value is enable.
						 When disabled, no alarms/events gets
						 generated."
                ::= {  fadmEntry 20}


		fadmPortTable	OBJECT-TYPE
                SYNTAX  SEQUENCE OF FadmPortEntry
                ACCESS  not-accessible
                STATUS  mandatory
                DESCRIPTION
                        "This table represents the physical connection for each
                         FADM card's port."
                ::= { fadm 7 }

        fadmPortEntry	OBJECT-TYPE
                SYNTAX  FadmPortEntry
                ACCESS  not-accessible
                STATUS  mandatory
                DESCRIPTION
                        "Specifies the index for each row in the table below"
                INDEX { fadmPortCardShelf, fadmPortCardSlot, fadmPortType }
                ::= { fadmPortTable 1 }

        FadmPortEntry        ::=
                SEQUENCE 
				{
						fadmPortCardShelf		CardShelf,
						fadmPortCardSlot		SlotInput,
						fadmPortType			INTEGER,
						fadmConnLocation		CardLocation,
						fadmConnIpAddress		IpAddress,
						fadmConnChassisID		NodeName,
						fadmConnSystemName		NodeName,						
						fadmConnCardType		INTEGER,
						fadmConnPort			INTEGER,
						fadmConnShelf			ShelfInput,
                        fadmConnSlot			SlotInput
				}

        fadmPortCardShelf    OBJECT-TYPE
                SYNTAX  CardShelf
                ACCESS  read-only 
                STATUS  mandatory
                DESCRIPTION
                        "The shelf the card is in.  Valid values are: 1 to 2."
                ::= { fadmPortEntry 1 }

        fadmPortCardSlot     OBJECT-TYPE
                SYNTAX  SlotInput
                ACCESS  read-only 
                STATUS  mandatory
                DESCRIPTION
                        "The slot within the shelf the card is in."
                ::= { fadmPortEntry 2 }

		fadmPortType		OBJECT-TYPE 
                SYNTAX  INTEGER { 
								  connATx-AToD(1), 
								  connARx-EXP(2), 
								  localTx-Local(3),
								  localRx-Rx(4), 
								  connBTx(5), 
								  connBRx(6) 
								}
                ACCESS  read-only
                STATUS  mandatory
                DESCRIPTION
                        "Type of the FADM/FADMB's port.  The order is CLI compatible.
					     For FADM model type, the ports are listed on the left column
						 and for FADMB model type, the ports are listed on the right
						 column"
                ::= { fadmPortEntry 3 }

        fadmConnLocation    OBJECT-TYPE
                SYNTAX  CardLocation
                ACCESS  read-write
                STATUS  mandatory
                DESCRIPTION
                        "The chassis's location of the card conn to."
                ::= { fadmPortEntry 4 }


        fadmConnIpAddress OBJECT-TYPE
                SYNTAX  IpAddress
                ACCESS  read-write
                STATUS  mandatory
                DESCRIPTION
                        "IpAddress of the connected node.  User config. If local
						 connection, a set on it would return an error; would be automatically
						 be set to the IP address of the node "
                ::= { fadmPortEntry 5}

		fadmConnChassisID OBJECT-TYPE
                SYNTAX  DisplayString(SIZE(0..16))
                ACCESS  read-write
                STATUS  mandatory
                DESCRIPTION
                        "Chassis ID of the connected node.  User config. If local connection,
						a set on it would return an error; would be automatically be set to
						the chassis Id of the local node"
                ::= { fadmPortEntry 6}

        fadmConnSystemName OBJECT-TYPE
                SYNTAX  DisplayString(SIZE(0..32))
                ACCESS  read-write
                STATUS  mandatory
                DESCRIPTION
                        "System Name of the connected node.  User config. If local connection,
						a set on it would return an error; would be automatically be set to
						the sysetem name of the local node."
                ::= { fadmPortEntry 7}


        fadmConnCardType      OBJECT-TYPE
                SYNTAX  INTEGER (0..30)
                ACCESS  read-write
                STATUS  mandatory
                DESCRIPTION
                        "Type of connection.  Valid values are ocmu(2),
			 ocmItu(3), ocm10g(27), mux(4), demux(5), mcm(8), w4cd(10), w2cmd(13), w4cm(21),
			 osam(20), fadm(6), oppm(7), fadmb(19), upsm(23), ocme(24), etc...
			 A zero will be used for no connections."
                ::= { fadmPortEntry 8}

        fadmConnPort    OBJECT-TYPE
                SYNTAX  INTEGER
                ACCESS  read-write
                STATUS  mandatory
                DESCRIPTION
                        "Conn port for FADM's port.Possible values based on 
				 card types that can connect to FADM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx 
				 UPSM/OPPM: 1=Link A Tx, 2=Link A Rx, 3=Link B Tx,
				 4=Link B Rx, 5=Local Tx, 6=Local Rx."						 
                ::= { fadmPortEntry 9 }

        fadmConnShelf   OBJECT-TYPE
                SYNTAX  ShelfInput
                ACCESS  read-write
                STATUS  mandatory
                DESCRIPTION
                        "The shelf the card conn to. Valid values are: 1 to 2."
                ::= { fadmPortEntry 10 }

        fadmConnSlot     OBJECT-TYPE
                SYNTAX  SlotInput
                ACCESS  read-write
                STATUS  mandatory
                DESCRIPTION
                        "The slot within the shelf the card conn to."
                ::= { fadmPortEntry 11 }

	
        -- The elements in the oppm subgroup of the configuration group

        oppmBootPromVer  OBJECT-TYPE
                SYNTAX  VersionString
                ACCESS  not-accessible
                STATUS  mandatory
                DESCRIPTION
                        "The current version string of the oppm Boot PROM code"
                ::= { oppm 1 }

        oppmROMSize      OBJECT-TYPE
                SYNTAX  INTEGER (0..1024)
                ACCESS  not-accessible
                STATUS  mandatory
                DESCRIPTION
                        "Total Size of the ROM in Kilobyes"
                ::= { oppm 2 }

        oppmNumSubDiv    OBJECT-TYPE
                SYNTAX  INTEGER (0..20)
                ACCESS  not-accessible
                STATUS  mandatory
                DESCRIPTION
                        "Number of the subdivisions of the ROM."
                ::= { oppm 3 }

        oppmSubDivTable  OBJECT-TYPE
                SYNTAX  SEQUENCE OF OppmSubDivEntry
                ACCESS  not-accessible
                STATUS  mandatory
                DESCRIPTION
                        "This table represents the number of sub divisions
                         and the size of each subdivision in ROM memory"
                ::= { oppm 4 }

        oppmSubDivEntry  OBJECT-TYPE
                SYNTAX  OppmSubDivEntry
                ACCESS  not-accessible
                STATUS  mandatory
                DESCRIPTION
                        "Specifies the index for each row in the table below"
                INDEX { oppmSubDivIndex }
                ::= { oppmSubDivTable 1 }

        OppmSubDivEntry  ::=
                SEQUENCE {
                        oppmSubDivIndex  INTEGER,
                        oppmSubDivDescr  DisplayString,
                        oppmSubDivSize   INTEGER,
                        oppmSubDivOffset OCTET STRING
                }

        oppmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { oppmSubDivEntry 1 }

        oppmSubDivDescr  OBJECT-TYPE
                SYNTAX  DisplayString (SIZE (0..20))
                ACCESS  not-accessible
                STATUS  mandatory
                DESCRIPTION
                        "Display Name of each Sub Division in ROM"
                ::= { oppmSubDivEntry 2 }

        oppmSubDivSize   OBJECT-TYPE
                SYNTAX  INTEGER (0..1024)
                ACCESS  not-accessible
                STATUS  mandatory
                DESCRIPTION
                        "Size of each sub division in ROM in kilobytes"
                ::= { oppmSubDivEntry 3 }

        oppmSubDivOffset OBJECT-TYPE
                SYNTAX  OCTET STRING (SIZE (0..8))
                ACCESS  not-accessible
                STATUS  mandatory
                DESCRIPTION
                        "Starting address of each sub division in the ROM
                         in HEX notation."
                ::= { oppmSubDivEntry 4 }

        oppmNumber       OBJECT-TYPE
                SYNTAX  INTEGER
                ACCESS  read-only
                STATUS  mandatory
                DESCRIPTION
                        "Number of OPPM rows in the following table.  This 
                         number is automatically updated whenever a new row is 
                         added to the table below."
                ::= { oppm 5 }

        oppmTable        OBJECT-TYPE
                SYNTAX  SEQUENCE OF OppmEntry
                ACCESS  not-accessible
                STATUS  mandatory
                DESCRIPTION
                        "This table represents the information for each
                         OPPM card"
                ::= { oppm 6 }

        oppmEntry        OBJECT-TYPE
                SYNTAX  OppmEntry
                ACCESS  not-accessible
                STATUS  mandatory
                DESCRIPTION
                        "Specifies the index for each row in the table below"
                INDEX { oppmCardLocation, oppmCardShelf, oppmCardSlot }
                ::= { oppmTable 1 }

        OppmEntry        ::=
                SEQUENCE {
                        oppmCardLocation        CardLocation,
                        oppmCardShelf           CardShelf,
                        oppmCardSlot            INTEGER,
                        oppmModelNum            DisplayString,
                        oppmMfgDate             DateAndTime,
                        oppmSerialNum           SerialString,
                        oppmModelType           INTEGER,
                        oppmName                CardName,
                        oppmFWVersionID         VersionString,
                        oppmSetState            RebootType,
                        oppmTxInsertLoss        DisplayString,
                        oppmRxInsertLoss        DisplayString,
                        oppmUpgradeFlag         INTEGER,
                        oppmSwitch              INTEGER,
                        oppmMarginForSwitch     INTEGER,
                        oppmHighAlarmMargin     INTEGER,
                        oppmConfigCommit        INTEGER,
                        oppmHWName              CardName,
						oppmLinkAPathID			PathIdName,
						oppmLinkBPathID			PathIdName,
						oppmAdminState			INTEGER
                }

        oppmCardLocation OBJECT-TYPE
                SYNTAX  CardLocation
                ACCESS  read-only
                STATUS  mandatory
                DESCRIPTION
                        "Location of the OPPM card.  Valid values are: Local in
                         the same chassis, or remote to this chassis"
                ::= { oppmEntry 1 }

        oppmCardShelf    OBJECT-TYPE
                SYNTAX  CardShelf
                ACCESS  read-only
                STATUS  mandatory
                DESCRIPTION
                        "The shelf the card is in.  Valid values are: 1 to 3"
                ::= { oppmEntry 2 }

        oppmCardSlot     OBJECT-TYPE
                SYNTAX  SlotInput
                ACCESS  read-write
                STATUS  mandatory
                DESCRIPTION
                        "The slot within the shelf the module is in.  The range
			 of valid values range from 1 through 21 depending on
			 the chassis type and the shelf the module is in.
                         To delete this card, set this variable to 0."
                ::= { oppmEntry 3 }


        oppmModelNum      OBJECT-TYPE
                SYNTAX  DisplayString
                ACCESS  read-only
                STATUS  mandatory
                DESCRIPTION
                        "Oppm's model number."
                ::= { oppmEntry 4 }



        oppmMfgDate      OBJECT-TYPE
                SYNTAX  DateAndTime
                ACCESS  read-only
                STATUS  mandatory
                DESCRIPTION
                        "Date and Time of manufacturing of the OPPM card"
                ::= { oppmEntry 5 }

        oppmSerialNum    OBJECT-TYPE
                SYNTAX  SerialString
                ACCESS  read-only
                STATUS  mandatory
                DESCRIPTION
                        "Serial # of the OPPM card."
                ::= { oppmEntry 6 }

        oppmModelType    OBJECT-TYPE
                SYNTAX  INTEGER { oppm(7) }
                ACCESS  read-only
                STATUS  mandatory
                DESCRIPTION
                        "Model type of the OPPM"
                ::= { oppmEntry 7 }

        oppmName         OBJECT-TYPE
                SYNTAX  CardName
                ACCESS  read-write
                STATUS  mandatory
                DESCRIPTION
                        "Display (Network) name of the OPPM Card"
                ::= { oppmEntry 8 }

        oppmFWVersionID    OBJECT-TYPE
                SYNTAX  VersionString
                ACCESS  read-only
                STATUS  mandatory
                DESCRIPTION
                        "The current version string of the OPPM FW code"
                ::= { oppmEntry 9 }


        oppmSetState      OBJECT-TYPE
                SYNTAX  RebootType
		ACCESS  read-write
                STATUS  mandatory
                DESCRIPTION
                        "Instruct the oppm to do a warmboot. A get on this will
			 always return an other." 
                ::= { oppmEntry 10 }




        oppmTxInsertLoss      OBJECT-TYPE
                SYNTAX  DisplayString 
                ACCESS  read-only
                STATUS  mandatory
                DESCRIPTION
                        "Transmit insertion loss."
                ::= { oppmEntry 12 }

        oppmRxInsertLoss      OBJECT-TYPE
                SYNTAX  DisplayString 
                ACCESS  read-only
                STATUS  mandatory
                DESCRIPTION
                        " Receive insertion loss."
                ::= { oppmEntry 13 }

        oppmUpgradeFlag    OBJECT-TYPE
                SYNTAX  INTEGER { upgradable(1), notUpgradable(2) }
                ACCESS  read-only
                STATUS  mandatory
                DESCRIPTION
                        "The oppm card's status is upgradable or not."
                ::= {oppmEntry 14 }

	oppmSwitch     OBJECT-TYPE
                SYNTAX  INTEGER { 
					other(1),
					switchToLinkA(2),
					switchToLinkB(3), 
					toggle(4),
					enableAutoSwitch(6) 
				}
                ACCESS  read-write
                STATUS  mandatory
                DESCRIPTION
                        "instruct the OPPM to take on an
                         action, such as: switch to link A or link B
			  A get would alway return other(1)."
                ::= { oppmEntry 15 }


	oppmMarginForSwitch     OBJECT-TYPE
                SYNTAX  INTEGER (5..15)
                ACCESS  read-write
                STATUS  mandatory
                DESCRIPTION
                        "Configurable switching margin in dB
			 for protection switch to occur."                         
                ::= { oppmEntry 16 }

	oppmHighAlarmMargin     OBJECT-TYPE
                SYNTAX  INTEGER 
                ACCESS  read-only
                STATUS  mandatory
                DESCRIPTION
                        "High alarm margin for input signal strength
			 displayed in dB unit "
                ::= { oppmEntry 17 }

        oppmConfigCommit       OBJECT-TYPE
                SYNTAX  INTEGER { other(1), save(2) }
                ACCESS  read-write
                STATUS  mandatory
                DESCRIPTION
                        "This allows the current module configuration,
			 such as oppmMarginForSwitch, to be
                         stored in permanent storage."
                ::= { oppmEntry 18 }

        oppmHWName       OBJECT-TYPE
                SYNTAX  CardName
                ACCESS  read-only
                STATUS  mandatory
                DESCRIPTION
                        "Display Hardware name of the OPPM Card."
                ::= { oppmEntry 19 }

		oppmLinkAPathID	OBJECT-TYPE
                SYNTAX  PathIdName
                ACCESS  read-write
                STATUS  mandatory
                DESCRIPTION
                        "Oppmm LinkA Path ID name that this card is associated with.  
						 Set input equal NULL will remove the card off the path 
						 and also remove the path if there is no card left 
						 associate with that path."
                ::= { oppmEntry 20 }

		oppmLinkBPathID	OBJECT-TYPE
                SYNTAX  PathIdName
                ACCESS  read-write
                STATUS  mandatory
                DESCRIPTION
                        "Oppm LinkB Path ID name that this card is associated with.  
						 Set input equal NULL will remove the card off the path 
						 and also remove the path if there is no card left 
						 associate with that path."
                ::= { oppmEntry 21 }

       oppmAdminState     OBJECT-TYPE
                SYNTAX  INTEGER
						{ disable(1),
						  enable(2),
						  na(3)
						}
                ACCESS  read-write
                STATUS  mandatory
                DESCRIPTION
                        "Administrative control over that oppm card. Default value is enable.
						 When disabled, no alarms/events gets
						 generated."
                ::= { oppmEntry 22 }

		
        oppmPortTable        OBJECT-TYPE
                SYNTAX  SEQUENCE OF OppmPortEntry
                ACCESS  not-accessible
                STATUS  mandatory
                DESCRIPTION
                        "This table represents the physical connection for each
                         OPPM card's port."
                ::= { oppm 7 }

        oppmPortEntry        OBJECT-TYPE
                SYNTAX  OppmPortEntry
                ACCESS  not-accessible
                STATUS  mandatory
                DESCRIPTION
                        "Specifies the index for each row in the table below"
                INDEX { oppmPortCardShelf, oppmPortCardSlot, oppmPortType }
                ::= { oppmPortTable 1 }

        OppmPortEntry        ::=
                SEQUENCE {
						oppmPortCardShelf		CardShelf,
						oppmPortCardSlot		INTEGER,
						oppmPortType			INTEGER,
						oppmConnLocation		CardLocation,
						oppmConnIpAddress		IpAddress,
						oppmConnChassisID		NodeName,
						oppmConnSystemName		NodeName,
						oppmConnCardType		INTEGER,
                        oppmConnPort			INTEGER,
                        oppmConnShelf			INTEGER,
                        oppmConnSlot			INTEGER						
						}


        oppmPortCardShelf    OBJECT-TYPE
                SYNTAX  CardShelf
                ACCESS  read-only 
                STATUS  mandatory
                DESCRIPTION
                        "The shelf the card is in.  Valid values are: 1 to 2."
                ::= { oppmPortEntry 1 }

        oppmPortCardSlot     OBJECT-TYPE
                SYNTAX  SlotInput
                ACCESS  read-only 
                STATUS  mandatory
                DESCRIPTION
                        "The slot within the shelf the card is in."
                ::= { oppmPortEntry 2 }

		oppmPortType		OBJECT-TYPE 
                SYNTAX  INTEGER { 
								  linkATx(1), 
								  linkARx(2), 
								  linkBTx(3),
								  linkBRx(4), 
								  localTx(5), 
								  localRx(6) 
								}
                ACCESS  read-write
                STATUS  mandatory
                DESCRIPTION
                        "Type of the OPPM's port."
                ::= { oppmPortEntry 3 }

		oppmConnLocation    OBJECT-TYPE
                SYNTAX  CardLocation
                ACCESS  read-write
                STATUS  mandatory
                DESCRIPTION
                        "The chassis's location of the card conn to."
                ::= { oppmPortEntry 4 }


        oppmConnIpAddress OBJECT-TYPE
                SYNTAX  IpAddress
                ACCESS  read-write
                STATUS  mandatory
                DESCRIPTION
                        "IpAddress of the connected node.  User config. If local
						 connection, a set on it would return an error; would be automatically
						 be set to the IP address of the node "
                ::= { oppmPortEntry 5}

		oppmConnChassisID OBJECT-TYPE
                SYNTAX  DisplayString(SIZE(0..16))
                ACCESS  read-write
                STATUS  mandatory
                DESCRIPTION
                        "Chassis ID of the connected node.  User config. If local connection,
						a set on it would return an error; would be automatically be set to
						the chassis Id of the local node"
                ::= { oppmPortEntry 6}

        oppmConnSystemName OBJECT-TYPE
                SYNTAX  DisplayString(SIZE(0..32))
                ACCESS  read-write
                STATUS  mandatory
                DESCRIPTION
                        "System Name of the connected node.  User config. If local connection,
						a set on it would return an error; would be automatically be set to
						the sysetem name of the local node."
                ::= { oppmPortEntry 7}

        oppmConnCardType      OBJECT-TYPE
                SYNTAX  INTEGER (0..30)
                ACCESS  read-write
                STATUS  mandatory
                DESCRIPTION
                        "Type of connection.  Valid values are ocmu(2),
			 ocmItu(3), ocm10g(27), mux(4), demux(5), mcm(8), w4cd(10), w2cmd(13), w4cm(21),
			 osam(20), fadm(6), oppm(7), fadmb(19), ocme(24), etc...
			 A zero will be used for no connections."
                ::= { oppmPortEntry 8}

        oppmConnPort    OBJECT-TYPE
                SYNTAX  INTEGER
                ACCESS  read-write
                STATUS  mandatory
                DESCRIPTION
                        "Conn port for OPPM's port.Possible values based on 
				 card types that can connect to OPPM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx "
						 
                ::= { oppmPortEntry 9 }

        oppmConnShelf    OBJECT-TYPE
                SYNTAX  ShelfInput
                ACCESS  read-write
                STATUS  mandatory
                DESCRIPTION
                        "The shelf the card conn to. Valid values are: 1 to 2."
                ::= { oppmPortEntry 10 }

        oppmConnSlot     OBJECT-TYPE
                SYNTAX  SlotInput
                ACCESS  read-write
                STATUS  mandatory
                DESCRIPTION
                        "The slot within the shelf the card conn to."
                ::= { oppmPortEntry 11 }


-- The table of mcm


        mcmBootPromVer  OBJECT-TYPE
                SYNTAX  VersionString
                ACCESS  read-only
                STATUS  mandatory
                DESCRIPTION
                        "The current version string of the mcm Boot PROM code"
                ::= { mcm 1 }

        mcmROMSize      OBJECT-TYPE
                SYNTAX  INTEGER (0..1024)
                ACCESS  read-only
                STATUS  mandatory
                DESCRIPTION
                        "Total Size of the ROM in Kilobyes"
                ::= { mcm 2 }

        mcmNumSubDiv    OBJECT-TYPE
                SYNTAX  INTEGER (0..20)
                ACCESS  read-only
                STATUS  mandatory
                DESCRIPTION
                        "Number of the subdivisions of the ROM."
                ::= { mcm 3 }

        mcmSubDivTable  OBJECT-TYPE
                SYNTAX  SEQUENCE OF McmSubDivEntry
                ACCESS  not-accessible
                STATUS  mandatory
                DESCRIPTION
                        "This table represents the number of sub divisions
                         and the size of each subdivision in ROM memory"
                ::= { mcm 4 }

        mcmSubDivEntry  OBJECT-TYPE
                SYNTAX  McmSubDivEntry
                ACCESS  not-accessible
                STATUS  mandatory
                DESCRIPTION
                        "Specifies the index for each row in the table below"
                INDEX { mcmSubDivIndex }
                ::= { mcmSubDivTable 1 }

        McmSubDivEntry  ::=
                SEQUENCE {
                        mcmSubDivIndex  INTEGER,
                        mcmSubDivDescr  DisplayString,
                        mcmSubDivSize   INTEGER,
                        mcmSubDivOffset OCTET STRING
                }

        mcmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { mcmSubDivEntry 1 }

        mcmSubDivDescr  OBJECT-TYPE
                SYNTAX  DisplayString (SIZE (0..20))
                ACCESS  not-accessible
                STATUS  mandatory
                DESCRIPTION
                        "Display Name of each Sub Division in ROM"
                ::= { mcmSubDivEntry 2 }

        mcmSubDivSize   OBJECT-TYPE
                SYNTAX  INTEGER (0..1024)
                ACCESS  not-accessible
                STATUS  mandatory
                DESCRIPTION
                        "Size of each sub division in ROM in kilobytes"
                ::= { mcmSubDivEntry 3 }

        mcmSubDivOffset OBJECT-TYPE
                SYNTAX  OCTET STRING (SIZE (0..8))
                ACCESS  not-accessible
                STATUS  mandatory
                DESCRIPTION
                        "Starting address of each sub division in the ROM
                         in HEX notation."
                ::= { mcmSubDivEntry 4 }

        mcmNumber       OBJECT-TYPE
                SYNTAX  INTEGER
                ACCESS  read-only
                STATUS  mandatory
                DESCRIPTION
                        "Number of ADM rows in the following table.  This number
                         is automatically updated whenever a new row is added
                         to the table below."
                ::= { mcm 5 }

        mcmTable        OBJECT-TYPE
                SYNTAX  SEQUENCE OF McmEntry
                ACCESS  not-accessible
                STATUS  mandatory
                DESCRIPTION
                        "This table represents the information for each
                         mcm module"
                ::= { mcm 6 }

        mcmEntry        OBJECT-TYPE
                SYNTAX  McmEntry
                ACCESS  not-accessible
                STATUS  mandatory
                DESCRIPTION
                        "Specifies the index for each row in the table below"
                INDEX { mcmCardLocation, mcmCardShelf, mcmCardSlot }
                ::= { mcmTable 1 }

        McmEntry        ::=
                SEQUENCE {
                        mcmCardLocation     CardLocation,
                        mcmCardShelf        CardShelf,
                        mcmCardSlot         INTEGER,
                        mcmMfgDate          DateAndTime,
                        mcmSerialNum        SerialString,
                        mcmModelType        INTEGER,
                        mcmName             CardName,
                        mcmFWVersionID      VersionString,
                        mcmAdminState       INTEGER,
                        mcmLaserTemperature INTEGER,
                        mcmBandwidth        INTEGER,
                        mcmSetState         INTEGER,
                        mcmNumPorts         INTEGER,
                        mcmUpgradeFlag      INTEGER,
                        mcmEthernetStatus   INTEGER,
                        mcmTimingPort       INTEGER,
                        mcmModelNum         DisplayString,
                        mcmMfgBiasCurrent   INTEGER,
                        mcmMfgModulation    INTEGER,
                        mcmMfgApc           INTEGER,
                        mcmMfgIwmModulation INTEGER,
                        mcmconnMuxShelf     INTEGER,
                        mcmconnMuxSlot      INTEGER,
                        mcmconnMuxPort      INTEGER,
                        mcmconnDemuxShelf   INTEGER,
                        mcmconnDemuxSlot    INTEGER,
                        mcmconnDemuxPort    INTEGER,
                        mcmTimingPriority   DisplayString,
                        mcmLinkName         LinkName,
                        mcmEthernetMode     INTEGER,
                        mcmHWName           CardName,
                        mcmLinkWaveLength   DisplayString,
						mcmFpgaVersionID	VersionString,
						mcmPathID			PathIdName
                }

        mcmCardLocation OBJECT-TYPE
                SYNTAX  CardLocation
                ACCESS  read-only
                STATUS  mandatory
                DESCRIPTION
                        "Location of the mcm Module."
                ::= { mcmEntry 1 }

        mcmCardShelf    OBJECT-TYPE
                SYNTAX  CardShelf
                ACCESS  read-only
                STATUS  mandatory
                DESCRIPTION
                        "The shelf of the mcm is in.  Valid values are: 1..3"
                ::= { mcmEntry 2 }

        mcmCardSlot     OBJECT-TYPE
                SYNTAX  SlotInput
                ACCESS  read-write
                STATUS  mandatory
                DESCRIPTION
                        "The slot within the shelf the module is in.  The range
			 of valid values range from 1 through 21 depending on
			 the chassis type and the shelf the module is in.
                         To delete this card, set this variable to 0."
                ::= { mcmEntry 3 }


        mcmMfgDate      OBJECT-TYPE
                SYNTAX  DateAndTime
                ACCESS  read-only
                STATUS  mandatory
                DESCRIPTION
                        "Date and Time of manufacturing of the mcm card"
                ::= { mcmEntry 4 }

        mcmSerialNum    OBJECT-TYPE
                SYNTAX  SerialString
                ACCESS  read-only
                STATUS  mandatory
                DESCRIPTION
                        "Serial # of the mcm card."
                ::= { mcmEntry 5 }

        mcmModelType    OBJECT-TYPE
                SYNTAX  INTEGER {
		  			mcmMod(8)
				}
                ACCESS  read-only 
                STATUS  mandatory
                DESCRIPTION
                        "Model type of the mcm"
                ::= { mcmEntry 6 }

        mcmName         OBJECT-TYPE
                SYNTAX  CardName
                ACCESS  read-write
                STATUS  mandatory
                DESCRIPTION
                        "Display (Network) name of the MCM Module"
                ::= { mcmEntry 7 }

        mcmFWVersionID    OBJECT-TYPE
                SYNTAX  VersionString
                ACCESS  read-only
                STATUS  mandatory
                DESCRIPTION
                        "The current version string of the MCM FW code"
                ::= { mcmEntry 8 }


        mcmAdminState     OBJECT-TYPE
                SYNTAX  INTEGER
						{ disable(1),
						  enable(2),
						  na(3)
						}
                ACCESS  read-write
                STATUS  mandatory
                DESCRIPTION
                        "Administrative control over that mcm card. Default value is enable.
						 When disabled, no alarms/events gets
						 generated."
                ::= {  mcmEntry 9 }

        mcmLaserTemperature  OBJECT-TYPE
                SYNTAX  INTEGER
                ACCESS  not-accessible 
                STATUS  mandatory
                DESCRIPTION
                        "Temperature of the Laser.  Not yet supported"
                ::= { mcmEntry 10 }

        mcmBandwidth    OBJECT-TYPE
                SYNTAX  INTEGER {
				other(1),
		    		oc3(2),
				oc12(3),
				oc48(4),
				gbEthernet(5),
				fibreChannel(6)
		    }
                ACCESS  not-accessible
                STATUS  mandatory
                DESCRIPTION
                        "mcm module's line rate."
                ::= { mcmEntry 11 }


        mcmSetState     OBJECT-TYPE
                SYNTAX  INTEGER { other(1),
				  resetWithCurrentConfiguration(2),
				  resetWithFactoryDefault(3),
				  nearEndCardLoopback(4),
				  networkCardLoopback(5),
				  nearEndPort1Loopback(6),
				  nearEndPort2Loopback(7),
				  nearEndPort3Loopback(8),
				  nearEndPort4Loopback(9),
				  networkPort1Loopback(10),
				  networkPort2Loopback(11),
				  networkPort3Loopback(12),
				  networkPort4Loopback(13),
				  disableLoopback(14)
				}
                ACCESS  read-write
                STATUS  mandatory
                DESCRIPTION
                        "Instruct the mcm card to do either a reset or loopback.
			 A get on this will always return an other." 
                ::= { mcmEntry 12 }


        mcmNumPorts    OBJECT-TYPE
                SYNTAX  INTEGER
                ACCESS  read-only
                STATUS  mandatory
                DESCRIPTION
                        "Total port numbers of MCM module."
                ::= { mcmEntry 13 }

        mcmUpgradeFlag    OBJECT-TYPE
                SYNTAX  INTEGER { upgradable(1), notUpgradable(2) }
                ACCESS  read-only
                STATUS  mandatory
                DESCRIPTION
                        "The MCM module's status is upgradable or not."
                ::= { mcmEntry 14 }

        mcmEthernetStatus    OBJECT-TYPE
                SYNTAX  INTEGER { connDown(1), connUp(2) }
                ACCESS  read-only
                STATUS  mandatory
                DESCRIPTION
                        "The MCM module's Ethernet status is down or up."
                ::= { mcmEntry 15 }

        mcmTimingPort    OBJECT-TYPE
                SYNTAX  INTEGER {
					internal(1),
					link(2),
					t1Port1(3),
					t1Port2(4),
					t1Port3(5),
					t1Port4(6)
				}
                ACCESS  read-only
                STATUS  mandatory
                DESCRIPTION
                        "The MCM module's port clock src"
                ::= { mcmEntry 16 }


        mcmModelNum    OBJECT-TYPE
                SYNTAX  DisplayString 
                ACCESS  read-only
                STATUS  mandatory
                DESCRIPTION
                        "The mcm port's model number"
                ::= { mcmEntry 17 }

        mcmMfgBiasCurrent  OBJECT-TYPE
                SYNTAX  INTEGER
                ACCESS  read-only
                STATUS  mandatory
                DESCRIPTION
                        "Bias current for the optical laser.  This is the
                         preset manufacturing value"
                ::= { mcmEntry 18 }

        mcmMfgModulation  OBJECT-TYPE
                SYNTAX  INTEGER
                ACCESS  read-only
                STATUS  mandatory
                DESCRIPTION
                        "The frequency modulation for the optical laser.  This
                         value is the preset manufacturing value."
                ::= { mcmEntry 19 }

        mcmMfgApc        OBJECT-TYPE
                SYNTAX  INTEGER
                ACCESS  read-only
                STATUS  mandatory
                DESCRIPTION
                        "The APC value.  This value is the preset
                         manufacturing value"
                ::= { mcmEntry 20 }

        mcmMfgIwmModulation  OBJECT-TYPE
                SYNTAX  INTEGER
                ACCESS  read-only
                STATUS  mandatory
                DESCRIPTION
                        "The frequency modulation for the IWM channel.  This
                         value is the preset manufacturing value"
                ::= { mcmEntry 21 }

       mcmconnMuxShelf     OBJECT-TYPE
                SYNTAX  ShelfInput
                ACCESS  read-only
                STATUS  mandatory
                DESCRIPTION
                        "The connected mux shelf."
                ::= { mcmEntry 22 }

        mcmconnMuxSlot      OBJECT-TYPE
                SYNTAX  SlotInput
                ACCESS  read-only
                STATUS  mandatory
                DESCRIPTION
                        "The connected mux slot."
                ::= { mcmEntry 23 }

        mcmconnMuxPort      OBJECT-TYPE
                SYNTAX  INTEGER
                ACCESS  read-only
                STATUS  mandatory
                DESCRIPTION
                        "The connected mux port. "
                ::= { mcmEntry 24 }

	mcmconnDemuxShelf     OBJECT-TYPE
                SYNTAX  ShelfInput
                ACCESS  read-only
                STATUS  mandatory
                DESCRIPTION
                        "The connected demux shelf."
                ::= { mcmEntry 25 }

        mcmconnDemuxSlot      OBJECT-TYPE
                SYNTAX  SlotInput
                ACCESS  read-only
                STATUS  mandatory
                DESCRIPTION
                        "The connected demux slot."
                ::= { mcmEntry 26 }

        mcmconnDemuxPort      OBJECT-TYPE
                SYNTAX  INTEGER
                ACCESS  read-only
                STATUS  mandatory
                DESCRIPTION
                        "The connected demux port. " 
                ::= { mcmEntry 27 }

	mcmTimingPriority	OBJECT-TYPE
		SYNTAX	DisplayString (SIZE (0..12))
		ACCESS	read-write
		STATUS	mandatory
		DESCRIPTION
			"The clock source priority in descending order
			 in the format of a,b,c,d,e,f in which a
			 through f should be replaced with 1 through 6
			 which has the same meaning as the options of
			 mcmTimingPort and are repeated as follows:
				
				0 - unknown
				1 - internal
				2 - link
				3 - t1Port1
				4 - t1Port2
				5 - t1Port3
				6 - t1Port4

			 For example, '2,5,4,6,3,1' will set the priority
			 of the clock source with link first, followed by
			 t1Port3, followed by t1Port2, followed by t1Port4,
			 followed by t1Port1, followed by internal."
                ::= { mcmEntry 28 }

        mcmLinkName         OBJECT-TYPE
                SYNTAX  LinkName
                ACCESS  read-write
                STATUS  mandatory
                DESCRIPTION
                        "User configurable Link name for the connection
			 between the local and remote MCM Modules"
                ::= { mcmEntry 29 }

        mcmEthernetMode    OBJECT-TYPE
                SYNTAX  INTEGER { auto(1), forced10M(2), forced100M(3) }
                ACCESS  read-write
                STATUS  mandatory
                DESCRIPTION
                        "This allows the ethernet mode configured as
			 auto detect, forced 10M, or forced 100M."
                ::= { mcmEntry 30 }

        mcmHWName       OBJECT-TYPE
                SYNTAX  CardName
                ACCESS  read-only
                STATUS  mandatory
                DESCRIPTION
                        "Display Hardware name of the MCM Card."
                ::= { mcmEntry 31 }

        mcmLinkWaveLength	OBJECT-TYPE
                SYNTAX  DisplayString (SIZE (0..15))
                ACCESS  read-only
                STATUS  mandatory
                DESCRIPTION
                        "Link Wavelength of the MCM card"
                ::= { mcmEntry 32 }

		mcmFpgaVersionID    OBJECT-TYPE
                SYNTAX  VersionString
                ACCESS  read-only
                STATUS  mandatory
                DESCRIPTION
                        "The current version string of the MCM FPGA."
                ::= { mcmEntry 33 }

		mcmPathID		OBJECT-TYPE
                SYNTAX  PathIdName
                ACCESS  read-write
                STATUS  mandatory
                DESCRIPTION
						"Upsr Path ID name that this card is associated with.  
						 Set input equal NULL will remove the card off the path 
						 and also remove the path if there is no card left 
						 associate with that path."
                ::= { mcmEntry 34 }

        mcmPortNumber       OBJECT-TYPE
                SYNTAX  INTEGER
                ACCESS  read-only
                STATUS  mandatory
                DESCRIPTION
                        "Number of MCM rows in the following table.  This 
                         number is automatically updated whenever a new row is 
                         added to the table below."
                ::= { mcm 7 }

        mcmPortTable        OBJECT-TYPE
                SYNTAX  SEQUENCE OF McmPortEntry
                ACCESS  not-accessible
                STATUS  mandatory
                DESCRIPTION
                        "This table represents the information for each
                         MCM module's port."
                ::= { mcm 8 }

        mcmPortEntry        OBJECT-TYPE
                SYNTAX  McmPortEntry
                ACCESS  not-accessible
                STATUS  mandatory
                DESCRIPTION
                        "Specifies the index for each row in the table below"
                INDEX { mcmPortCardLocation, mcmPortCardShelf,
                        mcmPortCardSlot,  mcmPortIndex }
                ::= { mcmPortTable 1 }

        McmPortEntry        ::=
                SEQUENCE {
                        mcmPortCardLocation 		CardLocation,
                        mcmPortCardShelf    		CardShelf,
                        mcmPortCardSlot     		INTEGER,
						mcmPortIndex	  			INTEGER,
                        mcmPortConnection        	INTEGER,
                        mcmPortFraming       		INTEGER,
                        mcmPortLineCoding     		INTEGER,
                        mcmPortLineEqualizer		INTEGER,
						mcmPortImpedance			INTEGER
                }

        mcmPortCardLocation OBJECT-TYPE
                SYNTAX  CardLocation
                ACCESS  read-only 
                STATUS  mandatory
                DESCRIPTION
                        "Location of the MCM port.  Valid values are: Local in
                         the same chassis, or remote to this chassis"
                ::= { mcmPortEntry 1 }

        mcmPortCardShelf    OBJECT-TYPE
                SYNTAX  CardShelf
                ACCESS  read-only 
                STATUS  mandatory
                DESCRIPTION
                        "The shelf the card is in.  Valid values are: 2..3."
                ::= { mcmPortEntry 2 }

        mcmPortCardSlot     OBJECT-TYPE
                SYNTAX  SlotInput
                ACCESS  read-only 
                STATUS  mandatory
                DESCRIPTION
                        "The slot within the shelf the Module is in.  Valid
                         values are: 1 to 21"
                ::= { mcmPortEntry 3 }

        mcmPortIndex      OBJECT-TYPE
                SYNTAX  INTEGER 
                ACCESS  read-only 
                STATUS  mandatory
                DESCRIPTION
                        "Port's index."
                ::= { mcmPortEntry 4 }

        mcmPortConnection      OBJECT-TYPE
                SYNTAX  INTEGER {
					connDown(1),
					connUp(2)
				}
                ACCESS  read-write
                STATUS  mandatory
                DESCRIPTION
                        "Port's connection status."
                ::= { mcmPortEntry 5 }

        mcmPortFraming      OBJECT-TYPE
                SYNTAX  INTEGER { esf(1),
    					    d4(2) 
		    }
                ACCESS  read-write
                STATUS  mandatory
                DESCRIPTION
                        "Type of Frame." 
                ::= { mcmPortEntry 6 }

        mcmPortLineCoding    OBJECT-TYPE
                SYNTAX  INTEGER {
					b8zs(1),
					ami(2)
				}
                ACCESS  read-write
                STATUS  mandatory
                DESCRIPTION
                        "The port's line coding type."
                ::= { mcmPortEntry 7 }


        mcmPortLineEqualizer     OBJECT-TYPE
                SYNTAX  INTEGER {
					l0to133ft(1),
					l133to266ft(2),
					l266to399ft(3),
					l399to533ft(4),
					l533to655ft(5)
				}
                ACCESS  read-write
                STATUS  mandatory
                DESCRIPTION
                        "The Line length."
                ::= { mcmPortEntry 8 }

        mcmPortImpedance     OBJECT-TYPE
                SYNTAX  INTEGER {
					ohms-120(1),
					ohms-75(2)
				}
                ACCESS  read-write
                STATUS  mandatory
                DESCRIPTION
                        "Line Impedance.  Only applicable for E1."
                ::= { mcmPortEntry 9 }

        -- The elements in the fn subgroup of the configuration group

        fnNumber        OBJECT-TYPE
                SYNTAX  INTEGER
                ACCESS  not-accessible 
                STATUS  mandatory
                DESCRIPTION
                        "Number of fn rows in the following table.  This number
                         is automatically updated whenever a new row is added
                         to the table below."
                ::= { fn 1 }

        fnTable         OBJECT-TYPE
                SYNTAX  SEQUENCE OF FnEntry
                ACCESS  not-accessible
                STATUS  mandatory
                DESCRIPTION
                        "This table represents the information for each
                         fn."
                ::= { fn 2 }

        fnEntry OBJECT-TYPE
                SYNTAX  FnEntry
                ACCESS  not-accessible
                STATUS  mandatory
                DESCRIPTION
                        "Specifies the index for each row in the table below"
                INDEX { fnID }
                ::= { fnTable 1 }

        FnEntry         ::=
                SEQUENCE {
                        fnID		INTEGER,
			fnMfgDate       DateAndTime,
                        fnSerialNum     SerialString,
                        fnModelType     ModelString
                }

        fnID    OBJECT-TYPE
                SYNTAX  INTEGER  (1..4)
                ACCESS  not-accessible 
                STATUS  mandatory
                DESCRIPTION
                        "The slot ID the fn is in.  Valid values are: 1 to 4"
                ::= { fnEntry 1 }



        fnMfgDate       OBJECT-TYPE
                SYNTAX  DateAndTime
                ACCESS  not-accessible 
                STATUS  mandatory
                DESCRIPTION
                        "Date and Time of manufacturing of the fn"
                ::= { fnEntry 2 }

        fnSerialNum     OBJECT-TYPE
                SYNTAX  SerialString
                ACCESS  not-accessible 
                STATUS  mandatory
                DESCRIPTION
                        "Serial # of the fn.  Not Supported Yet."
                ::= { fnEntry 3 }

        fnModelType     OBJECT-TYPE
                SYNTAX  ModelString
                ACCESS  not-accessible 
                STATUS  mandatory
                DESCRIPTION
                        "Model type of the fn. Up to 10 characters.
			 Not Supported Yet."
                ::= { fnEntry 4 }

	  --The elements in the csim subgroup of the configuration group
	csimSysMode 	OBJECT-TYPE
                SYNTAX  INTEGER
		    { 	enable(1),
				disable(2),
				other(3)
		    }
                ACCESS  read-write
                STATUS  mandatory
                DESCRIPTION
                        "The ColorSim Mode of the Chassis. The value Enable
			 means that the ColorSim feature is enabled for
			 all the interface cards. An action element, returns other on
			 a get request."
                ::= { csim 1 }
        
	csimTable       OBJECT-TYPE
                SYNTAX  SEQUENCE OF CsimEntry
                ACCESS  not-accessible
                STATUS  mandatory
                DESCRIPTION
                        "Each entry in this table represents the
			 information for each colorsim card."
                ::= { csim 2 }

        csimEntry       OBJECT-TYPE
                SYNTAX  CsimEntry
                ACCESS  not-accessible
                STATUS  mandatory
                DESCRIPTION
                        "Specifies the index for each row in the table below."
                INDEX { csimLocation, csimShelf, csimSlot }
                ::= { csimTable 1 }

        CsimEntry         ::=
                SEQUENCE {
                        csimLocation 		CardLocation,
                        csimShelf       	CardShelf,
                        csimSlot        	INTEGER,
			csimMode		INTEGER,
			csimDCMode		INTEGER,
			csimGatingIntvl		INTEGER,
			csimUpdtIntvl		INTEGER,
			csimSEIThreshold	DisplayString
			}
	
        csimLocation  OBJECT-TYPE
                SYNTAX  CardLocation
                ACCESS  read-only
                STATUS  mandatory
                DESCRIPTION
                        "Location of the card.  Valid values are: Local in
                         the same chassis, or remote to this chassis."
                ::= { csimEntry 1 }

        csimShelf     OBJECT-TYPE
                SYNTAX  CardShelf
                ACCESS  read-only
                STATUS  mandatory
                DESCRIPTION
                        "The shelf the card is in.  Valid values are: 1 to 10"
                ::= { csimEntry 2 }

        csimSlot      OBJECT-TYPE
                SYNTAX  SlotInput
                ACCESS  read-only 
                STATUS  mandatory
                DESCRIPTION
                        "This card occupies two slots currently."
                ::= { csimEntry 3 }

        csimMode     OBJECT-TYPE
                SYNTAX  INTEGER
		    { 	enable(1),
			disable(2)
		    }
                ACCESS  read-write
                STATUS  mandatory
                DESCRIPTION
                        "The Mode of ColorSIM for this entry. The Modes
			 are Enable or Disable."
                ::= { csimEntry 4 }

        csimDCMode     OBJECT-TYPE
                SYNTAX  INTEGER
		    { 	standard(1),
			continuous(2)
		    }
                ACCESS  read-write 
                STATUS  mandatory
                DESCRIPTION
                        "The Data Collection Mode of ColorSIM."
                ::= { csimEntry 5 }

        csimGatingIntvl     OBJECT-TYPE
                SYNTAX  INTEGER (1..65535)
                ACCESS  read-write 
                STATUS  mandatory
                DESCRIPTION
                        "The Gating Interval in seconds in which
			 the incoming data stream is being monitored
			 for errors."
                ::= { csimEntry 6 }

        csimUpdtIntvl     OBJECT-TYPE
                SYNTAX  INTEGER (1..65535)
                ACCESS  read-write
                STATUS  mandatory
                DESCRIPTION
                        "Number of gating intervals to be processed before
			 the data is logged for reporting purposes."
                ::= { csimEntry 7 }

        csimSEIThreshold     OBJECT-TYPE
                SYNTAX  DisplayString
                ACCESS  read-write
                STATUS  mandatory
                DESCRIPTION
                        "The SEI Threshold of ColorSIM specifies the
			 maximum number of errored bits that may have
			 occurred during a single gating interval before
			 the interval is considered Severely Errorred.
			 The Threshold values are in the form of
			 x.ye-z."
                ::= { csimEntry 8 }

        -- The elements in the rpsm subgroup of the configuration group

        rpsmBootPromVer  OBJECT-TYPE
                SYNTAX  VersionString
                ACCESS  not-accessible
                STATUS  mandatory
                DESCRIPTION
                        "The current version string of the rpsm
			 Boot PROM code"
                ::= { rpsm 1 }

        rpsmROMSize      OBJECT-TYPE
                SYNTAX  INTEGER (0..1024)
                ACCESS  not-accessible
                STATUS  mandatory
                DESCRIPTION
                        "Total Size of the ROM in Kilobyes"
                ::= { rpsm 2 }

        rpsmNumSubDiv    OBJECT-TYPE
                SYNTAX  INTEGER (0..20)
                ACCESS  not-accessible
                STATUS  mandatory
                DESCRIPTION
                        "Number of the subdivisions of the ROM."
                ::= { rpsm 3 }

        rpsmSubDivTable  OBJECT-TYPE
                SYNTAX  SEQUENCE OF RpsmSubDivEntry
                ACCESS  not-accessible
                STATUS  mandatory
                DESCRIPTION
                        "This table represents the number of sub divisions
                         and the size of each subdivision in ROM memory"
                ::= { rpsm 4 }

        rpsmSubDivEntry  OBJECT-TYPE
                SYNTAX  RpsmSubDivEntry
                ACCESS  not-accessible
                STATUS  mandatory
                DESCRIPTION
                        "Specifies the index for each row in the table below"
                INDEX { rpsmSubDivIndex }
                ::= { rpsmSubDivTable 1 }

        RpsmSubDivEntry  ::=
                SEQUENCE {
                        rpsmSubDivIndex  INTEGER,
                        rpsmSubDivDescr  DisplayString,
                        rpsmSubDivSize   INTEGER,
                        rpsmSubDivOffset OCTET STRING
                }

        rpsmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { rpsmSubDivEntry 1 }

        rpsmSubDivDescr  OBJECT-TYPE
                SYNTAX  DisplayString (SIZE (0..20))
                ACCESS  not-accessible
                STATUS  mandatory
                DESCRIPTION
                        "Display Name of each Sub Division in ROM"
                ::= { rpsmSubDivEntry 2 }

        rpsmSubDivSize   OBJECT-TYPE
                SYNTAX  INTEGER (0..1024)
                ACCESS  not-accessible
                STATUS  mandatory
                DESCRIPTION
                        "Size of each sub division in ROM in kilobytes"
                ::= { rpsmSubDivEntry 3 }

        rpsmSubDivOffset OBJECT-TYPE
                SYNTAX  OCTET STRING (SIZE (0..8))
                ACCESS  not-accessible
                STATUS  mandatory
                DESCRIPTION
                        "Starting address of each sub division in the ROM
                         in HEX notation."
                ::= { rpsmSubDivEntry 4 }

        rpsmNumber       OBJECT-TYPE
                SYNTAX  INTEGER
                ACCESS  read-only
                STATUS  mandatory
                DESCRIPTION
                        "Number of RPSM rows in the following table.  This 
                         number is automatically updated whenever a new row is 
                         added to the table below."
                ::= { rpsm 5 }

        rpsmTable        OBJECT-TYPE
                SYNTAX  SEQUENCE OF RpsmEntry
                ACCESS  not-accessible
                STATUS  mandatory
                DESCRIPTION
                        "This table represents the information for each
                         RPSM card"
                ::= { rpsm 6 }

        rpsmEntry        OBJECT-TYPE
                SYNTAX  RpsmEntry
                ACCESS  not-accessible
                STATUS  mandatory
                DESCRIPTION
                        "Specifies the index for each row in the table below"
                INDEX { rpsmCardLocation, rpsmCardShelf, rpsmCardSlot }
                ::= { rpsmTable 1 }

        RpsmEntry        ::=
                SEQUENCE {
                        rpsmCardLocation		CardLocation,
                        rpsmCardShelf			CardShelf,
                        rpsmCardSlot			INTEGER,
						rpsmModelNum			DisplayString,
                        rpsmOpticsMfgDate		DateAndTime,
                        rpsmSerialNum			SerialString,
                        rpsmModelType			INTEGER,
						rpsmHWName				CardName,
                        rpsmFWVersionID			VersionString,
						rpsmCardName			CardName,
						rpsmFWName				DisplayString,
						rpsmFWDate				DateAndTime,
						rpsmHWVersionID			VersionString,
						rpsmHWDate				DateAndTime,
                        rpsmSetState			RebootType,
						rpsmExpressLoss			DisplayString,
						rpsmMarginForSwitch		INTEGER,
						rpsmMinProtPowerForSwitch	INTEGER,
						rpsmDeBounce			INTEGER,
						rpsmBlackOutTime		INTEGER,
						rpsmSwitch				INTEGER,
						rpsmAddDropLoss			DisplayString,
						rpsmPathID				PathIdName,
						rpsmAdminState			INTEGER
                }

        rpsmCardLocation OBJECT-TYPE
                SYNTAX  CardLocation
                ACCESS  read-only
                STATUS  mandatory
                DESCRIPTION
                        "Location of the RPSM card.  Valid values are: Local in
                         the same chassis, or remote to this chassis."
                ::= { rpsmEntry 1 }

        rpsmCardShelf    OBJECT-TYPE
                SYNTAX  CardShelf
                ACCESS  read-only
                STATUS  mandatory
                DESCRIPTION
                        "The shelf the card is in.  Valid values are: 1 to 2."
                ::= { rpsmEntry 2 }

        rpsmCardSlot     OBJECT-TYPE
                SYNTAX  SlotInput
                ACCESS  read-write
                STATUS  mandatory
                DESCRIPTION
                        "The slot within the shelf the module is in.  The range
			 of valid values range from 1 through 17 depending on
			 the chassis type and the shelf the module is in.
                         To delete this card, set this variable to 0."
                ::= { rpsmEntry 3 }

        rpsmModelNum      OBJECT-TYPE
                SYNTAX  DisplayString
                ACCESS  read-only
                STATUS  mandatory
                DESCRIPTION
                        "RPSM's model number."
                ::= { rpsmEntry 4 }

        rpsmOpticsMfgDate      OBJECT-TYPE
                SYNTAX  DateAndTime
                ACCESS  read-only
                STATUS  mandatory
                DESCRIPTION
                        "Date and Time of manufacturing of the optics
			 on the RPSM card."
                ::= { rpsmEntry 5 }

        rpsmSerialNum    OBJECT-TYPE
                SYNTAX  SerialString
                ACCESS  read-only
                STATUS  mandatory
                DESCRIPTION
                        "Serial # of the RPSM card."
                ::= { rpsmEntry 6 }

        rpsmModelType    OBJECT-TYPE
                SYNTAX  INTEGER { rpsm(17) }
                ACCESS  read-only
                STATUS  mandatory
                DESCRIPTION
                        "Model type of the RPSM."
                ::= { rpsmEntry 7 }

        rpsmHWName       OBJECT-TYPE
                SYNTAX  CardName
                ACCESS  read-only
                STATUS  mandatory
                DESCRIPTION
                        "Manufacturing Hardware name of the RPSM Card."
                ::= { rpsmEntry 8 }

        rpsmFWVersionID    OBJECT-TYPE
                SYNTAX  VersionString
                ACCESS  read-only
                STATUS  mandatory
                DESCRIPTION
                        "The current version string of the RPSM FW code"
                ::= { rpsmEntry 9 }

        rpsmCardName    OBJECT-TYPE
                SYNTAX  CardName
		ACCESS  read-write
                STATUS  mandatory
                DESCRIPTION
                        "User configurable card name." 
                ::= { rpsmEntry 10 }

        rpsmFWName      OBJECT-TYPE
                SYNTAX  DisplayString
                ACCESS  read-only
                STATUS  mandatory
                DESCRIPTION
                        "RPSM's Firmware Name."
                ::= { rpsmEntry 11 }

        rpsmFWDate      OBJECT-TYPE
                SYNTAX  DateAndTime
                ACCESS  read-only
                STATUS  mandatory
                DESCRIPTION
                        "Date and Time of latest Firmware of the RPSM card."
                ::= { rpsmEntry 12 }

        rpsmHWVersionID    OBJECT-TYPE
                SYNTAX  VersionString
                ACCESS  read-only
                STATUS  mandatory
                DESCRIPTION
                        "The current version string of the RPSM HW code."
                ::= { rpsmEntry 13 }

        rpsmHWDate      OBJECT-TYPE
                SYNTAX  DateAndTime
                ACCESS  read-only
                STATUS  mandatory
                DESCRIPTION
                        "Date and Time of Hardware of the RPSM card."
                ::= { rpsmEntry 14 }

        rpsmSetState      OBJECT-TYPE
                SYNTAX  RebootType
		ACCESS  read-write
                STATUS  mandatory
                DESCRIPTION
                        "Instruct the rpsm to do a warmboot. A get on this will
			 always return an other." 
                ::= { rpsmEntry 15 }

        rpsmExpressLoss  OBJECT-TYPE
                SYNTAX  DisplayString
		ACCESS	read-only
                STATUS  mandatory
                DESCRIPTION
                        "Insertion loss for the expressed channel
			 through the RPSM module in dB." 
                ::= { rpsmEntry 16 }

        rpsmMarginForSwitch  OBJECT-TYPE
                SYNTAX  INTEGER (-40..0)
		ACCESS  read-write
                STATUS  mandatory
                DESCRIPTION
                        "Switching threshold in dB for protection
			 switch to occur." 
                ::= { rpsmEntry 17 }

        rpsmMinProtPowerForSwitch     OBJECT-TYPE
                SYNTAX  INTEGER (-40..0)
		ACCESS  read-write
                STATUS  mandatory
                DESCRIPTION
                        "Minimum protection link's light power in dBm
			 to allow protection switching to occur." 
                ::= { rpsmEntry 18 }

        rpsmDeBounce     OBJECT-TYPE
                SYNTAX	INTEGER
		ACCESS  read-only
                STATUS  mandatory
                DESCRIPTION
                        "Debounce in number of times to measure
			 low light power before protection switch."
                ::= { rpsmEntry 19 }

        rpsmBlackOutTime   OBJECT-TYPE
                SYNTAX  INTEGER
		ACCESS  read-only
                STATUS  mandatory
                DESCRIPTION
                        "Black out time in unit of 0.1 second after
			 protection switch to allow another protection
			 switch to occur again." 
                ::= { rpsmEntry 20 }

		rpsmSwitch     OBJECT-TYPE
                SYNTAX  INTEGER { 
					other(1),
					switchToLinkA(2),
					switchToLinkB(3), 
					toggle(4),
					enableAutoSwitch(6) 
				}
                ACCESS  read-write
                STATUS  mandatory
                DESCRIPTION
                        "instruct the RPSM to take on an action,
			 such as: switch to link A or link B.
			 A get would alway return other(1)."
                ::= { rpsmEntry 21 }

		rpsmAddDropLoss  OBJECT-TYPE
                SYNTAX  DisplayString
				ACCESS	read-only
                STATUS  mandatory
                DESCRIPTION
                        "Insertion loss of the Add/Drop path
			 through the RPSM module in dB." 
                ::= { rpsmEntry 22 }

		rpsmPathID		OBJECT-TYPE
                SYNTAX  PathIdName
				ACCESS	read-write
                STATUS  mandatory
                DESCRIPTION
                        "Upsr Path ID name that this card is associated with.  
						 Set input equal NULL will remove the card off the path 
						 and also remove the path if there is no card left 
						 associate with that path." 
                ::= { rpsmEntry 23 }

        rpsmAdminState     OBJECT-TYPE
                SYNTAX  INTEGER
						{ disable(1),
						  enable(2),
						  na(3)
						}
                ACCESS  read-write
                STATUS  mandatory
                DESCRIPTION
                        "Administrative control over that rpsm card. Default value is enable.
						 When disabled, no alarms/events gets
						 generated."
                ::= { rpsmEntry 24}

		rpsmPortTable	OBJECT-TYPE
                SYNTAX  SEQUENCE OF RpsmPortEntry
                ACCESS  not-accessible
                STATUS  mandatory
                DESCRIPTION
                        "This table represents the physical connection for each
                         RPSM card's port."
                ::= { rpsm 7 }

        rpsmPortEntry	OBJECT-TYPE
                SYNTAX  RpsmPortEntry
                ACCESS  not-accessible
                STATUS  mandatory
                DESCRIPTION
                        "Specifies the index for each row in the table below"
                INDEX { rpsmPortCardShelf, rpsmPortCardSlot, rpsmPortType }
                ::= { rpsmPortTable 1 }

        RpsmPortEntry        ::=
                SEQUENCE 
				{
						rpsmPortCardShelf		CardShelf,
						rpsmPortCardSlot		SlotInput,
						rpsmPortType			INTEGER,
						rpsmConnCardType		INTEGER,
						rpsmConnPort			INTEGER,
						rpsmConnShelf			ShelfInput,
                        rpsmConnSlot			SlotInput						
				}

        rpsmPortCardShelf    OBJECT-TYPE
                SYNTAX  CardShelf
                ACCESS  read-only 
                STATUS  mandatory
                DESCRIPTION
                        "The shelf the card is in.  Valid values are: 1 to 2."
                ::= { rpsmPortEntry 1 }

        rpsmPortCardSlot     OBJECT-TYPE
                SYNTAX  SlotInput
                ACCESS  read-only 
                STATUS  mandatory
                DESCRIPTION
                        "The slot within the shelf the card is in."
                ::= { rpsmPortEntry 2 }

		rpsmPortType		OBJECT-TYPE 
                SYNTAX  INTEGER { 
								  linkEast(1), 
								  linkWest(2), 
								  in(3),
								  out(4), 
								  aTOd(5), 
								  exp(6) 
								}
                ACCESS  read-only
                STATUS  mandatory
                DESCRIPTION
                        "Type of the RPSM's port.  The order is CLI compatible."
                ::= { rpsmPortEntry 3 }

        rpsmConnCardType      OBJECT-TYPE
                SYNTAX  INTEGER (0..30)
                ACCESS  read-write
                STATUS  mandatory
                DESCRIPTION
                        "Type of connection.  Valid values are ocmu(2),
			 ocmItu(3), mux(4), demux(5), mcm(8), w4cd(10), w2cmd(13), w4cm(21),
			 osam(20), fadm(6), oppm(7), fadmb(19), ocme(24), etc...
			 A zero will be used for no connections."
                ::= { rpsmPortEntry 4}

        rpsmConnPort    OBJECT-TYPE
                SYNTAX  INTEGER
                ACCESS  read-write
                STATUS  mandatory
                DESCRIPTION
                        "Conn port for RPSM's port.Possible values based on 
				 card types that can connect to RPSM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM: 1=Link Tx, 2=Link Rx
				 UPSM/OPPM: 1=Link A Tx, 2=Link A Rx, 3=Link B Tx,
				 4=Link B Rx, 5=Local Tx, 6=Local Rx "
						 
                ::= { rpsmPortEntry 5 }

        rpsmConnShelf   OBJECT-TYPE
                SYNTAX  ShelfInput
                ACCESS  read-write
                STATUS  mandatory
                DESCRIPTION
                        "The shelf the card conn to. Valid values are: 1 to 2."
                ::= { rpsmPortEntry 6 }

        rpsmConnSlot     OBJECT-TYPE
                SYNTAX  SlotInput
                ACCESS  read-write
                STATUS  mandatory
                DESCRIPTION
                        "The slot within the shelf the card conn to."
                ::= { rpsmPortEntry 7 }

        -- The elements in the rsdm subgroup of the configuration group

        rsdmBootPromVer  OBJECT-TYPE
                SYNTAX  VersionString
                ACCESS  not-accessible
                STATUS  mandatory
                DESCRIPTION
                        "The current version string of the rsdm Boot PROM code"
                ::= { rsdm 1 }

        rsdmROMSize      OBJECT-TYPE
                SYNTAX  INTEGER (0..1024)
                ACCESS  not-accessible
                STATUS  mandatory
                DESCRIPTION
                        "Total Size of the ROM in Kilobyes"
                ::= { rsdm 2 }

        rsdmNumSubDiv    OBJECT-TYPE
                SYNTAX  INTEGER (0..20)
                ACCESS  not-accessible
                STATUS  mandatory
                DESCRIPTION
                        "Number of the subdivisions of the ROM."
                ::= { rsdm 3 }

        rsdmSubDivTable  OBJECT-TYPE
                SYNTAX  SEQUENCE OF RsdmSubDivEntry
                ACCESS  not-accessible
                STATUS  mandatory
                DESCRIPTION
                        "This table represents the number of sub divisions
                         and the size of each subdivision in ROM memory"
                ::= { rsdm 4 }

        rsdmSubDivEntry  OBJECT-TYPE
                SYNTAX  RsdmSubDivEntry
                ACCESS  not-accessible
                STATUS  mandatory
                DESCRIPTION
                        "Specifies the index for each row in the table below"
                INDEX { rsdmSubDivIndex }
                ::= { rsdmSubDivTable 1 }

        RsdmSubDivEntry  ::=
                SEQUENCE {
                        rsdmSubDivIndex  INTEGER,
                        rsdmSubDivDescr  DisplayString,
                        rsdmSubDivSize   INTEGER,
                        rsdmSubDivOffset OCTET STRING
                }

        rsdmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { rsdmSubDivEntry 1 }

        rsdmSubDivDescr  OBJECT-TYPE
                SYNTAX  DisplayString (SIZE (0..20))
                ACCESS  not-accessible
                STATUS  mandatory
                DESCRIPTION
                        "Display Name of each Sub Division in ROM"
                ::= { rsdmSubDivEntry 2 }

        rsdmSubDivSize   OBJECT-TYPE
                SYNTAX  INTEGER (0..1024)
                ACCESS  not-accessible
                STATUS  mandatory
                DESCRIPTION
                        "Size of each sub division in ROM in kilobytes"
                ::= { rsdmSubDivEntry 3 }

        rsdmSubDivOffset OBJECT-TYPE
                SYNTAX  OCTET STRING (SIZE (0..8))
                ACCESS  not-accessible
                STATUS  mandatory
                DESCRIPTION
                        "Starting address of each sub division in the ROM
                         in HEX notation."
                ::= { rsdmSubDivEntry 4 }

        rsdmNumber       OBJECT-TYPE
                SYNTAX  INTEGER
                ACCESS  read-only
                STATUS  mandatory
                DESCRIPTION
                        "Number of RSDM rows in the following table.  This 
                         number is automatically updated whenever a new row is 
                         added to the table below."
                ::= { rsdm 5 }

        rsdmTable        OBJECT-TYPE
                SYNTAX  SEQUENCE OF RsdmEntry
                ACCESS  not-accessible
                STATUS  mandatory
                DESCRIPTION
                        "This table represents the information for each
                         RSDM card"
                ::= { rsdm 6 }

        rsdmEntry        OBJECT-TYPE
                SYNTAX  RsdmEntry
                ACCESS  not-accessible
                STATUS  mandatory
                DESCRIPTION
                        "Specifies the index for each row in the table below"
                INDEX { rsdmCardLocation, rsdmCardShelf, rsdmCardSlot }
                ::= { rsdmTable 1 }

        RsdmEntry        ::=
                SEQUENCE {
                        rsdmCardLocation		CardLocation,
                        rsdmCardShelf			CardShelf,
                        rsdmCardSlot			INTEGER,
			rsdmModelNum			DisplayString,
                        rsdmOpticsMfgDate		DateAndTime,
                        rsdmSerialNum			SerialString,
                        rsdmModelType			INTEGER,
                        rsdmHWName			CardName,
			rsdmCardName			CardName,
                        rsdmFWVersionID			VersionString,
			rsdmFWName			DisplayString,
			rsdmFWDate			DateAndTime,
			rsdmHWVersionID			VersionString,
			rsdmHWDate			DateAndTime,
                        rsdmSetState			RebootType,
			rsdmRxITUNumber			INTEGER,
			rsdmTxITUNumber			INTEGER,
			rsdmRxInsertionLoss		DisplayString,
			rsdmTxInsertionLoss		DisplayString, 
			rsdmExpressLoss			DisplayString,
			rsdmMarginForSwitch		INTEGER,
			rsdmMinProtPowerForSwitch	INTEGER,
			rsdmDeBounce			INTEGER,
			rsdmBlackOutTime		INTEGER,
			rsdmSwitch				INTEGER,
			rsdmPathID				PathIdName,
			rsdmAdminState			INTEGER
                }

        rsdmCardLocation OBJECT-TYPE
                SYNTAX  CardLocation
                ACCESS  read-only
                STATUS  mandatory
                DESCRIPTION
                        "Location of the RSDM card.  Valid values are: Local in
                         the same chassis, or remote to this chassis."
                ::= { rsdmEntry 1 }

        rsdmCardShelf    OBJECT-TYPE
                SYNTAX  CardShelf
                ACCESS  read-only
                STATUS  mandatory
                DESCRIPTION
                        "The shelf the card is in.  Valid values are: 1 to 2"
                ::= { rsdmEntry 2 }

        rsdmCardSlot     OBJECT-TYPE
                SYNTAX  SlotInput
                ACCESS  read-write
                STATUS  mandatory
                DESCRIPTION
                        "The slot within the shelf the module is in.  The range
			 of valid values range from 1 through 17 depending on
			 the chassis type and the shelf the module is in.
                         To delete this card, set this variable to 0."
                ::= { rsdmEntry 3 }

        rsdmModelNum      OBJECT-TYPE
                SYNTAX  DisplayString
                ACCESS  read-only
                STATUS  mandatory
                DESCRIPTION
                        "RSDM's model number."
                ::= { rsdmEntry 4 }

        rsdmOpticsMfgDate      OBJECT-TYPE
                SYNTAX  DateAndTime
                ACCESS  read-only
                STATUS  mandatory
                DESCRIPTION
                        "Date and Time of manufacturing of the optics on
			 the RSDM card."
                ::= { rsdmEntry 5 }

        rsdmSerialNum    OBJECT-TYPE
                SYNTAX  SerialString
                ACCESS  read-only
                STATUS  mandatory
                DESCRIPTION
                        "Serial # of the RSDM card."
                ::= { rsdmEntry 6 }

        rsdmModelType    OBJECT-TYPE
                SYNTAX  INTEGER { rsdm(16) }
                ACCESS  read-only
                STATUS  mandatory
                DESCRIPTION
                        "Model type of the RSDM."
                ::= { rsdmEntry 7 }

        rsdmHWName       OBJECT-TYPE
                SYNTAX  CardName
                ACCESS  read-only
                STATUS  mandatory
                DESCRIPTION
                        "Display Hardware name of the RSDM Card."
                ::= { rsdmEntry 8 }

        rsdmCardName     OBJECT-TYPE
                SYNTAX  CardName
                ACCESS  read-write
                STATUS  mandatory
                DESCRIPTION
                        "User configurable name of the RSDM Card."
                ::= { rsdmEntry 9 }

        rsdmFWVersionID    OBJECT-TYPE
                SYNTAX  VersionString
                ACCESS  read-only
                STATUS  mandatory
                DESCRIPTION
                        "The current version string of the RSDM FW code"
                ::= { rsdmEntry 10 }

        rsdmFWName      OBJECT-TYPE
                SYNTAX  DisplayString
                ACCESS  read-only
                STATUS  mandatory
                DESCRIPTION
                        "RSDM's Firmware Name."
                ::= { rsdmEntry 11 }

        rsdmFWDate      OBJECT-TYPE
                SYNTAX  DateAndTime
                ACCESS  read-only
                STATUS  mandatory
                DESCRIPTION
                        "Date and Time of latest Firmware of the RSDM card."
                ::= { rsdmEntry 12 }

        rsdmHWVersionID    OBJECT-TYPE
                SYNTAX  VersionString
                ACCESS  read-only
                STATUS  mandatory
                DESCRIPTION
                        "The current version string of the RSDM HW code."
                ::= { rsdmEntry 13 }

        rsdmHWDate      OBJECT-TYPE
                SYNTAX  DateAndTime
                ACCESS  read-only
                STATUS  mandatory
                DESCRIPTION
                        "Date and Time of Hardware of the RSDM card."
                ::= { rsdmEntry 14 }

        rsdmSetState      OBJECT-TYPE
                SYNTAX  RebootType
		ACCESS  read-write
                STATUS  mandatory
                DESCRIPTION
                        "Instruct the rsdm to do a warmboot. A get on this will
			 always return an other." 
                ::= { rsdmEntry 15 }

        rsdmRxITUNumber OBJECT-TYPE
                SYNTAX  INTEGER 
                ACCESS  read-only
                STATUS  mandatory
                DESCRIPTION
                        "Receive port's ITU wavelength number."
                ::= { rsdmEntry 16 }

        rsdmTxITUNumber OBJECT-TYPE
                SYNTAX  INTEGER 
                ACCESS  read-only
                STATUS  mandatory
                DESCRIPTION
                        "Transmit port's ITU wavelength number."
                ::= { rsdmEntry 17 }

        rsdmRxInsertionLoss OBJECT-TYPE
                SYNTAX  DisplayString 
                ACCESS  read-only
                STATUS  mandatory
                DESCRIPTION
                        "Receive port's insertion loss in dB."
                ::= { rsdmEntry 18 }

        rsdmTxInsertionLoss OBJECT-TYPE
                SYNTAX  DisplayString 
                ACCESS  read-only
                STATUS  mandatory
                DESCRIPTION
                        "Transmit port's insertion loss in dB."
                ::= { rsdmEntry 19 }

        rsdmExpressLoss  OBJECT-TYPE
                SYNTAX  DisplayString
		ACCESS	read-only
                STATUS  mandatory
                DESCRIPTION
                        "Insertion loss for the expressed channel
			 through the RSDM module in dB." 
                ::= { rsdmEntry 20 }

        rsdmMarginForSwitch  OBJECT-TYPE
                SYNTAX  INTEGER (-40..0)
		ACCESS  read-write
                STATUS  mandatory
                DESCRIPTION
                        "Switching threshold in dB for protection
			 switch to occur." 
                ::= { rsdmEntry 21 }

	rsdmMinProtPowerForSwitch     OBJECT-TYPE
		SYNTAX  INTEGER (-40..0)
		ACCESS  read-write
                STATUS  mandatory
                DESCRIPTION
                        "Minimum protection link's light power in dBm
			 to allow protection switching to occur." 
                ::= { rsdmEntry 22 }

        rsdmDeBounce     OBJECT-TYPE
		SYNTAX	INTEGER
		ACCESS  read-only
                STATUS  mandatory
                DESCRIPTION
                        "Debounce in number of times to measure
			 low light power before protection switch."
                ::= { rsdmEntry 23 }

        rsdmBlackOutTime   OBJECT-TYPE
		SYNTAX  INTEGER
		ACCESS  read-only
                STATUS  mandatory
                DESCRIPTION
                        "Black out time in unit of 0.1 second after
			 protection switch to allow another protection
			 switch to occur again." 
                ::= { rsdmEntry 24 }

		rsdmSwitch     OBJECT-TYPE
                SYNTAX  INTEGER { 
					other(1),
					switchToLinkA(2),
					switchToLinkB(3), 
					toggle(4),
					enableAutoSwitch(6) 
				}
                ACCESS  read-write
                STATUS  mandatory
                DESCRIPTION
                        "Instruct the RSDM to take on an action,
			 such as: switch to link A or link B.
			 A snmp get would always return other(1)."
                ::= { rsdmEntry 25 }

		rsdmPathID		OBJECT-TYPE
				SYNTAX  PathIdName
				ACCESS  read-write
                STATUS  mandatory
                DESCRIPTION
                        "Upsr Path ID name that this card is associated with.  
						 Set input equal NULL will remove the card off the path 
						 and also remove the path if there is no card left 
						 associate with that path." 
                ::= { rsdmEntry 26 }


        rsdmAdminState     OBJECT-TYPE
                SYNTAX  INTEGER
						{ disable(1),
						  enable(2),
						  na(3)
						}
                ACCESS  read-write
                STATUS  mandatory
                DESCRIPTION
                        "Administrative control over that rsdm card. Default value is enable.
						 When disabled, no alarms/events gets
						 generated."
                ::= { rsdmEntry 27 }

		rsdmPortTable	OBJECT-TYPE
                SYNTAX  SEQUENCE OF RsdmPortEntry
                ACCESS  not-accessible
                STATUS  mandatory
                DESCRIPTION
                        "This table represents the physical connection for each
                         RSDM card's port."
                ::= { rsdm 7 }

        rsdmPortEntry	OBJECT-TYPE
                SYNTAX  RsdmPortEntry
                ACCESS  not-accessible
                STATUS  mandatory
                DESCRIPTION
                        "Specifies the index for each row in the table below"
                INDEX { rsdmPortCardShelf, rsdmPortCardSlot, rsdmPortType }
                ::= { rsdmPortTable 1 }

        RsdmPortEntry        ::=
                SEQUENCE 
				{
						rsdmPortCardShelf		CardShelf,
						rsdmPortCardSlot		SlotInput,
						rsdmPortType			INTEGER,
						rsdmConnCardType		CardType,
						rsdmConnPort			INTEGER,
						rsdmConnShelf			ShelfInput,
                        rsdmConnSlot			SlotInput						
				}

        rsdmPortCardShelf    OBJECT-TYPE
                SYNTAX  CardShelf
                ACCESS  read-only 
                STATUS  mandatory
                DESCRIPTION
                        "The shelf the card is in.  Valid values are: 1 to 2."
                ::= { rsdmPortEntry 1 }

        rsdmPortCardSlot     OBJECT-TYPE
                SYNTAX  SlotInput
                ACCESS  read-only 
                STATUS  mandatory
                DESCRIPTION
                        "The slot within the shelf the card is in."
                ::= { rsdmPortEntry 2 }

		rsdmPortType		OBJECT-TYPE 
                SYNTAX  INTEGER { 
								  linkEast(1), 
								  linkWest(2), 
								  linkRx(3),
								  linkTx(4) 
								}
                ACCESS  read-only
                STATUS  mandatory
                DESCRIPTION
                        "Type of the RSDM's port.  The order is CLI compatible."
                ::= { rsdmPortEntry 3 }

        rsdmConnCardType      OBJECT-TYPE
                SYNTAX  CardType
                ACCESS  read-write
                STATUS  mandatory
                DESCRIPTION
                        "Type of connection.  Valid values are ocmu(2),
			 ocmItu(3), mux(4), demux(5), mcm(8), w4cd(10), w2cmd(13), w4cm(21),
			 osam(20), fadm(6), oppm(7), fadmb(19), ocme(24), etc...
			 A zero will be used for no connections."
                ::= { rsdmPortEntry 4}

        rsdmConnPort    OBJECT-TYPE
                SYNTAX  INTEGER
                ACCESS  read-write
                STATUS  mandatory
                DESCRIPTION
                        "Conn port for RSDM's port.Possible values based on 
				 card types that can connect to RSDM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM: 1=Link Tx, 2=Link Rx 
				 UPSM/OPPM: 1=Link A Tx, 2=Link A Rx, 3=Link B Tx,
				 4=Link B Rx, 5=Local Tx, 6=Local Rx "
						 
                ::= { rsdmPortEntry 5 }

        rsdmConnShelf   OBJECT-TYPE
                SYNTAX  ShelfInput
                ACCESS  read-write
                STATUS  mandatory
                DESCRIPTION
                        "The shelf the card conn to. Valid values are: 1 to 2."
                ::= { rsdmPortEntry 6 }

        rsdmConnSlot     OBJECT-TYPE
                SYNTAX  SlotInput
                ACCESS  read-write
                STATUS  mandatory
                DESCRIPTION
                        "The slot within the shelf the card conn to."
                ::= { rsdmPortEntry 7 }


        -- The elements in the rtdm subgroup of the configuration group

        rtdmBootPromVer  OBJECT-TYPE
                SYNTAX  VersionString
                ACCESS  read-only
                STATUS  mandatory
                DESCRIPTION
                        "The current version string of the RTDM Boot PROM code"
                ::= { rtdm 1 }

        rtdmROMSize      OBJECT-TYPE
                SYNTAX  INTEGER (0..1024)
                ACCESS  read-only
                STATUS  mandatory
                DESCRIPTION
                        "Total Size of the ROM in Kilobyes"
                ::= { rtdm 2 }

        rtdmNumSubDiv    OBJECT-TYPE
                SYNTAX  INTEGER (0..20)
                ACCESS  read-only
                STATUS  mandatory
                DESCRIPTION
                        "Number of the subdivisions of the ROM."
                ::= { rtdm 3 }

        rtdmSubDivTable  OBJECT-TYPE
                SYNTAX  SEQUENCE OF RtdmSubDivEntry
                ACCESS  not-accessible
                STATUS  mandatory
                DESCRIPTION
                        "This table represents the number of sub divisions
                         and the size of each subdivision in ROM memory"
                ::= { rtdm 4 }

        rtdmSubDivEntry  OBJECT-TYPE
                SYNTAX  RtdmSubDivEntry
                ACCESS  not-accessible
                STATUS  mandatory
                DESCRIPTION
                        "Specifies the index for each row in the table below"
                INDEX { rtdmSubDivIndex }
                ::= { rtdmSubDivTable 1 }

        RtdmSubDivEntry  ::=
                SEQUENCE {
                        rtdmSubDivIndex  INTEGER,
                        rtdmSubDivDescr  DisplayString,
                        rtdmSubDivSize   INTEGER,
                        rtdmSubDivOffset OCTET STRING
                }

        rtdmSubDivIndex  OBJECT-TYPE
                SYNTAX  INTEGER (0..20)
                ACCESS  read-only
                STATUS  mandatory
                DESCRIPTION
                        "Integer ID of each sub division in the ROM.  The order
                         of numbering is from the top of the ROM to the bottom
                         of the ROM."
                ::= { rtdmSubDivEntry 1 }

        rtdmSubDivDescr  OBJECT-TYPE
                SYNTAX  DisplayString (SIZE (0..20))
                ACCESS  read-only
                STATUS  mandatory
                DESCRIPTION
                        "Display Name of each Sub Division in ROM"
                ::= { rtdmSubDivEntry 2 }

        rtdmSubDivSize   OBJECT-TYPE
                SYNTAX  INTEGER (0..1024)
                ACCESS  read-only
                STATUS  mandatory
                DESCRIPTION
                        "Size of each sub division in ROM in kilobytes"
                ::= { rtdmSubDivEntry 3 }

        rtdmSubDivOffset OBJECT-TYPE
                SYNTAX  OCTET STRING (SIZE (0..8))
                ACCESS  read-only
                STATUS  mandatory
                DESCRIPTION
                        "Starting address of each sub division in the ROM
                         in HEX notation."
                ::= { rtdmSubDivEntry 4 }

        rtdmNumber       OBJECT-TYPE
                SYNTAX  INTEGER
                ACCESS  read-only
                STATUS  mandatory
                DESCRIPTION
                        "Number of RTDM rows in the following table.  This number
                         is automatically updated whenever a new row is added
                         to the table below."
                ::= { rtdm 5 }

        rtdmTable        OBJECT-TYPE
                SYNTAX  SEQUENCE OF RtdmEntry
                ACCESS  not-accessible
                STATUS  mandatory
                DESCRIPTION
                        "This table represents the information for each
                         RTDM card"
                ::= { rtdm 6 }

        rtdmEntry        OBJECT-TYPE
                SYNTAX  RtdmEntry
                ACCESS  not-accessible
                STATUS  mandatory
                DESCRIPTION
                        "Specifies the index for each row in the table below"
                INDEX { rtdmCardLocation, rtdmCardShelf, rtdmCardSlot }
                ::= { rtdmTable 1 }

        RtdmEntry        ::=
                SEQUENCE {
                        rtdmCardLocation		CardLocation,
                        rtdmCardShelf			CardShelf,
                        rtdmCardSlot			INTEGER,
                        rtdmModelNum			DisplayString,
                        rtdmOpticsMfgDate		DateAndTime,
                        rtdmSerialNum			SerialString,
                        rtdmModelType			INTEGER,
                        rtdmHWName			CardName,
                        rtdmFWVersionID			VersionString,
			rtdmCardName			CardName,
			rtdmFWName			DisplayString,
			rtdmFWDate			DateAndTime,
			rtdmHWVersionID			VersionString,
			rtdmHWDate			DateAndTime,
                        rtdmSetState			RebootType,
			rtdmCommonEInsertionLoss	DisplayString,
			rtdmCommonWInsertionLoss	DisplayString,
			rtdmMonEastInsertionLoss	DisplayString,
			rtdmMonWestInsertionLoss	DisplayString,
			rtdmPathID					PathIdName,
			rtdmAdminState				INTEGER
                }

        rtdmCardLocation OBJECT-TYPE
                SYNTAX  CardLocation
                ACCESS  read-only
                STATUS  mandatory
                DESCRIPTION
                        "Location of the RTDM card.  Valid values are: Local in
                         the same chassis, or remote to this chassis"
                ::= { rtdmEntry 1 }

        rtdmCardShelf    OBJECT-TYPE
                SYNTAX  CardShelf
                ACCESS  read-only
                STATUS  mandatory
                DESCRIPTION
                        "The shelf the card is in.  Valid values are: 1 to 10"
                ::= { rtdmEntry 2 }

        rtdmCardSlot     OBJECT-TYPE
                SYNTAX  SlotInput
                ACCESS  read-write
                STATUS  mandatory
                DESCRIPTION
                        "The slot within the shelf the module is in.  The range
			 of valid values range from 1 through 17 depending on
			 the chassis type and the shelf the module is in.
                         To delete this card, set this variable to 0."
                ::= { rtdmEntry 3 }

        rtdmModelNum      OBJECT-TYPE
                SYNTAX  DisplayString
                ACCESS  read-only
                STATUS  mandatory
                DESCRIPTION
                        "Model number for RTDM."  
                ::= { rtdmEntry 4 }

        rtdmOpticsMfgDate      OBJECT-TYPE
                SYNTAX  DateAndTime
                ACCESS  read-only
                STATUS  mandatory
                DESCRIPTION
                        "Date and Time of manufacturing of the optics
			 on the RTDM card"
                ::= { rtdmEntry 5 }

        rtdmSerialNum    OBJECT-TYPE
                SYNTAX  SerialString
                ACCESS  read-only
                STATUS  mandatory
                DESCRIPTION
                        "Serial # of the RTDM card."
                ::= { rtdmEntry 6 }

        rtdmModelType    OBJECT-TYPE
                SYNTAX  INTEGER { rtdm(18) }
                ACCESS  read-only
                STATUS  mandatory
                DESCRIPTION
                        "Model type of the RTDM"
                ::= { rtdmEntry 7 }

        rtdmHWName       OBJECT-TYPE
                SYNTAX  CardName
                ACCESS  read-only
                STATUS  mandatory
                DESCRIPTION
                        "Display (Network) name of the RTDM Card"
                ::= { rtdmEntry 8 }

	rtdmFWVersionID    OBJECT-TYPE
                SYNTAX  VersionString
                ACCESS  read-only
                STATUS  mandatory
                DESCRIPTION
                        "The current version string of the RTDM FW code"
                ::= { rtdmEntry 9 }

	rtdmCardName     OBJECT-TYPE
                SYNTAX  CardName
		ACCESS  read-write
                STATUS  mandatory
                DESCRIPTION
                        "User configurable card name." 
                ::= { rtdmEntry 10 }

	rtdmFWName      OBJECT-TYPE
                SYNTAX  DisplayString
                ACCESS  read-only
                STATUS  mandatory
                DESCRIPTION
                        "RTDM's Firmware Name."
                ::= { rtdmEntry 11 }

        rtdmFWDate      OBJECT-TYPE
                SYNTAX  DateAndTime
                ACCESS  read-only
                STATUS  mandatory
                DESCRIPTION
                        "Date and Time of latest Firmware of the RTDM card"
                ::= { rtdmEntry 12 }

        rtdmHWVersionID    OBJECT-TYPE
                SYNTAX  VersionString
                ACCESS  read-only
                STATUS  mandatory
                DESCRIPTION
                        "The current version string of the RTDM HW code"
                ::= { rtdmEntry 13 }

        rtdmHWDate      OBJECT-TYPE
                SYNTAX  DateAndTime
                ACCESS  read-only
                STATUS  mandatory
                DESCRIPTION
                        "Date and Time of Hardware of the RTDM card"
                ::= { rtdmEntry 14 }

        rtdmSetState      OBJECT-TYPE
                SYNTAX  RebootType
		ACCESS  read-write
                STATUS  mandatory
                DESCRIPTION
                        "Instruct the rtdm to do a warmboot. A get on this will
			 always return an other." 
                ::= { rtdmEntry 15 }

        rtdmCommonEInsertionLoss  OBJECT-TYPE
                SYNTAX  DisplayString
                ACCESS  read-only
                STATUS  mandatory
                DESCRIPTION
                        "The RTDM Common path East's insertion loss in dB."
                ::= { rtdmEntry 16 }

        rtdmCommonWInsertionLoss  OBJECT-TYPE
                SYNTAX  DisplayString
                ACCESS  read-only
                STATUS  mandatory
                DESCRIPTION
                        "The RTDM Common path West's insertion loss in dB."
                ::= { rtdmEntry 17 }

        rtdmMonEastInsertionLoss    OBJECT-TYPE
                SYNTAX  DisplayString
                ACCESS  read-only
                STATUS  mandatory
                DESCRIPTION
                        "The RTDM Monitor East Path's insertion loss
			 in dB."
                ::= { rtdmEntry 18 }

        rtdmMonWestInsertionLoss    OBJECT-TYPE
                SYNTAX  DisplayString
                ACCESS  read-only
                STATUS  mandatory
                DESCRIPTION
                        "The RTDM Monitor West Path's insertion loss
			 in dB."
                ::= { rtdmEntry 19 }

		rtdmPathID		OBJECT-TYPE
                SYNTAX  PathIdName
                ACCESS  read-write
                STATUS  mandatory
                DESCRIPTION
                        "Upsr Path ID name that this card is associated with.  
						 Set input equal NULL will remove the card off the path 
						 and also remove the path if there is no card left 
						 associate with that path."
                ::= { rtdmEntry 20 }

        rtdmAdminState     OBJECT-TYPE
                SYNTAX  INTEGER
						{ disable(1),
						  enable(2),
						  na(3)
						}
                ACCESS  read-write
                STATUS  mandatory
                DESCRIPTION
                        "Administrative control over that rtdm card. Default value is enable.
						 When disabled, no alarms/events gets
						 generated."
                ::= { rtdmEntry 21 }

		rtdmPortTable	OBJECT-TYPE
                SYNTAX  SEQUENCE OF RtdmPortEntry
                ACCESS  not-accessible
                STATUS  mandatory
                DESCRIPTION
                        "This table represents the physical connection for each
                         RTDM card's port."
                ::= { rtdm 7 }

        rtdmPortEntry	OBJECT-TYPE
                SYNTAX  RtdmPortEntry
                ACCESS  not-accessible
                STATUS  mandatory
                DESCRIPTION
                        "Specifies the index for each row in the table below"
                INDEX { rtdmPortCardShelf, rtdmPortCardSlot, rtdmPortType }
                ::= { rtdmPortTable 1 }

        RtdmPortEntry        ::=
                SEQUENCE 
				{
						rtdmPortCardShelf		CardShelf,
						rtdmPortCardSlot		SlotInput,
						rtdmPortType			INTEGER,
						rtdmConnCardType		INTEGER,
						rtdmConnPort			INTEGER,
						rtdmConnShelf			ShelfInput,
                        rtdmConnSlot			SlotInput						
				}

        rtdmPortCardShelf    OBJECT-TYPE
                SYNTAX  CardShelf
                ACCESS  read-only 
                STATUS  mandatory
                DESCRIPTION
                        "The shelf the card is in.  Valid values are: 1 to 2."
                ::= { rtdmPortEntry 1 }

        rtdmPortCardSlot     OBJECT-TYPE
                SYNTAX  SlotInput
                ACCESS  read-only 
                STATUS  mandatory
                DESCRIPTION
                        "The slot within the shelf the card is in."
                ::= { rtdmPortEntry 2 }

		rtdmPortType		OBJECT-TYPE 
                SYNTAX  INTEGER { 
								  localRx(1)
								}
                ACCESS  read-only
                STATUS  mandatory
                DESCRIPTION
                        "Type of the RTDM's port.  The order is CLI compatible."
                ::= { rtdmPortEntry 3 }

        rtdmConnCardType      OBJECT-TYPE
                SYNTAX  INTEGER (0..30)
                ACCESS  read-write
                STATUS  mandatory
                DESCRIPTION
                        "Type of connection.  Valid values are ocmu(2),
			 ocmItu(3), mux(4), demux(5), mcm(8), w4cd(10), w2cmd(13), w4cm(21),
			 osam(20), fadm(6), oppm(7), fadmb(19), ocme(24), etc..."
                ::= { rtdmPortEntry 4}

        rtdmConnPort    OBJECT-TYPE
                SYNTAX  INTEGER
                ACCESS  read-write
                STATUS  mandatory
                DESCRIPTION
                        "Conn port for RTDM's port.Possible values based on 
				 card types that can connect to RTDM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM: 1=Link Tx, 2=Link Rx 
				 UPSM/OPPM: 1=Link A Tx, 2=Link A Rx, 3=Link B Tx,
				 4=Link B Rx, 5=Local Tx, 6=Local Rx "
						 
                ::= { rtdmPortEntry 5 }

        rtdmConnShelf   OBJECT-TYPE
                SYNTAX  ShelfInput
                ACCESS  read-write
                STATUS  mandatory
                DESCRIPTION
                        "The shelf the card conn to. Valid values are: 1 to 2."
                ::= { rtdmPortEntry 6 }

        rtdmConnSlot     OBJECT-TYPE
                SYNTAX  SlotInput
                ACCESS  read-write
                STATUS  mandatory
                DESCRIPTION
                        "The slot within the shelf the card conn to.
						 A zero will be used for no connections."

                ::= { rtdmPortEntry 7 }


        -- The elements in the osam subgroup of the configuration group

        osamBootPromVer  OBJECT-TYPE
                SYNTAX  VersionString
                ACCESS  not-accessible
                STATUS  mandatory
                DESCRIPTION
                        "The current version string of the osam boot prom code."
                ::= { osam 1 }

        osamROMSize      OBJECT-TYPE
                SYNTAX  INTEGER (0..1024)
                ACCESS  not-accessible
                STATUS  mandatory
                DESCRIPTION
                        "Total Size of the ROM in Kilobytes."
                ::= { osam 2 }

        osamNumSubDiv    OBJECT-TYPE
                SYNTAX  INTEGER (0..20)
                ACCESS  not-accessible
                STATUS  mandatory
                DESCRIPTION
                        "Number of the ROM's subdivisions."
                ::= { osam 3 }

        osamSubDivTable  OBJECT-TYPE
                SYNTAX  SEQUENCE OF OsamSubDivEntry
                ACCESS  not-accessible
                STATUS  mandatory
                DESCRIPTION
                        "This table represents the number of sub divisions
                         and the size of each subdivision in ROM memory"
                ::= { osam 4 }

        osamSubDivEntry  OBJECT-TYPE
                SYNTAX  OsamSubDivEntry
                ACCESS  not-accessible
                STATUS  mandatory
                DESCRIPTION
                        "Specifies the index for each row in the table below"
                INDEX { osamSubDivIndex }
                ::= { osamSubDivTable 1 }

        OsamSubDivEntry  ::=
                SEQUENCE {
                        osamSubDivIndex  INTEGER,
                        osamSubDivDescr  DisplayString,
                        osamSubDivSize   INTEGER,
                        osamSubDivOffset OCTET STRING
                }

        osamSubDivIndex  OBJECT-TYPE
                SYNTAX  INTEGER (0..20)
                ACCESS  not-accessible
                STATUS  mandatory
                DESCRIPTION
                        "Integer ID of each subdivision."
                ::= { osamSubDivEntry 1 }

        osamSubDivDescr  OBJECT-TYPE
                SYNTAX  DisplayString (SIZE (0..20))
                ACCESS  not-accessible
                STATUS  mandatory
                DESCRIPTION
                        "Display name of each subdivision."
                ::= { osamSubDivEntry 2 }

        osamSubDivSize   OBJECT-TYPE
                SYNTAX  INTEGER (0..1024)
                ACCESS  not-accessible
                STATUS  mandatory
                DESCRIPTION
                        "Size of each subdivision in Kbytes."
                ::= { osamSubDivEntry 3 }

        osamSubDivOffset OBJECT-TYPE
                SYNTAX  OCTET STRING (SIZE (0..8))
                ACCESS  not-accessible
                STATUS  mandatory
                DESCRIPTION
                        "Starting address of each sub division in HEX
                         format."
                ::= { osamSubDivEntry 4 }

        osamNumber       OBJECT-TYPE
                SYNTAX  INTEGER (0..32)
                ACCESS  read-only
                STATUS  mandatory
                DESCRIPTION
                        "Number of rows in the osam table."
                ::= { osam 5 }

        osamTable        OBJECT-TYPE
                SYNTAX  SEQUENCE OF OsamEntry
                ACCESS  not-accessible
                STATUS  mandatory
                DESCRIPTION
                        "This table represents the information for each
                         osam card"
                ::= { osam 6 }

        osamEntry        OBJECT-TYPE
                SYNTAX  OsamEntry
                ACCESS  not-accessible
                STATUS  mandatory
                DESCRIPTION
                        "Specifies the index for each row in the table below"
                INDEX { osamCardLocation, osamCardShelf, osamCardSlot }
                ::= { osamTable 1 }

        OsamEntry        ::=
                SEQUENCE {
                        osamCardLocation		CardLocation,
                        osamCardShelf			CardShelf,
                        osamCardSlot			INTEGER,
                        osamModelNum            ModelNum,
                        osamSerialNum			SerialString,
                        osamModelType			CardType,
                        osamHWName				CardName,
                        osamHWVersionID			VersionString,
                        osamHWDate				DateAndTime,
                        osamFWName				CardName,
                        osamFWVersionID			VersionString,
                        osamFWDate				DateAndTime,
						osamCardName			CardName,
                        osamSetState			RebootType,
						osamLaserState			FlagType,
						osamOperationMode		INTEGER,
						osamLaserBiasCurrent    INTEGER,
						osamAmplifierGain		INTEGER,
						osamConfigCommit		INTEGER,
						osamNoiseFigure			INTEGER,
						osamPathID				PathIdName,
						osamAdminState			INTEGER,
						osam2NoiseFigure		DisplayString,
						osam2GainReq			DisplayString,
						osam2OpPowerReq			DisplayString
                }

        osamCardLocation OBJECT-TYPE
                SYNTAX  CardLocation
                ACCESS  read-only
                STATUS  mandatory
                DESCRIPTION
                        "Location of the module."
                ::= { osamEntry 1 }

        osamCardShelf    OBJECT-TYPE
                SYNTAX  CardShelf
                ACCESS  read-only
                STATUS  mandatory
                DESCRIPTION
                        "The shelf number in which the module is plugged in."
                ::= { osamEntry 2 }

        osamCardSlot     OBJECT-TYPE
                SYNTAX  INTEGER (0..16)
                ACCESS  read-write
                STATUS  mandatory
                DESCRIPTION
                        "The slot number in which the module is plugged in.
                         If a 0 is written into this mib element, the module
                         will be deleted from the system."
                ::= { osamEntry 3 }

        osamModelNum    OBJECT-TYPE
                SYNTAX  ModelNum
                ACCESS  read-only
                STATUS  mandatory
                DESCRIPTION
                        "Manufacturing model number of the module."
                ::= { osamEntry 4 }

        osamSerialNum    OBJECT-TYPE
                SYNTAX  SerialString
                ACCESS  read-only
                STATUS  mandatory
                DESCRIPTION
                        "Unique serial number of the module."
                ::= { osamEntry 5 }

        osamModelType    OBJECT-TYPE
                SYNTAX  CardType
                ACCESS  read-only
                STATUS  mandatory
                DESCRIPTION
                        "Model type of the module."
                ::= { osamEntry 6 }

        osamHWName       OBJECT-TYPE
                SYNTAX  CardName
                ACCESS  read-only
                STATUS  mandatory
                DESCRIPTION
                        "Manufacturing Hardware name of the module."
                ::= { osamEntry 7 }

	osamHWVersionID    OBJECT-TYPE
                SYNTAX  VersionString
                ACCESS  read-only
                STATUS  mandatory
                DESCRIPTION
                        "The current hardware version string of the module."
                ::= { osamEntry 8 }

        osamHWDate  OBJECT-TYPE
                SYNTAX  DateAndTime
                ACCESS  read-only
                STATUS  mandatory
                DESCRIPTION
                        "Date of manufacturing of the electronics portion of 
                         the module."
                ::= { osamEntry 9 }

        osamFWName       OBJECT-TYPE
                SYNTAX  CardName
                ACCESS  read-only
                STATUS  mandatory
                DESCRIPTION
                        "Manufacturing Firmware name of the module."
                ::= { osamEntry 10 }

	osamFWVersionID    OBJECT-TYPE
                SYNTAX  VersionString
                ACCESS  read-only
                STATUS  mandatory
                DESCRIPTION
                        "The current firmware version string of the module."
                ::= { osamEntry 11 }

        osamFWDate  OBJECT-TYPE
                SYNTAX  DateAndTime
                ACCESS  read-only
                STATUS  mandatory
                DESCRIPTION
                        "Release date for the firmware of the module."
                ::= { osamEntry 12 }

	osamCardName     OBJECT-TYPE
                SYNTAX  CardName
				ACCESS  read-write
                STATUS  mandatory
                DESCRIPTION
                        "User configurable card name for the module." 
                ::= { osamEntry 13 }

        osamSetState      OBJECT-TYPE
                SYNTAX  RebootType
				ACCESS  read-write
                STATUS  mandatory
                DESCRIPTION
                        "Instruct the osam module to do a reset.
                         A get on this will always return other."
                ::= { osamEntry 14 }

	osamLaserState     OBJECT-TYPE
                SYNTAX  FlagType
				ACCESS  read-only
                STATUS  mandatory
                DESCRIPTION
                        "The operational state of the laser." 
                ::= { osamEntry 15 }

		osamOperationMode     OBJECT-TYPE
                SYNTAX  INTEGER { currentControlled(1), gainControlled(2),
								  powerControlled(3) }
				ACCESS  read-write
                STATUS  mandatory
                DESCRIPTION
                        "Operation mode of the module." 
                ::= { osamEntry 16 }

        osamLaserBiasCurrent       OBJECT-TYPE
                SYNTAX  INTEGER (40..200)
                ACCESS  read-write
                STATUS  mandatory
                DESCRIPTION
                        "Constant current in mA to be used by the module when 
                         the operation mode is set to currentControlled. This 
                         value can't be set if operation mode is set to 
                         gainControlled.
						 Applicable only to OSAM module"
                ::= { osamEntry 17 }

        osamAmplifierGain       OBJECT-TYPE
                SYNTAX  INTEGER (0..30)
                ACCESS  read-write
                STATUS  mandatory
                DESCRIPTION
                        "Constant gain in dB to be used by the module when the 
                         operation mode is set to gainControlled. This value
                         can't be set if operation mode is set to 
                         currentControlled.
						 Not applicable to OSAM-HP/LP module"
                ::= { osamEntry 18 }

        osamConfigCommit       OBJECT-TYPE
                SYNTAX  INTEGER { other(1), save(2) }
                ACCESS  read-write
                STATUS  mandatory
                DESCRIPTION
                        "This allows the current module configuration to be
                         stored in permanent storage."
                ::= { osamEntry 19 }

        osamNoiseFigure       OBJECT-TYPE
                SYNTAX  INTEGER (0..10)
                ACCESS  read-only
                STATUS  mandatory
                DESCRIPTION
                        "The calibrated noise figure of the gain block in dB.
						 Applicable only to OSAM module"
                ::= { osamEntry 20 }

		osamPathID		OBJECT-TYPE
				SYNTAX  PathIdName
				ACCESS  read-write
                STATUS  mandatory
                DESCRIPTION
                        "Upsr Path ID name that this card is associated with.  
						 Set input equal NULL will remove the card off the path 
						 and also remove the path if there is no card left 
						 associate with that path." 
                ::= { osamEntry 21 }

        osamAdminState     OBJECT-TYPE
                SYNTAX  INTEGER
						{ disable(1),
						  enable(2),
						  na(3)
						}
                ACCESS  read-write
                STATUS  mandatory
                DESCRIPTION
                        "Administrative control over that osam card. Default value is enable.
						 When disabled, no alarms/events gets
						 generated."
                ::= { osamEntry 22 }

        osam2NoiseFigure  OBJECT-TYPE
                SYNTAX  DisplayString
                ACCESS  read-only
                STATUS  mandatory
                DESCRIPTION
                        "The calibrated noise figure of the gain block in dBm.
						 Applicable only to OSAM-HP/LP module"
                ::= { osamEntry 23 }

        osam2GainReq       OBJECT-TYPE
                SYNTAX  DisplayString
                ACCESS  read-write
                STATUS  mandatory
                DESCRIPTION
                        "Constant gain in dB to be used by the module when the 
                         operation mode is set to gainControlled. This value
                         can't be set if operation mode is set to 
                         powerControlled. Range is 0-16.5db(LP) and 0-23.3db(HP)
						 Applicable only to OSAM-HP/LP module"
                ::= { osamEntry 24 }

        osam2OpPowerReq       OBJECT-TYPE
                SYNTAX  DisplayString
                ACCESS  read-write
                STATUS  mandatory
                DESCRIPTION
                        "Constant output power in dBm to be used by the module when the 
                         operation mode is set to powerControlled. This value
                         can't be set if operation mode is set to 
                         gainControlled. Range is 0-9dbm (LP) and 0-18dbm(HP) 
						 Applicable only to OSAM-HP/LP module"
                ::= { osamEntry 25 }

        osamPortTable        OBJECT-TYPE
                SYNTAX  SEQUENCE OF OsamPortEntry
                ACCESS  not-accessible
                STATUS  mandatory
                DESCRIPTION
                        "This table represents the physical connection for each
                         OSAM card's port."
                ::= { osam 7 }

        osamPortEntry        OBJECT-TYPE
                SYNTAX  OsamPortEntry
                ACCESS  not-accessible
                STATUS  mandatory
                DESCRIPTION
                        "Specifies the index for each row in the table below"
                INDEX { osamPortCardShelf, osamPortCardSlot, osamPortType }
                ::= { osamPortTable 1 }

        OsamPortEntry        ::=
                SEQUENCE {
						osamPortCardShelf		CardShelf,
						osamPortCardSlot		INTEGER,
						osamPortType			INTEGER,
						osamConnCardType		INTEGER,
                        osamConnPort			INTEGER,
                        osamConnShelf		INTEGER,
                        osamConnSlot		INTEGER,
						osamPortCardType	CardType
						}


        osamPortCardShelf    OBJECT-TYPE
                SYNTAX  CardShelf
                ACCESS  read-only 
                STATUS  mandatory
                DESCRIPTION
                        "The shelf the card is in.  Valid values are: 1 to 2."
                ::= { osamPortEntry 1 }

        osamPortCardSlot     OBJECT-TYPE
                SYNTAX  SlotInput
                ACCESS  read-only 
                STATUS  mandatory
                DESCRIPTION
                        "The slot within the shelf the card is in."
                ::= { osamPortEntry 2 }

		osamPortType		OBJECT-TYPE 
                SYNTAX  INTEGER { 
								  in(1), 
								  out(2) 
								}
                ACCESS  read-write
                STATUS  mandatory
                DESCRIPTION
                        "Type of the OSAM's port."
                ::= { osamPortEntry 3 }



        osamConnCardType      OBJECT-TYPE
                SYNTAX  INTEGER (0..30)
                ACCESS  read-write
                STATUS  mandatory
                DESCRIPTION
                        "Type of connection.  Valid values are ocmu(2),
			 ocmItu(3), ocm10g(27), mux(4), demux(5), mcm(8), w4cd(10), w2cmd(13), w4cm(21),
			 fadm(6), oppm(7), fadmb(19), ocme(24), etc...
			 A zero will be used for no connections."
                ::= { osamPortEntry 4}

        osamConnPort    OBJECT-TYPE
                SYNTAX  INTEGER
                ACCESS  read-write
                STATUS  mandatory
                DESCRIPTION
                        "Conn port for OSAM's port.Possible values based on 
				 card types that can connect to OSAM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM/OCM10G: 1=Link Tx, 2=Link Rx "
						 
                ::= { osamPortEntry 5 }

        osamConnShelf    OBJECT-TYPE
                SYNTAX  ShelfInput
                ACCESS  read-write
                STATUS  mandatory
                DESCRIPTION
                        "The shelf the card conn to. Valid values are: 1 to 2." 
                ::= { osamPortEntry 6 }

        osamConnSlot     OBJECT-TYPE
                SYNTAX  SlotInput
                ACCESS  read-write
                STATUS  mandatory
                DESCRIPTION
                        "The slot within the shelf the card conn to."
                ::= { osamPortEntry 7 }

        osamPortCardType      OBJECT-TYPE
                SYNTAX  CardType
                ACCESS  read-only
                STATUS  mandatory
                DESCRIPTION
                        "Type of OSAM module."
                ::= { osamPortEntry 8}



-- The elements in the rsm subgroup of the configuration group

        rsmBootPromVer  OBJECT-TYPE
                SYNTAX  VersionString
                ACCESS  not-accessible
                STATUS  mandatory
                DESCRIPTION
                        "The current version string of the rsm
			 Boot PROM code"
                ::= { rsm 1 }

        rsmROMSize      OBJECT-TYPE
                SYNTAX  INTEGER (0..1024)
                ACCESS  not-accessible
                STATUS  mandatory
                DESCRIPTION
                        "Total Size of the ROM in Kilobyes"
                ::= { rsm 2 }

        rsmNumSubDiv    OBJECT-TYPE
                SYNTAX  INTEGER (0..20)
                ACCESS  not-accessible
                STATUS  mandatory
                DESCRIPTION
                        "Number of the subdivisions of the ROM."
                ::= { rsm 3 }

        rsmSubDivTable  OBJECT-TYPE
                SYNTAX  SEQUENCE OF RsmSubDivEntry
                ACCESS  not-accessible
                STATUS  mandatory
                DESCRIPTION
                        "This table represents the number of sub divisions
                         and the size of each subdivision in ROM memory"
                ::= { rsm 4 }

        rsmSubDivEntry  OBJECT-TYPE
                SYNTAX  RsmSubDivEntry
                ACCESS  not-accessible
                STATUS  mandatory
                DESCRIPTION
                        "Specifies the index for each row in the table below"
                INDEX { rsmSubDivIndex }
                ::= { rsmSubDivTable 1 }

        RsmSubDivEntry  ::=
                SEQUENCE {
                        rsmSubDivIndex  INTEGER,
                        rsmSubDivDescr  DisplayString,
                        rsmSubDivSize   INTEGER,
                        rsmSubDivOffset OCTET STRING
                }

        rsmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { rsmSubDivEntry 1 }

        rsmSubDivDescr  OBJECT-TYPE
                SYNTAX  DisplayString (SIZE (0..20))
                ACCESS  not-accessible
                STATUS  mandatory
                DESCRIPTION
                        "Display Name of each Sub Division in ROM"
                ::= { rsmSubDivEntry 2 }

        rsmSubDivSize   OBJECT-TYPE
                SYNTAX  INTEGER (0..1024)
                ACCESS  not-accessible
                STATUS  mandatory
                DESCRIPTION
                        "Size of each sub division in ROM in kilobytes"
                ::= { rsmSubDivEntry 3 }

        rsmSubDivOffset OBJECT-TYPE
                SYNTAX  OCTET STRING (SIZE (0..8))
                ACCESS  not-accessible
                STATUS  mandatory
                DESCRIPTION
                        "Starting address of each sub division in the ROM
                         in HEX notation."
                ::= { rsmSubDivEntry 4 }

        rsmNumber       OBJECT-TYPE
                SYNTAX  INTEGER
                ACCESS  read-only
                STATUS  mandatory
                DESCRIPTION
                        "Number of RSM rows in the following table.  This 
                         number is automatically updated whenever a new row is 
                         added to the table below."
                ::= { rsm 5 }

        rsmTable        OBJECT-TYPE
                SYNTAX  SEQUENCE OF RsmEntry
                ACCESS  not-accessible
                STATUS  mandatory
                DESCRIPTION
                        "This table represents the information for each
                         RSM card"
                ::= { rsm 6 }

        rsmEntry        OBJECT-TYPE
                SYNTAX  RsmEntry
                ACCESS  not-accessible
                STATUS  mandatory
                DESCRIPTION
                        "Specifies the index for each row in the table below"
                INDEX { rsmCardLocation, rsmCardShelf, rsmCardSlot }
                ::= { rsmTable 1 }

        RsmEntry        ::=
                SEQUENCE {
                        rsmCardLocation			CardLocation,
                        rsmCardShelf			CardShelf,
                        rsmCardSlot				SlotInput,
						rsmModelNum				DisplayString,
                        rsmOpticsMfgDate		DateAndTime,
                        rsmSerialNum			SerialString,
                        rsmModelType			INTEGER,
						rsmHWName				CardName,
						rsmCardName				CardName,
						rsmFWName				DisplayString,			
						rsmFWVersionID			VersionString,
						rsmFWDate				DateAndTime,
                        rsmSetState				RebootType,
						rsmRxInsertionLoss		DisplayString,
						rsmRxComInsertionLoss	DisplayString,
						rsmWorkingWavelength	INTEGER,
						rsmLinkAPathID			PathIdName,
						rsmLinkBPathID			PathIdName,
						rsmAdminState			INTEGER						
                }

        rsmCardLocation OBJECT-TYPE
                SYNTAX  CardLocation
                ACCESS  read-only
                STATUS  mandatory
                DESCRIPTION
                        "Location of the RSM card.  Valid values are: Local in
                         the same chassis."
                ::= { rsmEntry 1 }

        rsmCardShelf    OBJECT-TYPE
                SYNTAX  CardShelf
                ACCESS  read-only
                STATUS  mandatory
                DESCRIPTION
                        "The shelf the card is in.  Valid values are: 1 to 2."
                ::= { rsmEntry 2 }

        rsmCardSlot     OBJECT-TYPE
                SYNTAX  SlotInput
                ACCESS  read-write
                STATUS  mandatory
                DESCRIPTION
                        "The slot within the shelf the module is in.  The range
						 of valid values range from 1 through 17 depending on
						 the chassis type and the shelf the module is in.
                         To delete this card, set this variable to 0."
                ::= { rsmEntry 3 }

        rsmModelNum      OBJECT-TYPE
                SYNTAX  DisplayString
                ACCESS  read-only
                STATUS  mandatory
                DESCRIPTION
                        "RSM's model number."
                ::= { rsmEntry 4 }

        rsmOpticsMfgDate      OBJECT-TYPE
                SYNTAX  DateAndTime
                ACCESS  read-only
                STATUS  mandatory
                DESCRIPTION
                        "Date and Time of manufacturing of the optics
						 on the RSM card."
                ::= { rsmEntry 5 }

        rsmSerialNum    OBJECT-TYPE
                SYNTAX  SerialString
                ACCESS  read-only
                STATUS  mandatory
                DESCRIPTION
                        "Serial # of the RSM card."
                ::= { rsmEntry 6 }

        rsmModelType    OBJECT-TYPE
                SYNTAX  INTEGER 
                ACCESS  read-only
                STATUS  mandatory
                DESCRIPTION
                        "Model type of the RSM."
                ::= { rsmEntry 7 }

        rsmHWName       OBJECT-TYPE
                SYNTAX  CardName
                ACCESS  read-only
                STATUS  mandatory
                DESCRIPTION
                        "Manufacturing Hardware name of the RSM Card."
                ::= { rsmEntry 8 }

		rsmCardName     OBJECT-TYPE
                SYNTAX  CardName
				ACCESS  read-write
                STATUS  mandatory
                DESCRIPTION
                        "User configurable card name." 
                ::= { rsmEntry 9 }

        rsmFWName		OBJECT-TYPE
                SYNTAX  DisplayString
                ACCESS  read-only
                STATUS  mandatory
                DESCRIPTION
                        "RSM's Firmware Name."
                ::= { rsmEntry 10 }

		rsmFWVersionID	OBJECT-TYPE
                SYNTAX  VersionString
                ACCESS  read-only
                STATUS  mandatory
                DESCRIPTION
                        "The current version string of the RSM FW code."
                ::= { rsmEntry 11 }

        rsmFWDate		OBJECT-TYPE
                SYNTAX  DateAndTime
                ACCESS  read-only
                STATUS  mandatory
                DESCRIPTION
                        "Date and Time of latest Firmware of the RSM card."
                ::= { rsmEntry 12 }      

        rsmSetState		OBJECT-TYPE
                SYNTAX  RebootType
				ACCESS  read-write
                STATUS  mandatory
                DESCRIPTION
                        "Instruct the rsm to do a warmboot. A get on this will
						 always return an other." 
                ::= { rsmEntry 13 }

        rsmRxInsertionLoss   OBJECT-TYPE
                SYNTAX  DisplayString
				ACCESS  read-only
                STATUS  mandatory
                DESCRIPTION
                        "Insertion loss for Rx Path." 
                ::= { rsmEntry 14 }

		rsmRxComInsertionLoss   OBJECT-TYPE
                SYNTAX  DisplayString
				ACCESS  read-only
                STATUS  mandatory
                DESCRIPTION
                        "Insertion loss for Rx Com Path." 
                ::= { rsmEntry 15 }

		rsmWorkingWavelength	OBJECT-TYPE
                SYNTAX  INTEGER
				ACCESS  read-only
                STATUS  mandatory
                DESCRIPTION
                        "The RSM ITU number." 
                ::= { rsmEntry 16 }

		rsmLinkAPathID	OBJECT-TYPE
                SYNTAX  PathIdName
                ACCESS  read-write
                STATUS  mandatory
                DESCRIPTION
                        "Rsm LinkA Path ID name that this card is associated with.  
						 Set input equal NULL will remove the card off the path 
						 and also remove the path if there is no card left 
						 associate with that path."
                ::= { rsmEntry 17 }

		rsmLinkBPathID	OBJECT-TYPE
                SYNTAX  PathIdName
                ACCESS  read-write
                STATUS  mandatory
                DESCRIPTION
                        "Rsm LinkB Path ID name that this card is associated with.  
						 Set input equal NULL will remove the card off the path 
						 and also remove the path if there is no card left 
						 associate with that path."
                ::= { rsmEntry 18 }
				

        rsmAdminState     OBJECT-TYPE
                SYNTAX  INTEGER
						{ disable(1),
						  enable(2),
						  na(3)
						}
                ACCESS  read-write
                STATUS  mandatory
                DESCRIPTION
                        "Administrative control over that rsm card. Default value is enable.
						 When disabled, no alarms/events gets
						 generated."
                ::= { rsmEntry 19 }

		rsmPortTable	OBJECT-TYPE
                SYNTAX  SEQUENCE OF RsmPortEntry
                ACCESS  not-accessible
                STATUS  mandatory
                DESCRIPTION
                        "This table represents the information for each
                         RSM card's port."
                ::= { rsm 7 }

        rsmPortEntry	OBJECT-TYPE
                SYNTAX  RsmPortEntry
                ACCESS  not-accessible
                STATUS  mandatory
                DESCRIPTION
                        "Specifies the index for each row in the table below"
                INDEX { rsmPortCardShelf, rsmPortCardSlot, rsmPortType }
                ::= { rsmPortTable 1 }

        RsmPortEntry        ::=
                SEQUENCE 
				{
                        rsmPortCardShelf	CardShelf,
						rsmPortCardSlot		SlotInput,
						rsmPortType			INTEGER,
						rsmConnCardType		CardType,						
						rsmConnShelf		ShelfInput,
                        rsmConnSlot			SlotInput,
						rsmConnPort			INTEGER						
				}

        rsmPortCardShelf    OBJECT-TYPE
                SYNTAX  CardShelf
                ACCESS  read-only 
                STATUS  mandatory
                DESCRIPTION
                        "The shelf the card is in.  Valid values are: 1 to 2."
                ::= { rsmPortEntry 1 }

        rsmPortCardSlot	OBJECT-TYPE
                SYNTAX  SlotInput
                ACCESS  read-only 
                STATUS  mandatory
                DESCRIPTION
                        "The slot within the shelf the card is in."
                ::= { rsmPortEntry 2 }

		rsmPortType		OBJECT-TYPE 
                SYNTAX  INTEGER { 
								  localARx(1),
								  localATx(2),
								  localBRx(3),
								  localBTx(4)
								}
                ACCESS  read-only
                STATUS  mandatory
                DESCRIPTION
                        "Type of the RSM's port.  The order is CLI compatible."
                ::= { rsmPortEntry 3 }

        rsmConnCardType      OBJECT-TYPE
                SYNTAX  CardType
                ACCESS  read-write
                STATUS  mandatory
                DESCRIPTION
                        "Type of connection.  Valid values are ocmu(2), ocmi(3),
						 ocme(24).  A zero will be used for no connections."
                ::= { rsmPortEntry 4}

        rsmConnShelf   OBJECT-TYPE
                SYNTAX  ShelfInput
                ACCESS  read-write
                STATUS  mandatory
                DESCRIPTION
                        "The shelf the card conn to. Valid values are: 1 to 2." 
                ::= { rsmPortEntry 5 }

        rsmConnSlot     OBJECT-TYPE
                SYNTAX  SlotInput
                ACCESS  read-write
                STATUS  mandatory
                DESCRIPTION
                        "The slot within the shelf the card conn to."
                ::= { rsmPortEntry 6 }

		rsmConnPort    OBJECT-TYPE
                SYNTAX  INTEGER
                ACCESS  read-write
                STATUS  mandatory
                DESCRIPTION
                        "Conn port for RSM's port.Possible values based on 
				 card types that can connect to RSM are:
				 
				 OCMU/OCMITU/OCME: 3= CPE Tx, 4= CPE Rx 
				Input 0 to delete all the connections and unpair OCMs."
						 
                ::= { rsmPortEntry 7 }
                
-- The elements in the upsm subgroup of the configuration group

        upsmBootPromVer  OBJECT-TYPE
                SYNTAX  VersionString
                ACCESS  not-accessible
                STATUS  mandatory
                DESCRIPTION
                        "The current version string of the rsm
			 Boot PROM code"
                ::= { upsm 1 }

        upsmROMSize      OBJECT-TYPE
                SYNTAX  INTEGER (0..1024)
                ACCESS  not-accessible
                STATUS  mandatory
                DESCRIPTION
                        "Total Size of the ROM in Kilobyes"
                ::= { upsm 2 }

        upsmNumSubDiv    OBJECT-TYPE
                SYNTAX  INTEGER (0..20)
                ACCESS  not-accessible
                STATUS  mandatory
                DESCRIPTION
                        "Number of the subdivisions of the ROM."
                ::= { upsm 3 }

        upsmSubDivTable  OBJECT-TYPE
                SYNTAX  SEQUENCE OF UpsmSubDivEntry
                ACCESS  not-accessible
                STATUS  mandatory
                DESCRIPTION
                        "This table represents the number of sub divisions
                         and the size of each subdivision in ROM memory"
                ::= { upsm 4 }

        upsmSubDivEntry  OBJECT-TYPE
                SYNTAX  UpsmSubDivEntry
                ACCESS  not-accessible
                STATUS  mandatory
                DESCRIPTION
                        "Specifies the index for each row in the table below"
                INDEX { upsmSubDivIndex }
                ::= { upsmSubDivTable 1 }

        UpsmSubDivEntry  ::=
                SEQUENCE {
                        upsmSubDivIndex  INTEGER,
                        upsmSubDivDescr  DisplayString,
                        upsmSubDivSize   INTEGER,
                        upsmSubDivOffset OCTET STRING
                }

        upsmSubDivIndex  OBJECT-TYPE
                SYNTAX  INTEGER (0..20)
                ACCESS  not-accessible
                STATUS  mandatory
                DESCRIPTION
                        "Integer ID of each sub division in the ROM.  The order
                         of numbering is from the top of the ROM to the bottom
                         of the ROM."
                ::= { upsmSubDivEntry 1 }

        upsmSubDivDescr  OBJECT-TYPE
                SYNTAX  DisplayString (SIZE (0..20))
                ACCESS  not-accessible
                STATUS  mandatory
                DESCRIPTION
                        "Display Name of each Sub Division in ROM"
                ::= { upsmSubDivEntry 2 }

        upsmSubDivSize   OBJECT-TYPE
                SYNTAX  INTEGER (0..1024)
                ACCESS  not-accessible
                STATUS  mandatory
                DESCRIPTION
                        "Size of each sub division in ROM in kilobytes"
                ::= { upsmSubDivEntry 3 }

        upsmSubDivOffset OBJECT-TYPE
                SYNTAX  OCTET STRING (SIZE (0..8))
                ACCESS  not-accessible
                STATUS  mandatory
                DESCRIPTION
                        "Starting address of each sub division in the ROM
                         in HEX notation."
                ::= { upsmSubDivEntry 4 }

        upsmNumber		OBJECT-TYPE
                SYNTAX  INTEGER
                ACCESS  read-only
                STATUS  mandatory
                DESCRIPTION
                        "Number of UPSM rows in the following table.  This 
                         number is automatically updated whenever a new row is 
                         added to the table below."
                ::= { upsm 5 }

        upsmTable        OBJECT-TYPE
                SYNTAX  SEQUENCE OF UpsmEntry
                ACCESS  not-accessible
                STATUS  mandatory
                DESCRIPTION
                        "This table represents the information for each
                         UPSM card"
                ::= { upsm 6 }

        upsmEntry		OBJECT-TYPE
                SYNTAX  UpsmEntry
                ACCESS  not-accessible
                STATUS  mandatory
                DESCRIPTION
                        "Specifies the index for each row in the table below"
                INDEX { upsmCardLocation, upsmCardShelf, upsmCardSlot }
                ::= { upsmTable 1 }

        UpsmEntry        ::=
                SEQUENCE {
                        upsmCardLocation			CardLocation,
                        upsmCardShelf				CardShelf,
                        upsmCardSlot				SlotInput,
						upsmModelNum				DisplayString,
                        upsmOpticsMfgDate			DateAndTime,
                        upsmSerialNum				SerialString,
                        upsmModelType				INTEGER,
						upsmHWName					CardName,
						upsmCardName				CardName,
						upsmFWName					DisplayString,			
						upsmFWVersionID				VersionString,
						upsmFWDate					DateAndTime,
                        upsmSetState				RebootType,
						upsmRxInsertionLoss			DisplayString,
						upsmTxInsertionLoss			DisplayString,
						upsmMarginForSwitch			INTEGER,
						upsmMinProtPowerForSwitch	INTEGER,
						upsmDebounce				INTEGER,
						upsmBlackOutTime			INTEGER,
						upsmSwitch					INTEGER,
						upsmLinkAPathID				PathIdName,
						upsmLinkBPathID				PathIdName,
						upsmAdminState				INTEGER
                }

        upsmCardLocation OBJECT-TYPE
                SYNTAX  CardLocation
                ACCESS  read-only
                STATUS  mandatory
                DESCRIPTION
                        "Location of the UPSM card.  Valid values are: Local in
                         the same chassis."
                ::= { upsmEntry 1 }

        upsmCardShelf    OBJECT-TYPE
                SYNTAX  INTEGER
                ACCESS  read-only
                STATUS  mandatory
                DESCRIPTION
                        "The shelf the card is in.  Valid values are: 1 to 2."
                ::= { upsmEntry 2 }

        upsmCardSlot     OBJECT-TYPE
                SYNTAX  INTEGER
                ACCESS  read-write
                STATUS  mandatory
                DESCRIPTION
                        "The slot within the shelf the module is in.  The range
						 of valid values range from 1 through 17 depending on
						 the chassis type and the shelf the module is in.
                         To delete this card, set this variable to 0."
                ::= { upsmEntry 3 }

        upsmModelNum	OBJECT-TYPE
                SYNTAX  DisplayString
                ACCESS  read-only
                STATUS  mandatory
                DESCRIPTION
                        "UPSM's model number."
                ::= { upsmEntry 4 }

        upsmOpticsMfgDate      OBJECT-TYPE
                SYNTAX  DateAndTime
                ACCESS  read-only
                STATUS  mandatory
                DESCRIPTION
                        "Date and Time of manufacturing of the optics
			 on the UPSM card."
                ::= { upsmEntry 5 }

        upsmSerialNum    OBJECT-TYPE
                SYNTAX  SerialString
                ACCESS  read-only
                STATUS  mandatory
                DESCRIPTION
                        "Serial # of the UPSM card."
                ::= { upsmEntry 6 }

        upsmModelType    OBJECT-TYPE
                SYNTAX  INTEGER 
                ACCESS  read-only
                STATUS  mandatory
                DESCRIPTION
                        "Model type of the UPSM."
                ::= { upsmEntry 7 }

        upsmHWName       OBJECT-TYPE
                SYNTAX  CardName
                ACCESS  read-only
                STATUS  mandatory
                DESCRIPTION
                        "Manufacturing Hardware name of the UPSM Card."
                ::= { upsmEntry 8 }

		upsmCardName    OBJECT-TYPE
                SYNTAX  CardName
				ACCESS  read-write
                STATUS  mandatory
                DESCRIPTION
                        "User configurable card name." 
                ::= { upsmEntry 9 }

        upsmFWName		OBJECT-TYPE
                SYNTAX  DisplayString
                ACCESS  read-only
                STATUS  mandatory
                DESCRIPTION
                        "UPSM's Firmware Name."
                ::= { upsmEntry 10 }

		upsmFWVersionID	OBJECT-TYPE
                SYNTAX  VersionString
                ACCESS  read-only
                STATUS  mandatory
                DESCRIPTION
                        "The current version string of the UPSM FW code."
                ::= { upsmEntry 11 }

        upsmFWDate		OBJECT-TYPE
                SYNTAX  DateAndTime
                ACCESS  read-only
                STATUS  mandatory
                DESCRIPTION
                        "Date and Time of latest Firmware of the UPSM card."
                ::= { upsmEntry 12 }      

        upsmSetState	OBJECT-TYPE
                SYNTAX  RebootType
				ACCESS  read-write
                STATUS  mandatory
                DESCRIPTION
                        "Instruct the upsm to do a warmboot. A get on this will
			 always return an other." 
                ::= { upsmEntry 13 }

        upsmRxInsertionLoss   OBJECT-TYPE
                SYNTAX  DisplayString
				ACCESS  read-only
                STATUS  mandatory
                DESCRIPTION
                        "Insertion loss for Rx Path." 
                ::= { upsmEntry 14 }

		upsmTxInsertionLoss   OBJECT-TYPE
                SYNTAX  DisplayString
				ACCESS  read-only
                STATUS  mandatory
                DESCRIPTION
                        "Insertion loss for Tx Path." 
                ::= { upsmEntry 15 }

		upsmMarginForSwitch	OBJECT-TYPE
                SYNTAX  INTEGER (-28..-5)
				ACCESS  read-write
                STATUS  mandatory
                DESCRIPTION
				"The UPSM switching threshold for protection switch to occur.  
				The limit is from -28 to -5. " 
                ::= { upsmEntry 16 }

		upsmMinProtPowerForSwitch	OBJECT-TYPE
                SYNTAX  INTEGER (-28..-5)
				ACCESS  read-write
                STATUS  mandatory
                DESCRIPTION
				"The minimum protection link power to allow protection switch 
				to function.  The limit is from -28 to -5.  This value should 
				be 3dBm greater than the margin." 
                ::= { upsmEntry 17 }

		upsmDebounce	OBJECT-TYPE
                SYNTAX  INTEGER
				ACCESS  read-only
                STATUS  mandatory
                DESCRIPTION
                        "The number of times to measure low power condition 
						 before performing protection switch." 
                ::= { upsmEntry 18 }

		upsmBlackOutTime	OBJECT-TYPE
                SYNTAX  INTEGER
				ACCESS  read-only
                STATUS  mandatory
                DESCRIPTION
                        "The time after protection switch before allowing 
						 another protection switch." 
                ::= { upsmEntry 19 }

		upsmSwitch	OBJECT-TYPE
                SYNTAX  INTEGER
					{ 
						other(1),
						switchToLinkA(2),
						switchToLinkB(3), 
						toggle(4),
						enableAutoSwitch(6) 
					}
				ACCESS  read-write
                STATUS  mandatory
                DESCRIPTION
                        "The Link switch control. switchToLinkA or
						 switchToLinkB option would disable auto switch
						 functionality. Auto switch functionality can
						 be turned on by setting to enableAutoSwitch
						 option " 
                ::= { upsmEntry 20 }

		upsmLinkAPathID	OBJECT-TYPE
                SYNTAX  PathIdName
                ACCESS  read-write
                STATUS  mandatory
                DESCRIPTION
                        "Upsm LinkA Path ID name that this card is associated with.  
						 Set input equal NULL will remove the card off the path 
						 and also remove the path if there is no card left 
						 associate with that path."
                ::= { upsmEntry 21 }

		upsmLinkBPathID	OBJECT-TYPE
                SYNTAX  PathIdName
                ACCESS  read-write
                STATUS  mandatory
                DESCRIPTION
                        "Upsm LinkB Path ID name that this card is associated with.  
						 Set input equal NULL will remove the card off the path 
						 and also remove the path if there is no card left 
						 associate with that path."
                ::= { upsmEntry 22 }

        upsmAdminState     OBJECT-TYPE
                SYNTAX  INTEGER
						{ disable(1),
						  enable(2),
						  na(3)
						}
                ACCESS  read-write
                STATUS  mandatory
                DESCRIPTION
                        "Administrative control over that upsm card. Default value is enable.
						 When disabled, no alarms/events gets
						 generated."
                ::= { upsmEntry 23}

				
		upsmPortTable	OBJECT-TYPE
                SYNTAX  SEQUENCE OF UpsmPortEntry
                ACCESS  not-accessible
                STATUS  mandatory
                DESCRIPTION
                        "This table represents the information for each
                         UPSM card's port."
                ::= { upsm 7 }

        upsmPortEntry	OBJECT-TYPE
                SYNTAX  UpsmPortEntry
                ACCESS  not-accessible
                STATUS  mandatory
                DESCRIPTION
                        "Specifies the index for each row in the table below"
                INDEX { upsmPortCardShelf, upsmPortCardSlot, upsmPortType }
                ::= { upsmPortTable 1 }

        UpsmPortEntry        ::=
                SEQUENCE 
				{
                        upsmPortCardShelf			CardShelf,
						upsmPortCardSlot			SlotInput,
						upsmPortType				INTEGER,
						upsmConnLocation			CardLocation,
						upsmConnIpAddress			IpAddress,
						upsmConnChassisID			NodeName,
						upsmConnSystemName			NodeName,
						upsmConnCardType			INTEGER,
						upsmConnPort				INTEGER,
						upsmConnShelf				ShelfInput,
                        upsmConnSlot				SlotInput							
				}

        upsmPortCardShelf    OBJECT-TYPE
                SYNTAX  CardShelf
                ACCESS  read-only 
                STATUS  mandatory
                DESCRIPTION
                        "The shelf the card is in.  Valid values are: 1 to 2."
                ::= { upsmPortEntry 1 }

        upsmPortCardSlot	OBJECT-TYPE
                SYNTAX  SlotInput
                ACCESS  read-only 
                STATUS  mandatory
                DESCRIPTION
                        "The slot within the shelf the card is in."
                ::= { upsmPortEntry 2 }

		upsmPortType		OBJECT-TYPE 
                SYNTAX  INTEGER { 
								  linkATx(1),
								  linkARx(2),
								  linkBTx(3),
								  linkBRx(4),
								  localTx(5),
								  localRx(6)
								}
                ACCESS  read-only
                STATUS  mandatory
                DESCRIPTION
                        "Type of the UPSM's port.  The order is CLI compatible."
                ::= { upsmPortEntry 3 }

		upsmConnLocation    OBJECT-TYPE
                SYNTAX  CardLocation
                ACCESS  read-write
                STATUS  mandatory
                DESCRIPTION
                        "The chassis's location of the card conn to."
                ::= { upsmPortEntry 4 }


        upsmConnIpAddress OBJECT-TYPE
                SYNTAX  IpAddress
                ACCESS  read-write
                STATUS  mandatory
                DESCRIPTION
                        "IpAddress of the connected node.  User config. If local
						 connection, a set on it would return an error; would be automatically
						 be set to the IP address of the node "
                ::= { upsmPortEntry 5}

		upsmConnChassisID OBJECT-TYPE
                SYNTAX  DisplayString(SIZE(0..16))
                ACCESS  read-write
                STATUS  mandatory
                DESCRIPTION
                        "Chassis ID of the connected node.  User config. If local connection,
						a set on it would return an error; would be automatically be set to
						the chassis Id of the local node"
                ::= { upsmPortEntry 6}

        upsmConnSystemName OBJECT-TYPE
                SYNTAX  DisplayString(SIZE(0..32))
                ACCESS  read-write
                STATUS  mandatory
                DESCRIPTION
                        "System Name of the connected node.  User config. If local connection,
						a set on it would return an error; would be automatically be set to
						the sysetem name of the local node."
                ::= { upsmPortEntry 7}

        upsmConnCardType      OBJECT-TYPE
                SYNTAX  INTEGER (0..30)
                ACCESS  read-write
                STATUS  mandatory
                DESCRIPTION
                        "Type of connection.  Valid values are ocmu(2),
			 ocmItu(3), mux(4), demux(5), mcm(8), w4cd(10), w2cmd(13), w4cm(21),
			 osam(20), fadm(6), oppm(7), fadmb(19), ocme(24), etc...
			 A zero will be used for no connections."
                ::= { upsmPortEntry 8}

        upsmConnPort    OBJECT-TYPE
                SYNTAX  INTEGER
                ACCESS  read-write
                STATUS  mandatory
                DESCRIPTION
                        "Conn port for UPSM's port.Possible values based on 
				 card types that can connect to UPSM are:
				 OFCM/OFCD: 1/2/3/4= port index, 5=EXP, 6=OUT/IN
				 W4CM/W4CD: 1=1510, 2=1530, 3=1550,
                                    4=1570, 5=EXP, 6=IN/OUT
				 W2CM/W2CMD:1=13M, 2=15M, 3=13D, 4=15D, 5=IN , 6=OUT
				 OSAM: 1=IN, 2=OUT
				 FADM: 1=Conn A Tx, 2=Conn A Rx,  3=Local  Tx
					 4=Local  Rx, 5=Conn B Tx, 6=Conn B Rx
				 FADMB: 1=A/D, 2=EXP, 3=Local, 4=Rx
				 OCMU/OCMITU/MCM: 1=Link Tx, 2=Link Rx 
				 UPSM/OPPM: 1=Link A Tx, 2=Link A Rx, 3=Link B Tx,
				 4=Link B Rx, 5=Local Tx, 6=Local Rx
				 OLI: 1=1Tx, 2=1Rx, 3=2Tx, 4=2Rx, 5=3Tx, 6=3Rx, 7=4Tx, 8=4Rx"						 
                ::= { upsmPortEntry 9 }

        upsmConnShelf   OBJECT-TYPE
                SYNTAX  ShelfInput
                ACCESS  read-write
                STATUS  mandatory
                DESCRIPTION
                        "The shelf the card conn to. Valid values are: 1 to 2." 
                ::= { upsmPortEntry 10 }

        upsmConnSlot     OBJECT-TYPE
                SYNTAX  SlotInput
                ACCESS  read-write
                STATUS  mandatory
                DESCRIPTION
                        "The slot within the shelf the card conn to."
                ::= { upsmPortEntry 11 }

        -- The elements in the topology subgroup of the configuration group


        topologyTable        OBJECT-TYPE
                SYNTAX  SEQUENCE OF TopologyEntry
                ACCESS  not-accessible
                STATUS  mandatory
                DESCRIPTION
                        "This table represents the link topology between local and
                         remote cards"
                ::= { topology 1}

        topologyEntry        OBJECT-TYPE
                SYNTAX  TopologyEntry
                ACCESS  not-accessible
                STATUS  mandatory
                DESCRIPTION
                        "Specifies the index for each row in the table below"
                INDEX { topologyNearEndCardShelf, topologyNearEndCardSlot }
                ::= { topologyTable 1 }

        TopologyEntry        ::=
                SEQUENCE {
                        topologyNearEndCardShelf        CardShelf,
                        topologyNearEndCardSlot         INTEGER,
                        topologyNearEndCardPortIndex    PortIndex,
                        topologyNearEndCardType         CardType,
                        topologyFarEndChassisID         NodeName,
                        topologyFarEndSystemName        NodeName,
                        topologyFarEndNodeIpAddress     IpAddress,
                        topologyFarEndNodeCardShelf     CardShelf,
                        topologyFarEndNodeCardSlot      INTEGER,
                        topologyFarEndNodeCardPortIndex PortIndex,
						topologyLinkStatus				INTEGER,
                        topologyFarEndNodeCardType      CardType

                }

        topologyNearEndCardShelf OBJECT-TYPE
                SYNTAX  CardShelf
                ACCESS  read-only
                STATUS  mandatory
                DESCRIPTION
                        "Shelf of the near end card."
                ::= { topologyEntry 1 }


        topologyNearEndCardSlot OBJECT-TYPE
                SYNTAX  CardSlot
                ACCESS  read-write
                STATUS  mandatory
                DESCRIPTION
                        "Slot of the near end card.  Input 0 will 
						 delete the topology link."
                ::= { topologyEntry 2 }

        topologyNearEndCardPortIndex OBJECT-TYPE
                SYNTAX  PortIndex
                ACCESS  not-accessible
                STATUS  mandatory
                DESCRIPTION
                        "Futuristic to support port based topology if the card happens 
				 to have more than 1 optical link port."
                ::= { topologyEntry 3 }

        topologyNearEndCardType OBJECT-TYPE
                SYNTAX  CardType
                ACCESS  read-only
                STATUS  mandatory
                DESCRIPTION
                        "Card type of the near end card."
                ::= { topologyEntry 4 }

        topologyFarEndChassisID OBJECT-TYPE
                SYNTAX  NodeName
                ACCESS  read-only
                STATUS  mandatory
                DESCRIPTION
                        "Chassis ID of the far end chassis. Part of manufacturing info"
                ::= { topologyEntry 5}

        topologyFarEndSystemName OBJECT-TYPE
                SYNTAX  NodeName
                ACCESS  read-only
                STATUS  mandatory
                DESCRIPTION
                        "Name of the far end node/chassis.  Not supported for
			 remote TMM masters."
                ::= { topologyEntry 6}

        topologyFarEndNodeIpAddress OBJECT-TYPE
                SYNTAX  IpAddress
                ACCESS  read-only
                STATUS  mandatory
                DESCRIPTION
                        "IpAddress of the far end chassis. Not supported for
			 remote TMM masters."
                ::= { topologyEntry 7}

        topologyFarEndNodeCardShelf OBJECT-TYPE
                SYNTAX  CardShelf
                ACCESS  read-only
                STATUS  mandatory
                DESCRIPTION
                        "Shelf of the far end module"
                ::= { topologyEntry 8}

        topologyFarEndNodeCardSlot OBJECT-TYPE
                SYNTAX  CardSlot
                ACCESS  read-only
                STATUS  mandatory
                DESCRIPTION
                        "Slot of the far end module"
                ::= { topologyEntry 9}

        topologyFarEndNodeCardPortIndex OBJECT-TYPE
                SYNTAX  PortIndex
                ACCESS  read-only
                STATUS  mandatory
                DESCRIPTION
                        "Futuristic to support port based topology if the card happens 
				 to have more than 1 optical link port."
                ::= { topologyEntry 10}

        topologyLinkStatus OBJECT-TYPE
                SYNTAX  INTEGER
						{
						  down(1),
						  active(2)
						}
                ACCESS  read-only
                STATUS  mandatory
                DESCRIPTION
                        "Status of the link to indicate if active or down"
                ::= { topologyEntry 11}

        topologyFarEndNodeCardType OBJECT-TYPE
                SYNTAX  CardType
                ACCESS  read-only
                STATUS  mandatory
                DESCRIPTION
                        "Card type of the far end card."
                ::= { topologyEntry 12 }

	topologyDiscover     OBJECT-TYPE
                SYNTAX  INTEGER { 
					other(1),
					discoverTopology(2)
					}
                ACCESS  read-write
                STATUS  mandatory
                DESCRIPTION
			  " An action to rediscover the complete topology
			  A get would alway return other(1)."
                ::= { topology 2 }


        -- The elements in the routing subgroup of the configuration group

		-- This table is no longer supported, instead user needs to use imnRoutingTable

        routingTable        OBJECT-TYPE
                SYNTAX  SEQUENCE OF RoutingEntry
                ACCESS  not-accessible
                STATUS  mandatory
                DESCRIPTION
                        "This table represents dynamic and static routing information"
                ::= { routing 1}

        routingEntry        OBJECT-TYPE
                SYNTAX  RoutingEntry
                ACCESS  not-accessible
                STATUS  mandatory
                DESCRIPTION
                        "Specifies the index for each row in the table below"
                INDEX { routeIpDestAddress, routeLocalCCShelf, routeLocalCCSlot  }
                ::= { routingTable 1 }

        RoutingEntry        ::=
                SEQUENCE {
                        routeLocalCCShelf				CardShelf,
                        routeLocalCCSlot				INTEGER,
						routeIpDestAddress				IpAddress,
						routeDestType					INTEGER,
						routeMode						INTEGER	
                }

        routeLocalCCShelf OBJECT-TYPE
                SYNTAX  CardShelf
                ACCESS  not-accessible
                STATUS  mandatory
                DESCRIPTION
                        "Shelf of the local CC card."
                ::= { routingEntry 1 }


        routeLocalCCSlot OBJECT-TYPE
                SYNTAX  CardSlot
                ACCESS  not-accessible
                STATUS  mandatory
                DESCRIPTION
                        "Slot of the local CC card."
                ::= { routingEntry 2 }


        routeIpDestAddress OBJECT-TYPE
                SYNTAX  IpAddress
                ACCESS  not-accessible
                STATUS  mandatory
                DESCRIPTION
                       "Destination IP address. Not supported for
						remote TMM masters."
                ::= { routingEntry 3}

 
		routeDestType     OBJECT-TYPE
                SYNTAX  INTEGER { 
					externalRoute(1),
					internalRoute(2)
					}
                ACCESS  not-accessible
                STATUS  mandatory
                DESCRIPTION
				"Destination route type. External means destination is not part of LuxN network. 
				 Internal means destination is one of the LuxN node "
                ::= { routingEntry 4 }

		routeMode     OBJECT-TYPE
                SYNTAX  INTEGER { 
					static(1),
					dynamic(2)
					}
                ACCESS  not-accessible
                STATUS  mandatory
                DESCRIPTION
				"Is the route added statically(manually) or dynamically(automatic) "
                ::= { routingEntry 5 }

        imnDynamicRoutingTable        OBJECT-TYPE
                SYNTAX  SEQUENCE OF ImnDynamicRoutingEntry
                ACCESS  not-accessible
                STATUS  mandatory
                DESCRIPTION
                        "This table represents IMN based dynamic routing information"
                ::= { routing 2}

        imnDynamicRoutingEntry        OBJECT-TYPE
                SYNTAX  ImnDynamicRoutingEntry
                ACCESS  not-accessible
                STATUS  mandatory
                DESCRIPTION
                        "Specifies the index for each row in the table below"
                INDEX { imnDynamicRouteIpDest}
                ::= { imnDynamicRoutingTable 1 }

        ImnDynamicRoutingEntry        ::=
                SEQUENCE {
						imnDynamicRouteIpDest						IpAddress,
						imnDynamicRouteIpMask						IpAddress,
						imnDynamicRouteMetric						INTEGER,
						imnDynamicRouteNextHop						IpAddress
                }



        imnDynamicRouteIpDest OBJECT-TYPE
                SYNTAX  IpAddress
                ACCESS  read-only
                STATUS  mandatory
                DESCRIPTION
                       "Destination IP address. Not supported for
						remote TMM masters."
                ::= { imnDynamicRoutingEntry 1}

        imnDynamicRouteIpMask OBJECT-TYPE
                SYNTAX  IpAddress
                ACCESS  read-only
                STATUS  mandatory
                DESCRIPTION
                       "Destination's IP mask address. Not supported for
						remote TMM masters."
                ::= { imnDynamicRoutingEntry 2}

        imnDynamicRouteMetric OBJECT-TYPE
                SYNTAX  INTEGER(1..15)
                ACCESS  read-only
                STATUS  mandatory
                DESCRIPTION
                       "Cost associated with this route."
                ::= { imnDynamicRoutingEntry 3}


        imnDynamicRouteNextHop OBJECT-TYPE
                SYNTAX  IpAddress
                ACCESS  read-only
                STATUS  mandatory
                DESCRIPTION
                       "Neighbour node of this route."
                ::= { imnDynamicRoutingEntry 4}

		imnRouteUpdateTimer		OBJECT-TYPE
                SYNTAX  INTEGER (1..254)
                ACCESS  read-write
                STATUS  mandatory
                DESCRIPTION
				"Time in seconds for the route table to get updated/propagated
				 Default value is 30 seconds."
                ::= { routing 3}

		imnRouteKeepAliveTimer		OBJECT-TYPE
                SYNTAX  INTEGER (1..255)
                ACCESS  read-write
                STATUS  mandatory
                DESCRIPTION
				"Time in seconds before neighbors enter unreachable state after communication
				 is lost. This value has to be greater than or equal to imnRouteUpdateTimer
				 Default value is 60 seconds" 
                ::= { routing 4}

		imnRouteUnReachableTimer		OBJECT-TYPE
                SYNTAX  INTEGER (1..255)
                ACCESS  read-write
                STATUS  mandatory
                DESCRIPTION
				"Time in seconds before Neighbors in unreachable state are deleted from 
				 the route table. This value has to greater than or equal to imnRouteUpdateTimer
				 Default value is  60 seconds" 
                ::= { routing 5}

		imnRouteMode		OBJECT-TYPE
                SYNTAX  INTEGER {
						disabled(1),
						enable(2)
						}
                ACCESS  read-write
                STATUS  mandatory
                DESCRIPTION
				"Enable/Disable IMN functionality. Default is disabled" 
                ::= { routing 6}

        imnStaticRoutingTable        OBJECT-TYPE
                SYNTAX  SEQUENCE OF ImnStaticRoutingEntry
                ACCESS  not-accessible
                STATUS  mandatory
                DESCRIPTION
                        "This table represents IMN based static routing information"
                ::= { routing 7}

        imnStaticRoutingEntry        OBJECT-TYPE
                SYNTAX  ImnStaticRoutingEntry
                ACCESS  not-accessible
                STATUS  mandatory
                DESCRIPTION
                        "Specifies the index for each row in the table below"
                INDEX { imnStaticRouteIpDest}
                ::= { imnStaticRoutingTable 1 }

        ImnStaticRoutingEntry        ::=
                SEQUENCE {
						imnStaticRouteIpDest						IpAddress,
						imnStaticRouteIpMask						IpAddress,
						imnStaticRouteMetric						INTEGER
                }



        imnStaticRouteIpDest OBJECT-TYPE
                SYNTAX  IpAddress
                ACCESS  read-only
                STATUS  mandatory
                DESCRIPTION
                       "Destination IP address. Not supported for
						remote TMM masters."
                ::= { imnStaticRoutingEntry 1}

        imnStaticRouteIpMask OBJECT-TYPE
                SYNTAX  IpAddress
                ACCESS  read-only
                STATUS  mandatory
                DESCRIPTION
                       "Destination's IP mask address. Not supported for
						remote TMM masters."
                ::= { imnStaticRoutingEntry 2}

        imnStaticRouteMetric OBJECT-TYPE
                SYNTAX  INTEGER(1..15)
                ACCESS  read-only
                STATUS  mandatory
                DESCRIPTION
                       "Cost associated with this route."
                ::= { imnStaticRoutingEntry 3}

		imnRouteMaxMetric		OBJECT-TYPE
                SYNTAX  INTEGER 
                ACCESS  read-write
                STATUS  mandatory
                DESCRIPTION
				"Maximum acceptable metric count before the routes gets dropped.
				 Default value is 255. Ideally this value should be greater than
				 imnStaticRouteMetric" 
                ::= { routing 8}



	-- The elements in the ring subgroup of the configuration group

		ringNum			OBJECT-TYPE
                SYNTAX  INTEGER
                ACCESS  read-only
                STATUS  mandatory
                DESCRIPTION
                        "Total number of ring configured in the list."
                ::= { ring 1 }


        ringTable        OBJECT-TYPE
                SYNTAX  SEQUENCE OF RingEntry
                ACCESS  not-accessible
                STATUS  mandatory
                DESCRIPTION
                        "This table represent the ring information"
                ::= { ring 2}

        ringEntry		OBJECT-TYPE
                SYNTAX  RingEntry
                ACCESS  not-accessible
                STATUS  mandatory
                DESCRIPTION
                        "Specifies the index for each row in the table below"
                INDEX { ringIndex  }
                ::= { ringTable 1 }

        RingEntry        ::=
                SEQUENCE {
                        ringIndex					INTEGER,
                        ringID						RingIdName,
						ringPathID1					PathIdName,
						ringPathID2					PathIdName,
						ringPath1RemoteIP			IpAddress,
						ringPath1RemoteChassisId	DisplayString,
						ringPath2RemoteIP			IpAddress,
						ringPath2RemoteChassisId	DisplayString

                }

        ringIndex		OBJECT-TYPE
                SYNTAX  INTEGER
                ACCESS  not-accessible
                STATUS  mandatory
                DESCRIPTION
                        "The ringIndex and also the index of the ring table."
                ::= { ringEntry 1 }


        ringID			OBJECT-TYPE
                SYNTAX  RingIdName
                ACCESS  read-write
                STATUS  mandatory
                DESCRIPTION
				"RingID Name for UPSR.  Empty string will remove and deassociate 
				the RingID with the PathIDs.  You always has one dummy entry for 
				adding another ring."
                ::= { ringEntry 2 }


        ringPathID1		OBJECT-TYPE
                SYNTAX  PathIdName
                ACCESS  read-write
                STATUS  mandatory
                DESCRIPTION
                       "PathID 1 associate with this ring."
                ::= { ringEntry 3}

		ringPathID2		OBJECT-TYPE
                SYNTAX  PathIdName
                ACCESS  read-write
                STATUS  mandatory
                DESCRIPTION
                       "PathID 2 associate with this ring."
                ::= { ringEntry 4}

        ringPath1RemoteIP     OBJECT-TYPE
                SYNTAX  IpAddress
                ACCESS  read-only
                STATUS  mandatory
                DESCRIPTION
                        "IP Address of the neighbor node associated with path 1"
                ::= {  ringEntry 5 }

		ringPath1RemoteChassisId  OBJECT-TYPE
                SYNTAX  DisplayString(SIZE(0..16))
                ACCESS  read-only
                STATUS  mandatory
                DESCRIPTION
                        "Chassis ID of the neighbor node associated with path 1"
			::= { ringEntry 6}

        ringPath2RemoteIP     OBJECT-TYPE
                SYNTAX  IpAddress
                ACCESS  read-only
                STATUS  mandatory
                DESCRIPTION
                        "IP Address of the neighbor node associated with path 2"
                ::= {  ringEntry 7 }

		ringPath2RemoteChassisId  OBJECT-TYPE
                SYNTAX  DisplayString(SIZE(0..16))
                ACCESS  read-only
                STATUS  mandatory
                DESCRIPTION
                        "Chassis ID of the neighbor node associated with path 2"
			::= { ringEntry 8}



        -- Miscellaneous configuration elements
        
        sysAddCard      OBJECT-TYPE
                SYNTAX  DisplayString (SIZE (0..10))
                ACCESS  read-write
                STATUS  mandatory
                DESCRIPTION
                       "Add card operation given type, shelf, slot, and
                        optionally sub card type.  The format is (type,shelf,
                        slot[,optional_csim]).  If the fourth optional
                        parameter is present, its value should be 1 to
                        indicate OCMITU/OCMU with CSIM.
                        Different types of card:
                        OCMU:	2 //with or without csim module
                        OCMI:   3 // with or without csim module
                        OFCM:   4
                        OFCD:   5
                        FADM:   6
                        OPPM:   7
                        MCM:    8
                        W4CD:	10
                        W2CM/D: 13
                        RSDM:   16
                        RPSM:   17
                        RTDM:   18
                        FADMB:  19
                        OSAM:   20
                        W4CM:	21
						RSM:	22
						UPSM:	23
						OCME:	24
						OCM10G: 27
                        For example, to add a FADM card in shelf 1, slot 8,
                        this variable will be set to 6,1,8.
                        To add an OCMI card with colorsim module in shelf 1,
                        slot 7, this variable will be set to 3,1,7,1
                        A get on this will return 0,0,0,0"
		::= { systemConfig 1 } 

	sysAlarmCtrl	OBJECT-TYPE
                SYNTAX  INTEGER { enable(1), disable(2) }
                ACCESS  read-write
                STATUS  mandatory
                DESCRIPTION
			"The Master Control for Alarms. Will enable or disable
			 all external and visual alarms of the system. The
			 default state is enable."
		    ::= { systemConfig 2 } 

	sysAlarmCritical	OBJECT-TYPE
                SYNTAX  INTEGER { on(1), off(2) }
                ACCESS  read-write
                STATUS  mandatory
                DESCRIPTION
			"Turns on or off all external critical audible
			 and visual alarms."
		    ::= { systemConfig  3 } 

	sysAlarmMajor	OBJECT-TYPE
                SYNTAX  INTEGER { on(1), off(2) }
                ACCESS  read-write
                STATUS  mandatory
                DESCRIPTION
			"Turns on or off all external major and minor
			 audible and visual alarms."
		    ::= { systemConfig 4 } 

	sysAlarmSerial	OBJECT-TYPE
                SYNTAX  INTEGER { enable(1), disable(2) }
                ACCESS  read-write
                STATUS  mandatory
                DESCRIPTION
			"Enables or disables the flow of TL1 alarms to the
			 serial port."
		    ::= { systemConfig 5 }

	sysAlarmAutoCutoff	OBJECT-TYPE
                SYNTAX  INTEGER { enable(1), disable(2) }
                ACCESS  read-write
                STATUS  mandatory
                DESCRIPTION
			"Enables or disables the AutoCutoff feature
			 for dry-contact alarm closures"			 
		    ::= { systemConfig 6 }


        sysAddRoute      OBJECT-TYPE
                SYNTAX  DisplayString (SIZE (0..20))
                ACCESS  not-accessible
                STATUS  mandatory
                DESCRIPTION
                       "Add route operation given local shelf, local slot, destination
                        IP address and route Type.  The format is (shelf, slot, 
                        route Type, destination IP). 
                        Different types of route types are:

						external Route: 1 (Route to an external non LuxN node)
						internal Route: 2 (Route to a LuxN node in the network)

                        For example, to add an internal route to a LuxN node with IP address
						192.162.6.65 from local shelf 1, slot 6 this variable would
						be set to 1,6,3,192.162.6.65

						For adding an external route, shelf & slot needs to be zero. For e.g
						To add an external route to destination address 192.168.9.99,
						this variable needs to be set to 0,0,192.168.9.99

                        A get on this will return 0,0,0,0
						NO LONGER SUPPORTED, user now needs to use sysImnAddRoute"
						::= { systemConfig 7 } 

        sysDeleteRoute      OBJECT-TYPE
                SYNTAX  DisplayString (SIZE (0..20))
                ACCESS  not-accessible
                STATUS  mandatory
                DESCRIPTION
                       "Delete  route operation given local shelf, local slot & destination
                        IP address .  The format is (shelf, slot, 
                        destination IP).  

                        For example, to delete a route to a LuxN node with IP address
						192.162.6.65 from local shelf 1, slot 6 this variable would
						be set to 1,6,192.162.6.65
                        A get on this will return 0,0,0
						NO LONGER SUPPORTED, user now needs to use sysImnAddRoute"
						::= { systemConfig 8 } 

		sysSwitchByPathId      OBJECT-TYPE
                SYNTAX  PathIdName
                ACCESS  read-write
                STATUS  mandatory
                DESCRIPTION
                       "Initiate UPSR switching by Path ID."
						::= { systemConfig 9 } 

		sysSwitchAll	OBJECT-TYPE
                SYNTAX  INTEGER { yes(1), no(2) }
                ACCESS  read-write
                STATUS  mandatory
                DESCRIPTION
						"Switch all CC cards that have backup."			 
		    ::= { systemConfig 10 }

		sysAlarmMinor	OBJECT-TYPE
					SYNTAX  INTEGER { on(1), off(2) }
					ACCESS  read-write
					STATUS  mandatory
					DESCRIPTION
				"Turns on or off all external minor
				 audible and visual alarms."
				::= { systemConfig 11 }

		sysDelCfgDb	OBJECT-TYPE
					SYNTAX  INTEGER { other(1), delete(2) }
					ACCESS  read-write
					STATUS  mandatory
					DESCRIPTION
				"Action to delete configuration database. MPM would reboot
				 after the database is deleted. A get on it will return other"
				::= { systemConfig 12 }

		sysImnAddRoute      OBJECT-TYPE
                SYNTAX  DisplayString (SIZE (0..20))
                ACCESS  read-write
                STATUS  mandatory
                DESCRIPTION
                       "Add route operation. It takes destination IP address, 
					    IP mask and the route metric.  
					    The format is (destination IP, IP mask, routeMetric). 

                        A get on this will return 0.0.0.0,0.0.0.0,0"
						::= { systemConfig 13 }
						
        sysImnDeleteRoute      OBJECT-TYPE
                SYNTAX  DisplayString (SIZE (0..20))
                ACCESS  read-write
                STATUS  mandatory
                DESCRIPTION
                       "Delete route operation. It takes destination IP address 
					    and IP mask.
					    The format is (destination IP, IP mask=). 

                        A get on this will return 0.0.0.0,0.0.0.0"
						::= { systemConfig 14 }  

	
        sysExtAlarmInputTable     OBJECT-TYPE
                SYNTAX  SEQUENCE OF SysExtAlarmInputEntry
                ACCESS  not-accessible
                STATUS  mandatory
                DESCRIPTION
                        "This table represents the input information for each
                         external alarm indicator"
                ::= { systemConfig 17 }

       sysExtAlarmInputEntry    OBJECT-TYPE
                SYNTAX  SysExtAlarmInputEntry
                ACCESS  not-accessible
                STATUS  mandatory
                DESCRIPTION
                        "Specifies the index for each row in the table below"
                INDEX { sysExtAlarmInputId }
                ::= { sysExtAlarmInputTable 1 }

        SysExtAlarmInputEntry     ::=
                SEQUENCE {
                        sysExtAlarmInputId     INTEGER,
                        sysExtAlarmInput	   INTEGER,
						sysExtAlarmInputName   DisplayString
                }

        sysExtAlarmInputId      OBJECT-TYPE
                SYNTAX  INTEGER
                ACCESS  read-only
                STATUS  mandatory
                DESCRIPTION
                        "Id of an external alarm indicator. Valid
                         values are: 1 to 6"
                ::= { sysExtAlarmInputEntry 1 }

        sysExtAlarmInput      OBJECT-TYPE
                SYNTAX  INTEGER
					{	off(1), 
						minor(2),
						major(3),
						critical(4),
						na(5)
					}							
                ACCESS  read-write
                STATUS  mandatory
                DESCRIPTION
                        "Configurable value for an external alarm indicator.
						 Default value is off. For old sensor board,
						 the value is na"
                ::= { sysExtAlarmInputEntry 2 }

        sysExtAlarmInputName      OBJECT-TYPE
				SYNTAX  DisplayString (SIZE (0..32))					
                ACCESS  read-write
                STATUS  mandatory
                DESCRIPTION
                        "User configurable name for an external alarm input indicator"
                ::= { sysExtAlarmInputEntry 3 }

		sysAudioAlarm      OBJECT-TYPE
				SYNTAX  INTEGER {
							brief(1),
							test(2),
							continous(3),
							off(4),
							na(5)
						}
				ACCESS  read-write
				STATUS  mandatory
				DESCRIPTION
					   "Mode for audio alarm.
					    Default is off. For old sensor board, it is na"
						::= { systemConfig 18  }  

		sysAudioAlarmSeverity      OBJECT-TYPE
				SYNTAX  INTEGER {
							major(1),
							critical(2),
							minor(3),
							na(4)
						}

				ACCESS  read-write
				STATUS  mandatory
				DESCRIPTION
					   "Controls for audio alarm. When the control is set to
					    minor, it will go off for all minor and up
						alarms. Default is major. For old sensor board,
						it is na. These control only make sense for
						audio alarm in brief or continous mode"
						::= { systemConfig 19  }  
		

        -- The elements in the systemPerf subgroup of the current subgroup

        sysStatus       OBJECT-TYPE
                SYNTAX  CardStatus
                ACCESS  read-only
                STATUS  mandatory
                DESCRIPTION
                        "The global status of the system as computed based on
                         the traps (events) that are generated.  Choices are:
                         Critical, Major, Minor or Normal."
                ::= { systemPerf 1 }

        sysClearStatus  OBJECT-TYPE
                SYNTAX  ResetType
                ACCESS  not-accessible 
                STATUS  mandatory
                DESCRIPTION
                        "Reset the system state to Normal.  The value of reset
                         means set the state to Normal.  A get on this will
			 	 always return other. 
                         Note: This element is now made not-accessible as sysStatus
                         is now a read-only element"
                ::= { systemPerf 2 }

        sysClearCounters OBJECT-TYPE
                SYNTAX  ResetType
                ACCESS  read-write
                STATUS  mandatory
                DESCRIPTION
                        "Reset all performance counters in this 15 minutes time
                         interval to zero.  The value of reset means to reset the
                         counters to zero.  A get on this will always return
			 other."
                ::= { systemPerf 3 }

        sysLastBootTime OBJECT-TYPE
                SYNTAX  DateAndTime
                ACCESS  read-only
                STATUS  mandatory
                DESCRIPTION
                        "The date and time of the last system boot.  This time
                         represents the boot time of a CP card.  It is also
                         anonymous with the power-up cycle of the chassis."
                ::= { systemPerf 4 }

        sysAvailTime    OBJECT-TYPE
                SYNTAX  Counter
                ACCESS  read-only
                STATUS  mandatory
                DESCRIPTION
                        "The number of seconds in this time slot (15 minutes)
                         that the system has been up and running.  This will
                         generally be the same as 15 minutes in seconds (900),
                         but, if the system has been reboot in the last 15
                         minutes interval, then it represents the number of
                         seconds the system has been up.  The criteria for the
                         system available time is having at least one CP
                         running with atmost non-service affecting minor
                         alarm system status"
                ::= { systemPerf 5 }

        sysErrFreeSecs  OBJECT-TYPE
                SYNTAX  Counter
                ACCESS  read-only
                STATUS  mandatory
                DESCRIPTION
                        "The number of seconds in this time slot (15 minutes)
                         that the device has not experienced any alarms.  This
                         counter is across all cards in the chassis.  The
                         system must be in Normal status for this counter to
                         be incremented."
                ::= { systemPerf 6 }

	  sysExhaustTemperature     OBJECT-TYPE
                SYNTAX  INTEGER
                ACCESS  read-only
                STATUS  mandatory
                DESCRIPTION
                        "Temperature of the Chassis.  Units of dgree centigrade."
                ::= { systemPerf 7 }



        -- The elements in the downloadPerf subgroup of the current subgroup

        dlStatus        OBJECT-TYPE
                SYNTAX  DownloadStatus
                ACCESS  read-write 
                STATUS  mandatory
                DESCRIPTION
                        "The global status of the download task.  The download task 
				(download to the device) is either ftp_inprogress, module 
				update inprogrss or currently idle.  Since only one download 
				at the time is handled by the system, this flag is set to 
				inprogress as soon as any download starts.  
				It is reset back to idle when the download is completed.  
				This flag is set to idle on system startup.  This flag 
				can be remotely set to idle if a previous FTP download 
				was interrupted."
                ::= { downloadPerf 1 }

        dlOkDownloads   OBJECT-TYPE
                SYNTAX  Counter
                ACCESS  read-only 
                STATUS  mandatory
                DESCRIPTION
                        "The number of successful downloads in this time
                         interval (15 minutes)."
                ::= { downloadPerf 2 }

        dlBadDownloads  OBJECT-TYPE
                SYNTAX  Counter
                ACCESS  read-only 
                STATUS  mandatory
                DESCRIPTION
                        "The number of failed downloads in this time
                         interval (15 minutes)."
                ::= { downloadPerf 3 }

        dlLongestTime   OBJECT-TYPE
                SYNTAX  Gauge
                ACCESS  read-only 
                STATUS  mandatory
                DESCRIPTION
                        "Longest time for any download, in seconds, in this
                         time interval (15 minutes)."
                ::= { downloadPerf 4 }

        dlLongestSize   OBJECT-TYPE
                SYNTAX  Gauge
                ACCESS  read-only 
                STATUS  mandatory
                DESCRIPTION
                        "Longest download size for any download, in bytes, in
                         this time interval (15 minutes)."
                ::= { downloadPerf 5 }


        -- The elements in the cpPerf subgroup of the current subgroup

        cpNumEvents     OBJECT-TYPE
                SYNTAX  Counter
                ACCESS  read-only
                STATUS  mandatory
                DESCRIPTION
                        "Total number of events received by the active CP in
                         this time slot (15 minutes)."
                ::= { cpPerf 1 }

        cpTrapsSent     OBJECT-TYPE
                SYNTAX  Counter
                ACCESS  read-only
                STATUS  mandatory
                DESCRIPTION
                        "Total number of traps sent by the active CP in
                         this time slot (15 minutes)."
                ::= { cpPerf 2 }

        cpSNMPCmdsRcvd  OBJECT-TYPE
                SYNTAX  Counter
                ACCESS  read-only
                STATUS  mandatory
                DESCRIPTION
                        "Total number of SNMP commands received by the active
                         CP in this time slot (15 minutes)."
                ::= { cpPerf 3 }

        cpCounterFlag   OBJECT-TYPE
                SYNTAX  FlagType
                ACCESS  read-write
                STATUS  mandatory
                DESCRIPTION
                        "Turns software counters On or Off."
                ::= { cpPerf 4 }

        cpCntrTable     OBJECT-TYPE
                SYNTAX  SEQUENCE OF CpCntrEntry
                ACCESS  not-accessible
                STATUS  mandatory
                DESCRIPTION
                        "This table represents the information for each
                         entry of the software counters.  It is only 
			 applicable to the active MPM card."
                ::= { cpPerf 5 }

        cpCntrEntry     OBJECT-TYPE
                SYNTAX  CpCntrEntry
                ACCESS  not-accessible
                STATUS  mandatory
                DESCRIPTION
                        "Specifies the index for each row in the table below"
                INDEX { cpCntrShelf, cpCntrSlot, cpCntrType }
                ::= { cpCntrTable 1 }

        CpCntrEntry     ::=
                SEQUENCE {
                        cpCntrShelf     CardShelf,
                        cpCntrSlot      INTEGER,
                        cpCntrType      INTEGER,
                        cpTotPktSent    Counter,
                        cpTotPktRcvd    Counter,
                        cpBadPktRcvd    Counter,
                        cpTotBadTrans   Counter,
                        cpBytesSent     Counter,
                        cpBytesRcvd     Counter,
                        cpMsgsDlvrd     Counter,
                        cpBufAllocFail  Counter,
                        cpEcbAllocFail  Counter,
                        cpClearCntrs    ResetType
                }

        cpCntrShelf     OBJECT-TYPE
                SYNTAX  CardShelf
                ACCESS  read-only
                STATUS  mandatory
                DESCRIPTION
                        "The shelf the card is in.  Valid values are: 1 to 2.
                         The system automatically determines the right value
                         for this entry based on the value of the current
                         active CP card."
                ::= { cpCntrEntry 1 }

        cpCntrSlot      OBJECT-TYPE
                SYNTAX  CardSlot
                ACCESS  read-only
                STATUS  mandatory
                DESCRIPTION
                        "The slot within the shelf the card is in.  Valid
                         values are: 1 to 2.  The system automatically
                         determines the right value for this entry based
                         on the value of the current active CP card."
                ::= { cpCntrEntry 2 }

        cpCntrType      OBJECT-TYPE
                SYNTAX  INTEGER { spi(1) }
                ACCESS  read-only
                STATUS  mandatory
                DESCRIPTION
                        "The type of the software counter data in this row.
                         The data is collected for the SPI data channels."
                ::= { cpCntrEntry 3 }

        cpTotPktSent    OBJECT-TYPE
                SYNTAX  Counter
                ACCESS  read-only
                STATUS  mandatory
                DESCRIPTION
                        "The number of data packets sent over the given data
                         channel."
                ::= { cpCntrEntry 4 }

        cpTotPktRcvd    OBJECT-TYPE
                SYNTAX  Counter
                ACCESS  read-only
                STATUS  mandatory
                DESCRIPTION
                        "The number of data packets received over the given
                         data channel."
                ::= { cpCntrEntry 5 }

        cpBadPktRcvd    OBJECT-TYPE
                SYNTAX  Counter
                ACCESS  read-only
                STATUS  mandatory
                DESCRIPTION
                        "The number of bad data packets received over the given
                         data channel."
                ::= { cpCntrEntry 6 }

        cpTotBadTrans   OBJECT-TYPE
                SYNTAX  Counter
                ACCESS  read-only
                STATUS  mandatory
                DESCRIPTION
                        "The number of bad data transmissions over the given
                         data channel."
                ::= { cpCntrEntry 7 }

        cpBytesSent     OBJECT-TYPE
                SYNTAX  Counter
                ACCESS  read-only
                STATUS  mandatory
                DESCRIPTION
                        "Total number of bytes sent over the given
                         data channel."
                ::= { cpCntrEntry 8 }

        cpBytesRcvd     OBJECT-TYPE
                SYNTAX  Counter
                ACCESS  read-only
                STATUS  mandatory
                DESCRIPTION
                        "Total number of data bytes received over the given
                         data channel."
                ::= { cpCntrEntry 9 }

        cpMsgsDlvrd     OBJECT-TYPE
                SYNTAX  Counter
                ACCESS  read-only
                STATUS  mandatory
                DESCRIPTION
                        "The number of complete messages delivered over the
                         given data channel."
                ::= { cpCntrEntry 10 }

        cpBufAllocFail  OBJECT-TYPE
                SYNTAX  Counter
                ACCESS  read-only
                STATUS  mandatory
                DESCRIPTION
                        "Number of buffer allocation failures for the given
                         data channel."
                ::= { cpCntrEntry 11 }

        cpEcbAllocFail  OBJECT-TYPE
                SYNTAX  Counter
                ACCESS  read-only
                STATUS  mandatory
                DESCRIPTION
                        "Number of Event Control Block allocation failures
                         for the given data channel."
                ::= { cpCntrEntry 12 }

        cpClearCntrs    OBJECT-TYPE
                SYNTAX  ResetType
                ACCESS  read-write
                STATUS  mandatory
                DESCRIPTION
                        "If the value is reset, all software counters for this
                         15 minute interval are reset to zero.  A get on this
			 will always return other"
                ::= { cpCntrEntry 13 }

        cpPerfTable     OBJECT-TYPE
                SYNTAX  SEQUENCE OF CpPerfEntry
                ACCESS  not-accessible
                STATUS  mandatory
                DESCRIPTION
                        "This table represents the information for performance
                         data collected for each communication processor"
                ::= { cpPerf 6 }

        cpPerfEntry     OBJECT-TYPE
                SYNTAX  CpPerfEntry
                ACCESS  not-accessible
                STATUS  mandatory
                DESCRIPTION
                        "Specifies the index for each row in the table below"
                INDEX { cpPerfShelf, cpPerfSlot }
                ::= { cpPerfTable 1 }

        CpPerfEntry     ::=
                SEQUENCE {
                        cpPerfShelf     CardShelf,
                        cpPerfSlot      INTEGER,
                        cpPerfMode      RedundancyMode,
                        cpPerfState     CardState,
                        cpPerfStatus    CardStatus,
                        cpLastBootTime  DateAndTime,
                        cpAvailTime     Counter,
                        cpErrFreeSecs   Counter
                }

        cpPerfShelf     OBJECT-TYPE
                SYNTAX  CardShelf
                ACCESS  read-only
                STATUS  mandatory
                DESCRIPTION
                        "The shelf the card is in.  Valid values are: 1 to 2"
                ::= { cpPerfEntry 1 }

        cpPerfSlot      OBJECT-TYPE
                SYNTAX  CardSlot
                ACCESS  read-only
                STATUS  mandatory
                DESCRIPTION
                        "The slot within the shelf the card is in.  Valid
                         values are: 1 to 3"
                ::= { cpPerfEntry 2 }

        cpPerfMode      OBJECT-TYPE
                SYNTAX  RedundancyMode
                ACCESS  read-only
                STATUS  mandatory
                DESCRIPTION
                        "The valid types are: active CP or standby CP"
                ::= { cpPerfEntry 3 }

        cpPerfState     OBJECT-TYPE
                SYNTAX  CardState
                ACCESS  read-only
                STATUS  mandatory
                DESCRIPTION
                        "The status of the communication card.  The status'
                         are: online, offline, empty, loopback or diagnostics."
                ::= { cpPerfEntry 4 }

        cpPerfStatus    OBJECT-TYPE
                SYNTAX  CardStatus
                ACCESS  read-only
                STATUS  mandatory
                DESCRIPTION
                        "The status of the communication processor.  This
                         status represents the state of the communication
                         processor and in general is different from the
                         status of the system."
                ::= { cpPerfEntry 5 }

        cpLastBootTime  OBJECT-TYPE
                SYNTAX  DateAndTime
                ACCESS  read-only
                STATUS  mandatory
                DESCRIPTION
                        "The date and time of the last boot for this CP."
                ::= { cpPerfEntry 6 }

        cpAvailTime     OBJECT-TYPE
                SYNTAX  Counter
                ACCESS  read-only
                STATUS  mandatory
                DESCRIPTION
                        "The number of seconds in this time slot (15 minutes)
                         that this CP has been up and running.  This will
                         generally be the same as 15 minutes in seconds (900)."
                ::= { cpPerfEntry 7 }

        cpErrFreeSecs   OBJECT-TYPE
                SYNTAX  Counter
                ACCESS  read-only
                STATUS  mandatory
                DESCRIPTION
                        "The number of seconds in this time slot (15 minutes)
                         that this CP has not experienced any alarms."
                ::= { cpPerfEntry 8 }


        -- The elements in the ccPerf subgroup of the current subgroup

        ccNumEvents     OBJECT-TYPE
                SYNTAX  Counter
                ACCESS  read-only
                STATUS  mandatory
                DESCRIPTION
                        "Total number of events received for all CC's in
                         this time slot (15 minutes)."
                ::= { ccPerf 1 }

        ccCntrTable     OBJECT-TYPE
                SYNTAX  SEQUENCE OF CcCntrEntry
                ACCESS  not-accessible
                STATUS  mandatory
                DESCRIPTION
                        "This table represents the information for each
                         entry for the software counters."
                ::= { ccPerf 2 }

        ccCntrEntry     OBJECT-TYPE
                SYNTAX  CcCntrEntry
                ACCESS  not-accessible
                STATUS  mandatory
                DESCRIPTION
                        "Specifies the index for each row in the table below"
                INDEX { ccCntrLocation, ccCntrShelf, ccCntrSlot, ccCntrType }
                ::= { ccCntrTable 1 }

        CcCntrEntry     ::=
                SEQUENCE {
                        ccCntrLocation  CardLocation,
                        ccCntrShelf     CardShelf,
                        ccCntrSlot      INTEGER,
                        ccCntrType      INTEGER,
                        ccCounterFlag   FlagType,
                        ccTotPktSent    Counter,
                        ccTotPktRcvd    Counter,
                        ccBadPktRcvd    Counter,
                        ccTotBadTrans   Counter,
                        ccBytesSent     Counter,
                        ccBytesRcvd     Counter,
                        ccMsgsDlvrd     Counter,
                        ccBufAllocFail  Counter,
                        ccEcbAllocFail  Counter,
                        ccClearCntrs    ResetType
                }

        ccCntrLocation  OBJECT-TYPE
                SYNTAX  CardLocation
                ACCESS  read-only
                STATUS  mandatory
                DESCRIPTION
                        "The location of the CC card.  The values are: Local
                         or Remote.  The system automatically determines the
                         right value for this entry based on the known
                         CC cards."
                ::= { ccCntrEntry 1 }

        ccCntrShelf     OBJECT-TYPE
                SYNTAX  CardShelf
                ACCESS  read-only
                STATUS  mandatory
                DESCRIPTION
                        "The shelf the card is in.  Valid values are: 1 to 10.
                         The system automatically determines the right value
                         for this entry based on the known (available) CC
                         cards."
                ::= { ccCntrEntry 2 }

        ccCntrSlot      OBJECT-TYPE
                SYNTAX  CardSlot
                ACCESS  read-only
                STATUS  mandatory
                DESCRIPTION
                        "The slot within the shelf the card is in.  Valid
                         values are: 4 to 42.  The system automatically
                         determines the right value for this entry based
                         on the known (available) CC cards."
                ::= { ccCntrEntry 3 }

	ccCntrType      OBJECT-TYPE
		SYNTAX  INTEGER { spi(1), iwm(2) }
		ACCESS  read-only
		STATUS  mandatory
		DESCRIPTION
                        "The type of the software counter data in this row.
                         The data is collected for the SPI data channels."
                ::= { ccCntrEntry 4 }

	ccCounterFlag   OBJECT-TYPE
		SYNTAX  FlagType
		ACCESS  read-write
		STATUS  mandatory
		DESCRIPTION
			"Turns software counters, both On or both Off for this CC.
			 When set to Off, both counters statistic information will
			 be cleared."
                ::= { ccCntrEntry 5 }

        ccTotPktSent    OBJECT-TYPE
                SYNTAX  Counter
                ACCESS  read-only
                STATUS  mandatory
                DESCRIPTION
                        "The number of data packets sent over the given data
                         channel."
                ::= { ccCntrEntry 6 }

        ccTotPktRcvd    OBJECT-TYPE
                SYNTAX  Counter
                ACCESS  read-only
                STATUS  mandatory
                DESCRIPTION
                        "The number of data packets received over the given
                         data channel."
                ::= { ccCntrEntry 7 }

        ccBadPktRcvd    OBJECT-TYPE
                SYNTAX  Counter
                ACCESS  read-only
                STATUS  mandatory
                DESCRIPTION
                        "The number of bad data packets received over the given
                         data channel."
                ::= { ccCntrEntry 8 }

        ccTotBadTrans   OBJECT-TYPE
                SYNTAX  Counter
                ACCESS  read-only
                STATUS  mandatory
                DESCRIPTION
                        "The number of bad data transmissions over the given
                         data channel."
                ::= { ccCntrEntry 9 }

        ccBytesSent     OBJECT-TYPE
                SYNTAX  Counter
                ACCESS  read-only
                STATUS  mandatory
                DESCRIPTION
                        "Total number of bytes sent over the given
                         data channel."
                ::= { ccCntrEntry 10 }

        ccBytesRcvd     OBJECT-TYPE
                SYNTAX  Counter
                ACCESS  read-only
                STATUS  mandatory
                DESCRIPTION
                        "Total number of data bytes received over the given
                         data channel."
                ::= { ccCntrEntry 11 }

        ccMsgsDlvrd     OBJECT-TYPE
                SYNTAX  Counter
                ACCESS  read-only
                STATUS  mandatory
                DESCRIPTION
                        "The number of complete messages delivered over the
                         given data channel."
                ::= { ccCntrEntry 12 }

        ccBufAllocFail  OBJECT-TYPE
                SYNTAX  Counter
                ACCESS  read-only
                STATUS  mandatory
                DESCRIPTION
                        "Number of buffer allocation failures for the given
                         data channel."
                ::= { ccCntrEntry 13 }

        ccEcbAllocFail  OBJECT-TYPE
                SYNTAX  Counter
                ACCESS  read-only
                STATUS  mandatory
                DESCRIPTION
                        "Number of Event Control Block allocation failures
                         for the given data channel."
                ::= { ccCntrEntry 14 }

        ccClearCntrs    OBJECT-TYPE
                SYNTAX  ResetType
                ACCESS  read-write
                STATUS  mandatory
                DESCRIPTION
                        "If the value is reset, all software counters for this
                         15 minute interval are reset to zero.  A get on this
			 will always return other"
                ::= { ccCntrEntry 15 }

        ccPerfTable     OBJECT-TYPE
                SYNTAX  SEQUENCE OF CcPerfEntry
                ACCESS  not-accessible
                STATUS  mandatory
                DESCRIPTION
                        "This table represents the information for performance
                         data collected for each channel card"
                ::= { ccPerf 3 }

        ccPerfEntry     OBJECT-TYPE
                SYNTAX  CcPerfEntry
                ACCESS  not-accessible
                STATUS  mandatory
                DESCRIPTION
                        "Specifies the index for each row in the table below"
                INDEX { ccPerfLocation, ccPerfShelf, ccPerfSlot }
                ::= { ccPerfTable 1 }

        CcPerfEntry     ::=
                SEQUENCE {
                        ccPerfLocation  CardLocation,
                        ccPerfShelf     CardShelf,
                        ccPerfSlot      INTEGER,
                        ccPerfState     CardState,
                        ccPerfStatus    CardStatus,
                        ccLastBootTime  DateAndTime,
                        ccAvailTime     Counter,
                        ccErrFreeSecs   Counter,
                        ccBiasCurrent   INTEGER,
                        ccModulation    INTEGER,
                        ccApc           INTEGER,
                        ccIwmModulation INTEGER,
                        ccLaserOnOff    FlagType,
                        ccTemperature   Gauge,
                        ccIntensity     Gauge,
                        ccSignalStrength Gauge,
                        ccLossOfLight   Boolean,
                        ccSignalDetect  Boolean,
                        ccRefClock      INTEGER,
                        ccClockDiv      INTEGER,
				ccLinkTxPwrStatus	INTEGER,
				ccLinkRxSigStrStatus	INTEGER,
				ccCpeRxSigDetect		INTEGER,
				ccLinkIWMStatus		INTEGER,
				ccLinkSummaryStatus	INTEGER,
				ccProtectionMode	INTEGER,
				ccLinkRxSigStr		DisplayString
                }

        ccPerfLocation  OBJECT-TYPE
                SYNTAX  CardLocation
                ACCESS  read-only
                STATUS  mandatory
                DESCRIPTION
                        "The location of the card.  Valid choices are Local
                         or Remote.  The system automatically selects this
                         value based on the known (available) CC cards."
                ::= { ccPerfEntry 1 }

        ccPerfShelf     OBJECT-TYPE
                SYNTAX  CardShelf
                ACCESS  read-only
                STATUS  mandatory
                DESCRIPTION
                        "The shelf the card is in.  Valid values are: 1 to 10"
                ::= { ccPerfEntry 2 }

        ccPerfSlot      OBJECT-TYPE
                SYNTAX  CardSlot
                ACCESS  read-only
                STATUS  mandatory
                DESCRIPTION
                        "The slot within the shelf the card is in.  Valid
                         values are: 4 to 42"
                ::= { ccPerfEntry 3 }

        ccPerfState     OBJECT-TYPE
                SYNTAX  CardState
                ACCESS  read-only
                STATUS  mandatory
                DESCRIPTION
                        "The state of the channel card.  The states'
                         are: online, offline, empty, loopback or diagnostics."
                ::= { ccPerfEntry 4 }

        ccPerfStatus    OBJECT-TYPE
                SYNTAX  CardStatus
                ACCESS  read-only
                STATUS  mandatory
                DESCRIPTION
                        "The status of the channel card.  This
                         status represents the status of the communication
                         processor and in general is different from the
                         status of the system."
                ::= { ccPerfEntry 5 }

        ccLastBootTime  OBJECT-TYPE
                SYNTAX  DateAndTime
                ACCESS  read-only
                STATUS  mandatory
                DESCRIPTION
                        "The date and time of the last boot for this card."
                ::= { ccPerfEntry 6 }

        ccAvailTime     OBJECT-TYPE
                SYNTAX  Counter
                ACCESS  read-only
                STATUS  mandatory
                DESCRIPTION
                        "The number of seconds in this time slot (15 minutes)
                         that this CC has been up and running.  This will
                         generally be the same as 15 minutes in seconds (900)."
                ::= { ccPerfEntry 7 }

        ccErrFreeSecs   OBJECT-TYPE
                SYNTAX  Counter
                ACCESS  read-only
                STATUS  mandatory
                DESCRIPTION
                        "The number of seconds in this time slot (15 minutes)
                         that this CC has not experienced any alarms."
                ::= { ccPerfEntry 8 }

        ccBiasCurrent   OBJECT-TYPE
                SYNTAX  INTEGER
                ACCESS  read-only
                STATUS  mandatory
                DESCRIPTION
                        "Bias current for the optical laser."
                ::= { ccPerfEntry 9 }

        ccModulation    OBJECT-TYPE
                SYNTAX  INTEGER
                ACCESS  read-only
                STATUS  mandatory
                DESCRIPTION
                        "The frequency modulation for the optical laser."
                ::= { ccPerfEntry 10 }

        ccApc           OBJECT-TYPE
                SYNTAX  INTEGER
                ACCESS  read-only
                STATUS  mandatory
                DESCRIPTION
                        "The APC value."
                ::= { ccPerfEntry 11 }

        ccIwmModulation OBJECT-TYPE
                SYNTAX  INTEGER
                ACCESS  read-only
                STATUS  mandatory
                DESCRIPTION
                        "The frequency modulation for the IWM channel."
                ::= { ccPerfEntry 12 }

        ccLaserOnOff    OBJECT-TYPE
                SYNTAX  FlagType
                ACCESS  read-only
                STATUS  mandatory
                DESCRIPTION
                        "The laser On/Off flag."
                ::= { ccPerfEntry 13 }

        ccTemperature   OBJECT-TYPE
                SYNTAX  Gauge
                ACCESS  read-only
                STATUS  mandatory
                DESCRIPTION
                        "The current temperature, or the operating temperature
                         of the optical device."
                ::= { ccPerfEntry 14 }

        ccIntensity     OBJECT-TYPE
                SYNTAX  Gauge
                ACCESS  read-only
                STATUS  mandatory
                DESCRIPTION
                        "The intensity of the optical light."
                ::= { ccPerfEntry 15 }

        ccSignalStrength OBJECT-TYPE
                SYNTAX  Gauge
                ACCESS  read-only
                STATUS  mandatory
                DESCRIPTION
                        "The current signal strength for the optical path."
                ::= { ccPerfEntry 16 }

        ccLossOfLight   OBJECT-TYPE
                SYNTAX  Boolean
                ACCESS  read-only
                STATUS  mandatory
                DESCRIPTION
                        "If set to true, no laser light is present.  If set to
                         false, no loss of light has occurred."
                ::= { ccPerfEntry 17 }

        ccSignalDetect  OBJECT-TYPE
                SYNTAX  Boolean
                ACCESS  not-accessible
                STATUS  mandatory
                DESCRIPTION
                        "If set to true, signal is detected.  If set to false,
                         no signal is present. Replaced with ccCpeRxSigDetect"
                ::= { ccPerfEntry 18 }

        ccRefClock      OBJECT-TYPE
                SYNTAX  INTEGER { 	en1660(1),
    						en1944(2),
    						en1953(3)
				}
                ACCESS  not-accessible
                STATUS  mandatory
                DESCRIPTION
                        "The value of the reference clock in decimal notation.
                         For a given value, like 1660, the actual value is
                         16.60-EN.  In otherwords, assume a two digit decimal
                         point, plus any appropriate scaling factor."
                ::= { ccPerfEntry 19 }

        ccClockDiv      OBJECT-TYPE
                SYNTAX  INTEGER { dout-1250(1), dout-622(2), dout-155(3) }
                ACCESS  not-accessible
                STATUS  mandatory
                DESCRIPTION
                        "The clock divisor.  Values are 1250, 622 or 155 in the
                         appropriate clock frequency scale."
                ::= { ccPerfEntry 20 }

        ccLinkTxPwrStatus      OBJECT-TYPE
                SYNTAX  INTEGER { ok(1), fault(2) }
                ACCESS  read-only
                STATUS  mandatory
                DESCRIPTION
                        "This indicates whether the link transmit power is within the
				  normal range of operation."
                ::= { ccPerfEntry 21 }

        ccLinkRxSigStrStatus      OBJECT-TYPE
                SYNTAX  INTEGER { ok(1), fault(2) }
                ACCESS  read-only
                STATUS  mandatory
                DESCRIPTION
                        "This indicates whether the link's receive signal is within the
				  normal range of operation."
                ::= { ccPerfEntry 22 }

        ccCpeRxSigDetect      OBJECT-TYPE
                SYNTAX  INTEGER { yes(1), no(2)}
                ACCESS  read-only
                STATUS  mandatory
                DESCRIPTION
                        "This indicates whether there is presence of CPE receive signal"
                ::= { ccPerfEntry 23 }

        ccLinkIWMStatus      OBJECT-TYPE
                SYNTAX  INTEGER { ok(1), error(2), notApplicable(3) }
                ACCESS  read-only
                STATUS  mandatory
                DESCRIPTION
                        "This indicates the current status of IWM. This value is only
			 applicable to remote OCMs"
                ::= { ccPerfEntry 24 }

        ccLinkSummaryStatus      OBJECT-TYPE
                SYNTAX  INTEGER { ok(1), fault(2), notApplicable(3) }
                ACCESS  read-only
                STATUS  mandatory
                DESCRIPTION
                        "This is the result of a logical and operation of all the individual
			 link status. If any of the attributes is N/A, except for the local
			 local IWM status, this value is N/A"
                ::= { ccPerfEntry 25 }

		ccProtectionMode      OBJECT-TYPE
                SYNTAX  INTEGER 
				{ 
						working(1),  
						protection(2),
						na(3) 
				}
                ACCESS  read-only
                STATUS  mandatory
                DESCRIPTION
                        "UPSR Protection Mode:  active, standby and n/a."
                ::= { ccPerfEntry 26 }

        ccLinkRxSigStr 	OBJECT-TYPE
                SYNTAX  DisplayString
                ACCESS  read-only
                STATUS  mandatory
                DESCRIPTION
                        "Link's received signal strength in dBm."
                ::= { ccPerfEntry 27 }


        -- The elements in the muxPerf subgroup of the current subgroup

        muxNumEvents    OBJECT-TYPE
                SYNTAX  Counter
                ACCESS  read-only
                STATUS  mandatory
                DESCRIPTION
                        "Total number of all traps (events) generated by all
                         MUX's in this time slot (15 minutes)."
                ::= { muxPerf 1 }
	

        muxPerfTable    OBJECT-TYPE
                SYNTAX  SEQUENCE OF MuxPerfEntry
                ACCESS  not-accessible
                STATUS  mandatory
                DESCRIPTION
                        "This table represents the information for performance
                         data collected for each mux/demux card"
                ::= { muxPerf 2 }

        muxPerfEntry    OBJECT-TYPE
                SYNTAX  MuxPerfEntry
                ACCESS  not-accessible
                STATUS  mandatory
                DESCRIPTION
                        "Specifies the index for each row in the table below"
                INDEX { muxPerfLocation, muxPerfShelf, muxPerfSlot }
                ::= { muxPerfTable 1 }

        MuxPerfEntry    ::=
                SEQUENCE {
                        muxPerfLocation CardLocation,
                        muxPerfShelf    CardShelf,
                        muxPerfSlot     INTEGER,
                        muxType         INTEGER,
                        muxPerfState    CardState,
                        muxPerfStatus   CardStatus,
                        muxLastBootTime DateAndTime,
                        muxAvailTime    Counter,
                        muxErrFreeSecs  Counter
                }

        muxPerfLocation OBJECT-TYPE
                SYNTAX  CardLocation
                ACCESS  read-only
                STATUS  mandatory
                DESCRIPTION
                        "The location of the card.  Choices are local or
                         remote."
                ::= { muxPerfEntry 1 }

        muxPerfShelf    OBJECT-TYPE
                SYNTAX  CardShelf
                ACCESS  read-only
                STATUS  mandatory
                DESCRIPTION
                        "The shelf the card is in.  Valid values are: 1 to 10"
                ::= { muxPerfEntry 2 }

        muxPerfSlot     OBJECT-TYPE
                SYNTAX  CardSlot
                ACCESS  read-only
                STATUS  mandatory
                DESCRIPTION
                        "The slot within the shelf the card is in.  Valid
                         values are: 1 to 42"
                ::= { muxPerfEntry 3 }

        muxType         OBJECT-TYPE
                SYNTAX  INTEGER { mux(4), demux(5), w4cd(10), w2cmd(13), w4cm(21)}
                ACCESS  read-only
                STATUS  mandatory
                DESCRIPTION
                        "The type of the mux.  The choices are: mux or demux."
                ::= { muxPerfEntry 4 }

        muxPerfState    OBJECT-TYPE
                SYNTAX  CardState
                ACCESS  read-only
                STATUS  mandatory
                DESCRIPTION
                        "The state of the mux card.  The states are:
                         online, offline, empty, loopback or diag."
                ::= { muxPerfEntry 5 }

        muxPerfStatus   OBJECT-TYPE
                SYNTAX  CardStatus
                ACCESS  read-only
                STATUS  mandatory
                DESCRIPTION
                        "The status of the mux card.  This status represents
                         the status of the mux card and in general is
                         different from the status of the system."
                ::= { muxPerfEntry 6 }

        muxLastBootTime OBJECT-TYPE
                SYNTAX  DateAndTime
                ACCESS  read-only
                STATUS  mandatory
                DESCRIPTION
                        "The date and time of the last boot for this card."
                ::= { muxPerfEntry 7 }

        muxAvailTime    OBJECT-TYPE
                SYNTAX  Counter
                ACCESS  read-only
                STATUS  mandatory
                DESCRIPTION
                        "The number of seconds in this time slot (15 minutes)
                         that this Mux has been up and running.  This will
                         generally be the same as 15 minutes in seconds (900)."
                ::= { muxPerfEntry 8 }

        muxErrFreeSecs  OBJECT-TYPE
                SYNTAX  Counter
                ACCESS  read-only
                STATUS  mandatory
                DESCRIPTION
                        "The number of seconds in this time slot (15 minutes)
                         that this mux has not experienced any alarms."
                ::= { muxPerfEntry 9 }


        -- The elements in the psPerf subgroup of the current subgroup

        psNumEvents     OBJECT-TYPE
                SYNTAX  Counter
                ACCESS  read-only
                STATUS  mandatory
                DESCRIPTION
                        "Total number of all traps (events) generated by all
                         Power Supplies in this time slot (15 minutes)."
                ::= { psPerf 1 }

        psVoltageLevel3pt4Volt     OBJECT-TYPE
                SYNTAX  DisplayString (SIZE (0..10))
                ACCESS  read-only
                STATUS  mandatory
                DESCRIPTION
                        "Voltage Level of the 3.4 V power supply."  
                ::= { psPerf 2 }

        psVoltageLevel5pt1Volt      OBJECT-TYPE
                SYNTAX  DisplayString (SIZE (0..10))
                ACCESS  read-only
                STATUS  mandatory
                DESCRIPTION
                        "Voltage Level of the 5.1 V power supply."  
                ::= { psPerf 3 }

        psVoltageLevel12Volt     OBJECT-TYPE
                SYNTAX  DisplayString (SIZE (0..10))
                ACCESS  read-only
                STATUS  mandatory
                DESCRIPTION
                        "Voltage Level of the 12 V power supply."  
                ::= { psPerf 4 }

        psPerfTable     OBJECT-TYPE
                SYNTAX  SEQUENCE OF PsPerfEntry
                ACCESS  not-accessible
                STATUS  mandatory
                DESCRIPTION
                        "This table represents the information for performance
                         data collected for each power supply card"
                ::= { psPerf 5 }

        psPerfEntry     OBJECT-TYPE
                SYNTAX  PsPerfEntry
                ACCESS  not-accessible
                STATUS  mandatory
                DESCRIPTION
                        "Specifies the index for each row in the table below"
                INDEX { psPerfID }
                ::= { psPerfTable 1 }

        PsPerfEntry     ::=
                SEQUENCE {
                        psPerfID	INTEGER,
                        psPerfType      RedundancyMode,
                        psPerfState     INTEGER,
                        psPerfStatus    CardStatus
                }

        psPerfID     OBJECT-TYPE
                SYNTAX  INTEGER
                ACCESS  read-only
                STATUS  mandatory
                DESCRIPTION
                        "The module ID where the PS is plugged in."
                ::= { psPerfEntry 1 }

        psPerfType      OBJECT-TYPE
                SYNTAX  RedundancyMode
                ACCESS  not-accessible
                STATUS  mandatory
                DESCRIPTION
                        "The type of the power supply card.  The choices are:
                         active (primary PS) or standby."
                ::= { psPerfEntry 2 }


        psPerfState     OBJECT-TYPE
                SYNTAX  INTEGER  { psEmpty(1),
                                   psOK(2),
				   psFailed(3),
				   psDegrade(4)
				 }
                ACCESS  read-only
                STATUS  mandatory
                DESCRIPTION
                        "The state of the power supply module."
                ::= { psPerfEntry 3 }

        psPerfStatus    OBJECT-TYPE
                SYNTAX  CardStatus
                ACCESS  read-only
                STATUS  mandatory
                DESCRIPTION
                        "The status of the power supply module.  This status
                         represents the status of the ps module and in general is
                         different from the status of the system."
                ::= { psPerfEntry 4 }

		psVoltageLevelFeedA     OBJECT-TYPE
                SYNTAX  DisplayString (SIZE (0..10))
                ACCESS  read-only
                STATUS  mandatory
                DESCRIPTION
					"Voltage Level of the -48 VDC input from Feed A."  
                ::= { psPerf 6 }

		psVoltageLevelFeedB     OBJECT-TYPE
                SYNTAX  DisplayString (SIZE (0..10))
                ACCESS  read-only
                STATUS  mandatory
                DESCRIPTION
					"Voltage Level of the -48 VDC input from Feed B."  
                ::= { psPerf 7 }

		psBreakerConditionFeedA     OBJECT-TYPE
                SYNTAX  INTEGER
							{	open(1),
								closed(2),
								na(3)
							}
                ACCESS  read-only
                STATUS  mandatory
                DESCRIPTION
					"State of Feed A breaker."  
                ::= { psPerf 8 }

		psPerfStatusFeedA     OBJECT-TYPE
                SYNTAX  INTEGER
							{	feedOK(1),
								feedFAILED(2),
								feedUNKNOWN(3),
								na(4)
							}
                ACCESS  read-only
                STATUS  mandatory
                DESCRIPTION
					"State of Feed A breaker. Failed if it
					 goes into shutdown condition
					 Unknown if the corresponding breaker
					 is open"  
                ::= { psPerf 9 }

		psBreakerConditionFeedB     OBJECT-TYPE
                SYNTAX  INTEGER
							{	open(1),
								closed(2),
								na(3)
							}
                ACCESS  read-only
                STATUS  mandatory
                DESCRIPTION
					"State of Feed B breaker."  
                ::= { psPerf 10 }

		psPerfStatusFeedB     OBJECT-TYPE
                SYNTAX  INTEGER
							{	feedOK(1),
								feedFAILED(2),
								feedUNKNOWN(3),
								na(4)
							}
                ACCESS  read-only
                STATUS  mandatory
                DESCRIPTION
					"State of Feed B.
					 Failed if it goes into shutdown condition
					 Unknown if the corresponding breaker is open"
                ::= { psPerf 11 }



        -- The elements in the fadmPerf subgroup of the current subgroup

        fadmNumEvents    OBJECT-TYPE
                SYNTAX  Counter
                ACCESS  read-only
                STATUS  mandatory
                DESCRIPTION
                        "Total number of all traps (events) generated by all
                         MUX's in this time slot (15 minutes)."
                ::= { fadmPerf 1 }

        fadmPerfTable    OBJECT-TYPE
                SYNTAX  SEQUENCE OF FadmPerfEntry
                ACCESS  not-accessible
                STATUS  mandatory
                DESCRIPTION
                        "This table represents the information for performance
                         data collected for each fadm card"
                ::= { fadmPerf 2 }

        fadmPerfEntry    OBJECT-TYPE
                SYNTAX  FadmPerfEntry
                ACCESS  not-accessible
                STATUS  mandatory
                DESCRIPTION
                        "Specifies the index for each row in the table below"
                INDEX { fadmPerfLocation, fadmPerfShelf, fadmPerfSlot }
                ::= { fadmPerfTable 1 }

        FadmPerfEntry    ::=
                SEQUENCE {
                        fadmPerfLocation CardLocation,
                        fadmPerfShelf    CardShelf,
                        fadmPerfSlot     INTEGER,
                        fadmPerfState    CardState,
                        fadmPerfStatus   CardStatus,
                        fadmLastBootTime DateAndTime,
                        fadmAvailTime    Counter,
                        fadmErrFreeSecs  Counter
                }

        fadmPerfLocation OBJECT-TYPE
                SYNTAX  CardLocation
                ACCESS  read-only
                STATUS  mandatory
                DESCRIPTION
                        "The location of the card.  Choices are local or
                         remote."
                ::= { fadmPerfEntry 1 }

        fadmPerfShelf    OBJECT-TYPE
                SYNTAX  CardShelf
                ACCESS  read-only
                STATUS  mandatory
                DESCRIPTION
                        "The shelf the card is in.  Valid values are: 1 to 10"
                ::= { fadmPerfEntry 2 }

        fadmPerfSlot     OBJECT-TYPE
                SYNTAX  CardSlot
                ACCESS  read-only
                STATUS  mandatory
                DESCRIPTION
                        "The slot within the shelf the card is in.  Valid
                         values are: 1 to 42"
                ::= { fadmPerfEntry 3 }

        fadmPerfState    OBJECT-TYPE
                SYNTAX  CardState
                ACCESS  read-only
                STATUS  mandatory
                DESCRIPTION
                        "The status of the fadm card.  The states are:
                         online, offline, empty, loopback or diag."
                ::= { fadmPerfEntry 4 }

        fadmPerfStatus   OBJECT-TYPE
                SYNTAX  CardStatus
                ACCESS  read-only
                STATUS  mandatory
                DESCRIPTION
                        "The status of the fadm card.  This status represents
                         the status of the fadm card and in general is
                         different from the status of the system."
                ::= { fadmPerfEntry 5 }

        fadmLastBootTime OBJECT-TYPE
                SYNTAX  DateAndTime
                ACCESS  read-only
                STATUS  mandatory
                DESCRIPTION
                        "The date and time of the last boot for this card."
                ::= { fadmPerfEntry 6 }

        fadmAvailTime    OBJECT-TYPE
                SYNTAX  Counter
                ACCESS  read-only
                STATUS  mandatory
                DESCRIPTION
                        "The number of seconds in this time slot (15 minutes)
                         that this fadm card has been up and running.  This will
                         generally be the same as 15 minutes in seconds (900)."
                ::= { fadmPerfEntry 7 }

        fadmErrFreeSecs  OBJECT-TYPE
                SYNTAX  Counter
                ACCESS  read-only
                STATUS  mandatory
                DESCRIPTION
                        "The number of seconds in this time slot (15 minutes)
                         that this fadm card has not experienced any alarms."
                ::= { fadmPerfEntry 8 }


        -- The elements in the oppmPerf subgroup of the current subgroup

        oppmNumEvents    OBJECT-TYPE
                SYNTAX  Counter
                ACCESS  not-accessible
                STATUS  mandatory
                DESCRIPTION
                        "Total number of all traps (events) generated by all
                         OPPM's in this time slot (15 minutes)."
                ::= { oppmPerf 1 }

        oppmPerfTable    OBJECT-TYPE
                SYNTAX  SEQUENCE OF OppmPerfEntry
                ACCESS  not-accessible
                STATUS  mandatory
                DESCRIPTION
                        "This table represents the information for performance
                         data collected for each oppm card"
                ::= { oppmPerf 2 }

       oppmPerfEntry    OBJECT-TYPE
                SYNTAX  OppmPerfEntry
                ACCESS  not-accessible
                STATUS  mandatory
                DESCRIPTION
                        "Specifies the index for each row in the table below"
                INDEX { oppmPerfLocation, oppmPerfShelf, oppmPerfSlot }
                ::= { oppmPerfTable 1 }

        OppmPerfEntry    ::=
                SEQUENCE {
                        oppmPerfLocation		CardLocation,
                        oppmPerfShelf    		CardShelf,
                        oppmPerfSlot     		INTEGER,
                        oppmPerfState    		CardState,
                        oppmPerfStatus   		CardStatus,
                        oppmLinkAState    	INTEGER,
                        oppmLinkAStatus   	INTEGER,
                        oppmLinkBState    	INTEGER,
                        oppmLinkBStatus   	INTEGER,
						oppmLastBootTime		DateAndTime,
                        oppmAvailTime     	Counter,
                        oppmErrFreeSecs   	Counter,
						oppmWorkingPower	INTEGER,
						oppmProtectPower	INTEGER


                }

        oppmPerfLocation OBJECT-TYPE
                SYNTAX  CardLocation
                ACCESS  read-only
                STATUS  mandatory
                DESCRIPTION
                        "The location of the card.  Choices are local or remote."
                ::= { oppmPerfEntry 1 }

        oppmPerfShelf    OBJECT-TYPE
                SYNTAX  CardShelf
                ACCESS  read-only
                STATUS  mandatory
                DESCRIPTION
                        "The shelf the card is in.  Valid values are: 1 to 10"
                ::= { oppmPerfEntry 2 }

        oppmPerfSlot     OBJECT-TYPE
                SYNTAX  CardSlot
                ACCESS  read-only
                STATUS  mandatory
                DESCRIPTION
                        "The slot within the shelf the card is in.  Valid
                         values are: 4 to 42"
                ::= { oppmPerfEntry 3 }


        oppmPerfState    OBJECT-TYPE
                SYNTAX  CardState
                ACCESS  read-only
                STATUS  mandatory
                DESCRIPTION
                        "The state of the oppm card.  The states are:
                         online, offline."
                ::= { oppmPerfEntry 4 }

        oppmPerfStatus   OBJECT-TYPE
                SYNTAX  CardStatus 
                ACCESS  read-only
                STATUS  mandatory
                DESCRIPTION
                        "The status of the oppm card.  This status represents
                         the status of the oppm card and in general is
                         different from the status of the system."
                ::= { oppmPerfEntry 5 }

        oppmLinkAState    OBJECT-TYPE
                SYNTAX  INTEGER  {
					linked(1),
					notLinked(2),
					unknown(3)
				}
                ACCESS  read-only
                STATUS  mandatory
                DESCRIPTION
                        "The state of the oppm card.  The states are:
                         linked, notLinked."
                ::= { oppmPerfEntry 6 }

        oppmLinkAStatus   OBJECT-TYPE
                SYNTAX  INTEGER {
					active(1),
					standby(2),
					hibernation(3)
				}
                ACCESS  read-only
                STATUS  mandatory
                DESCRIPTION
                        "The status of the card channel.  This status represents
                         the status of the link A of the card and in general is
                         different from the status of the card."
                ::= { oppmPerfEntry 7 }


        oppmLinkBState    OBJECT-TYPE
                SYNTAX  INTEGER  {
					linked(1),
					notLinked(2),
					unknown(3)
				}
                ACCESS  read-only
                STATUS  mandatory
                DESCRIPTION
                        "The state of the oppm card link B.  The states are:
                         linked, notLinked."
                ::= { oppmPerfEntry 8 }

        oppmLinkBStatus   OBJECT-TYPE
                SYNTAX  INTEGER {
					active(1),
					standby(2),
					hibernation(3)
				}
                ACCESS  read-only
                STATUS  mandatory
                DESCRIPTION
                        "The status of the card channel.  This status represents
                         the status of the link B of the card and in general is
                         different from the status of the card."
                ::= { oppmPerfEntry 9 }

 	oppmLastBootTime OBJECT-TYPE
                SYNTAX  DateAndTime
                ACCESS  read-only
                STATUS  mandatory
                DESCRIPTION
                        "The date and time of the last boot for this card."
                ::= { oppmPerfEntry 10 }

 	oppmAvailTime    OBJECT-TYPE
                SYNTAX  Counter
                ACCESS  read-only
                STATUS  mandatory
                DESCRIPTION
                        "The number of seconds in this time slot (15 minutes)
                         that this oppm card has been up and running.  This will
                         generally be the same as 15 minutes in seconds (900)."
                ::= { oppmPerfEntry 11 }

      oppmErrFreeSecs  OBJECT-TYPE
                SYNTAX  Counter
                ACCESS  read-only
                STATUS  mandatory
                DESCRIPTION
                        "The number of seconds in this time slot (15 minutes)
                         that this oppm card has not experienced any alarms."
                ::= { oppmPerfEntry 12 }

	oppmWorkingPower     OBJECT-TYPE
                SYNTAX  INTEGER 
                ACCESS  read-only
                STATUS  mandatory
                DESCRIPTION
                        "working power displayed in dBm unit"
                ::= { oppmPerfEntry 13 }

	oppmProtectPower     OBJECT-TYPE
                SYNTAX  INTEGER 
                ACCESS  read-only
                STATUS  mandatory
                DESCRIPTION
                        "protect power displayed in dBm unit"
                ::= { oppmPerfEntry 14 }




        -- The elements in the mcmPerf subgroup of the current subgroup

        mcmNumEvents     OBJECT-TYPE
                SYNTAX  Counter
                ACCESS  read-only
                STATUS  mandatory
                DESCRIPTION
                        "Total number of events received for all mcm's in
                         this time slot (15 minutes)."
                ::= { mcmPerf 1 }

        mcmCntrTable     OBJECT-TYPE
                SYNTAX  SEQUENCE OF McmCntrEntry
                ACCESS  not-accessible
                STATUS  mandatory
                DESCRIPTION
                        "This table represents the information for each
                         entry for the software counters."
                ::= { mcmPerf 2 }

        mcmCntrEntry     OBJECT-TYPE
                SYNTAX  McmCntrEntry
                ACCESS  not-accessible
                STATUS  mandatory
                DESCRIPTION
                        "Specifies the index for each row in the table below"
                INDEX { mcmCntrLocation, mcmCntrShelf, mcmCntrSlot, mcmCntrType }
                ::= { mcmCntrTable 1 }

        McmCntrEntry     ::=
                SEQUENCE {
                        mcmCntrLocation  CardLocation,
                        mcmCntrShelf     CardShelf,
                        mcmCntrSlot      INTEGER,
                        mcmCntrType      INTEGER,
                        mcmCounterFlag   FlagType,
                        mcmTotPktSent    Counter,
                        mcmTotPktRcvd    Counter,
                        mcmBadPktRcvd    Counter,
                        mcmTotBadTrans   Counter,
                        mcmBytesSent     Counter,
                        mcmBytesRcvd     Counter,
                        mcmMsgsDlvrd     Counter,
                        mcmBufAllocFail  Counter,
                        mcmEcbAllocFail  Counter,
                        mcmClearCntrs    ResetType
                }

        mcmCntrLocation  OBJECT-TYPE
                SYNTAX  CardLocation
                ACCESS  read-only
                STATUS  mandatory
                DESCRIPTION
                        "The location of the mcm card.  The values are: Local
                         or Remote.  The system automatically determines the
                         right value for this entry based on the known
                         mcm cards."
                ::= { mcmCntrEntry 1 }

        mcmCntrShelf     OBJECT-TYPE
                SYNTAX  CardShelf
                ACCESS  read-only
                STATUS  mandatory
                DESCRIPTION
                        "The shelf the card is in.  Valid values are: 1 to 3.
                         The system automatically determines the right value
                         for this entry based on the known (available) mcm
                         cards."
                ::= { mcmCntrEntry 2 }

        mcmCntrSlot      OBJECT-TYPE
                SYNTAX  CardSlot
                ACCESS  read-only
                STATUS  mandatory
                DESCRIPTION
                        "The slot within the shelf the card is in.  Valid
                         values are: 1 to 21.  The system automatically
                         determines the right value for this entry based
                         on the known (available) mcm cards."
                ::= { mcmCntrEntry 3 }

        mcmCntrType      OBJECT-TYPE
                SYNTAX  INTEGER { spi(1), iwm(2) }
                ACCESS  read-only
                STATUS  mandatory
                DESCRIPTION
                        "The type of the software counter data in this row.
                         The data is collected for the SPI data channels."
                ::= { mcmCntrEntry 4 }

        mcmCounterFlag   OBJECT-TYPE
                SYNTAX  FlagType
                ACCESS  read-write
                STATUS  mandatory
                DESCRIPTION
                        "Turns software counters On or Off for this mcm."
                ::= { mcmCntrEntry 5 }

        mcmTotPktSent    OBJECT-TYPE
                SYNTAX  Counter
                ACCESS  read-only
                STATUS  mandatory
                DESCRIPTION
                        "The number of data packets sent over the given data
                         channel."
                ::= { mcmCntrEntry 6 }

        mcmTotPktRcvd    OBJECT-TYPE
                SYNTAX  Counter
                ACCESS  read-only
                STATUS  mandatory
                DESCRIPTION
                        "The number of data packets received over the given
                         data channel."
                ::= { mcmCntrEntry 7 }

        mcmBadPktRcvd    OBJECT-TYPE
                SYNTAX  Counter
                ACCESS  read-only
                STATUS  mandatory
                DESCRIPTION
                        "The number of bad data packets received over the given
                         data channel."
                ::= { mcmCntrEntry 8 }

        mcmTotBadTrans   OBJECT-TYPE
                SYNTAX  Counter
                ACCESS  read-only
                STATUS  mandatory
                DESCRIPTION
                        "The number of bad data transmissions over the given
                         data channel."
                ::= { mcmCntrEntry 9 }

        mcmBytesSent     OBJECT-TYPE
                SYNTAX  Counter
                ACCESS  read-only
                STATUS  mandatory
                DESCRIPTION
                        "Total number of bytes sent over the given
                         data channel."
                ::= { mcmCntrEntry 10 }

        mcmBytesRcvd     OBJECT-TYPE
                SYNTAX  Counter
                ACCESS  read-only
                STATUS  mandatory
                DESCRIPTION
                        "Total number of data bytes received over the given
                         data channel."
                ::= { mcmCntrEntry 11 }

        mcmMsgsDlvrd     OBJECT-TYPE
                SYNTAX  Counter
                ACCESS  read-only
                STATUS  mandatory
                DESCRIPTION
                        "The number of complete messages delivered over the
                         given data channel."
                ::= { mcmCntrEntry 12 }

        mcmBufAllocFail  OBJECT-TYPE
                SYNTAX  Counter
                ACCESS  read-only
                STATUS  mandatory
                DESCRIPTION
                        "Number of buffer allocation failures for the given
                         data channel."
                ::= { mcmCntrEntry 13 }

        mcmEcbAllocFail  OBJECT-TYPE
                SYNTAX  Counter
                ACCESS  read-only
                STATUS  mandatory
                DESCRIPTION
                        "Number of Event Control Block allocation failures
                         for the given data channel."
                ::= { mcmCntrEntry 14 }

        mcmClearCntrs    OBJECT-TYPE
                SYNTAX  ResetType
                ACCESS  read-write
                STATUS  mandatory
                DESCRIPTION
                        "If the value is reset, all software counters for this
                         15 minute interval are reset to zero.  A get on this
			 will always return other"
                ::= { mcmCntrEntry 15 }

        mcmPerfTable     OBJECT-TYPE
                SYNTAX  SEQUENCE OF McmPerfEntry
                ACCESS  not-accessible
                STATUS  mandatory
                DESCRIPTION
                        "This table represents the information for performance
                         data collected for each mcm card"
                ::= { mcmPerf 3 }

        mcmPerfEntry     OBJECT-TYPE
                SYNTAX  McmPerfEntry
                ACCESS  not-accessible
                STATUS  mandatory
                DESCRIPTION
                        "Specifies the index for each row in the table below"
                INDEX { mcmPerfLocation, mcmPerfShelf, mcmPerfSlot }
                ::= { mcmPerfTable 1 }

        McmPerfEntry     ::=
                SEQUENCE {
                        mcmPerfLocation  CardLocation,
                        mcmPerfShelf     CardShelf,
                        mcmPerfSlot      INTEGER,
                        mcmPerfState     CardState,
                        mcmPerfStatus    CardStatus,
                        mcmLastBootTime  DateAndTime,
                        mcmAvailTime     Counter,
                        mcmErrFreeSecs   Counter,
                        mcmBiasCurrent   INTEGER,
                        mcmModulation    INTEGER,
                        mcmApc           INTEGER,
                        mcmIwmModulation INTEGER,
                        mcmLaserOnOff    FlagType,
                        mcmTemperature   Gauge,
                        mcmIntensity     Gauge,
                        mcmSignalStrength Gauge,
                        mcmLossOfLight   Boolean,
                        mcmSignalDetect  Boolean
                }

        mcmPerfLocation  OBJECT-TYPE
                SYNTAX  CardLocation
                ACCESS  read-only
                STATUS  mandatory
                DESCRIPTION
                        "The location of the card.  Valid choices are Local
                         or Remote.  The system automatically selects this
                         value based on the known (available) mcm cards."
                ::= { mcmPerfEntry 1 }

        mcmPerfShelf     OBJECT-TYPE
                SYNTAX  CardShelf
                ACCESS  read-only
                STATUS  mandatory
                DESCRIPTION
                        "The shelf the card is in.  Valid values are: 1 to 3"
                ::= { mcmPerfEntry 2 }

        mcmPerfSlot      OBJECT-TYPE
                SYNTAX  CardSlot
                ACCESS  read-only
                STATUS  mandatory
                DESCRIPTION
                        "The slot within the shelf the card is in.  Valid
                         values are: 1 to 21"
                ::= { mcmPerfEntry 3 }

        mcmPerfState     OBJECT-TYPE
                SYNTAX  CardState
                ACCESS  read-only
                STATUS  mandatory
                DESCRIPTION
                        "The state of the mcm card.  The states' are:
                         online, offline, empty, loopback or diagnostics."
                ::= {mcmPerfEntry 4 }

        mcmPerfStatus    OBJECT-TYPE
                SYNTAX  CardStatus
                ACCESS  read-only
                STATUS  mandatory
                DESCRIPTION
                        "The status of the channel card.  This
                         status represents the status of the communication
                         processor and in general is different from the
                         status of the system."
                ::= { mcmPerfEntry 5 }

        mcmLastBootTime  OBJECT-TYPE
                SYNTAX  DateAndTime
                ACCESS  read-only
                STATUS  mandatory
                DESCRIPTION
                        "The date and time of the last boot for this card."
                ::= { mcmPerfEntry 6 }

        mcmAvailTime     OBJECT-TYPE
                SYNTAX  Counter
                ACCESS  read-only
                STATUS  mandatory
                DESCRIPTION
                        "The number of seconds in this time slot (15 minutes)
                         that this mcm has been up and running.  This will
                         generally be the same as 15 minutes in seconds (900)."
                ::= { mcmPerfEntry 7 }

        mcmErrFreeSecs   OBJECT-TYPE
                SYNTAX  Counter
                ACCESS  read-only
                STATUS  mandatory
                DESCRIPTION
                        "The number of seconds in this time slot (15 minutes)
                         that this mcm has not experienced any alarms."
                ::= { mcmPerfEntry 8 }

        mcmBiasCurrent   OBJECT-TYPE
                SYNTAX  INTEGER
                ACCESS  read-only
                STATUS  mandatory
                DESCRIPTION
                        "Bias current for the optical laser.  This value can
                         be set remotely"
                ::= { mcmPerfEntry 9 }

        mcmModulation    OBJECT-TYPE
                SYNTAX  INTEGER
                ACCESS  read-only
                STATUS  mandatory
                DESCRIPTION
                        "The frequency modulation for the optical laser.  This
                         value can be adjusted remotely."
                ::= { mcmPerfEntry 10 }

        mcmApc           OBJECT-TYPE
                SYNTAX  INTEGER
                ACCESS  read-only
                STATUS  mandatory
                DESCRIPTION
                        "The APC value.  This value can be set remotely."
                ::= { mcmPerfEntry 11 }

        mcmIwmModulation OBJECT-TYPE
                SYNTAX  INTEGER
                ACCESS  read-only
                STATUS  mandatory
                DESCRIPTION
                        "The frequency modulation for the IWM channel.  This
                         value can be adjusted remotely."
                ::= { mcmPerfEntry 12 }

        mcmLaserOnOff    OBJECT-TYPE
                SYNTAX  FlagType
                ACCESS  read-only
                STATUS  mandatory
                DESCRIPTION
                        "The laser On/Off flag.  This value can be set
                         remotely."
                ::= { mcmPerfEntry 13 }

        mcmTemperature   OBJECT-TYPE
                SYNTAX  Gauge
                ACCESS  read-only
                STATUS  mandatory
                DESCRIPTION
                        "The current temperature, or the operating temperature
                         of the optical device."
                ::= { mcmPerfEntry 14 }

        mcmIntensity     OBJECT-TYPE
                SYNTAX  Gauge
                ACCESS  read-only
                STATUS  mandatory
                DESCRIPTION
                        "The intensity of the optical light.  This value can
                         be set remotely."
                ::= { mcmPerfEntry 15 }

        mcmSignalStrength OBJECT-TYPE
                SYNTAX  Gauge
                ACCESS  read-only
                STATUS  mandatory
                DESCRIPTION
                        "The current signal strength for the optical path."
                ::= { mcmPerfEntry 16 }

        mcmLossOfLight   OBJECT-TYPE
                SYNTAX  Boolean
                ACCESS  read-only
                STATUS  mandatory
                DESCRIPTION
                        "If set to true, no laser light is present.  If set to
                         false, no loss of light has occurred."
                ::= { mcmPerfEntry 17 }

        mcmSignalDetect  OBJECT-TYPE
                SYNTAX  Boolean
                ACCESS  read-only
                STATUS  mandatory
                DESCRIPTION
                        "If set to true, signal is detected.  If set to false,
                         no signal is present."
                ::= { mcmPerfEntry 18 }



        mcmPortCurrTable        OBJECT-TYPE
                SYNTAX  SEQUENCE OF McmPortCurrEntry
                ACCESS  not-accessible
                STATUS  mandatory
                DESCRIPTION
                        "This table represents the information for each
                         MCM port's current counters."
                ::= { mcmPerf 4 }

        mcmPortCurrEntry        OBJECT-TYPE
                SYNTAX  McmPortCurrEntry
                ACCESS  not-accessible
                STATUS  mandatory
                DESCRIPTION
                        "Specifies the index for each row in the table below"
                INDEX { mcmPortCurrCardLocation, mcmPortCurrCardShelf,
                        mcmPortCurrCardSlot,  mcmPortCurrIndex }
                ::= { mcmPortCurrTable 1 }

        McmPortCurrEntry        ::=
                SEQUENCE {
                        mcmPortCurrCardLocation 		CardLocation,
                        mcmPortCurrCardShelf    		CardShelf,
                        mcmPortCurrCardSlot     		INTEGER,
				mcmPortCurrIndex	  			INTEGER,
                        mcmPortCurrASs		        	Counter,
	--mcmPortCurrFrameASs			Counter,
                        mcmPortCurrFEs				Counter,
                        mcmPortCurrCRCErrs			Counter,
				mcmPortCurrSESs				Counter,
                        mcmPortCurrSEFSs				Counter,
                        mcmPortCurrUASs				Counter,
				mcmPortCurrLESs				Counter,
                        mcmPortCurrBESs				Counter,
                        mcmPortCurrDMs				Counter,
				mcmPortCurrLCVs				Counter
                }

        mcmPortCurrCardLocation OBJECT-TYPE
                SYNTAX  CardLocation
                ACCESS  read-only
                STATUS  mandatory
                DESCRIPTION
                        "Location of the MCM port.  Valid values are: Local in
                         the same chassis, or remote to this chassis"
                ::= { mcmPortCurrEntry 1 }

        mcmPortCurrCardShelf    OBJECT-TYPE
                SYNTAX  CardShelf
                ACCESS  read-only
                STATUS  mandatory
                DESCRIPTION
                        "The shelf the card is in.  Valid values are: 2..3."
                ::= { mcmPortCurrEntry 2 }

        mcmPortCurrCardSlot     OBJECT-TYPE
                SYNTAX  CardSlot
                ACCESS  read-only
                STATUS  mandatory
                DESCRIPTION
                        "The slot within the shelf the Module is in."
                ::= { mcmPortCurrEntry 3 }

        mcmPortCurrIndex      OBJECT-TYPE
                SYNTAX  INTEGER 
                ACCESS  read-only
                STATUS  mandatory
                DESCRIPTION
                        "Port's index."
                ::= { mcmPortCurrEntry 4 }

        mcmPortCurrASs      OBJECT-TYPE
                SYNTAX  Counter 
                ACCESS  read-only
                STATUS  mandatory
                DESCRIPTION
                        "mcm port's ASs counter less than 15 mins."
                ::= { mcmPortCurrEntry 5 }

       -- mcmPortCurrFrameASs      OBJECT-TYPE
       --         SYNTAX  Counter
       --         ACCESS  read-only
       --         STATUS  mandatory
       --         DESCRIPTION
       --                 "MCM port's FrameASs counter less than 15 mins."
       --        ::= { mcmPortCurrEntry 6 }

        mcmPortCurrFEs      OBJECT-TYPE
                SYNTAX  Counter
                ACCESS  read-only
                STATUS  mandatory
                DESCRIPTION
                        "MCM port's FEs counter less than 15 mins." 
                ::= { mcmPortCurrEntry 7 }

        mcmPortCurrCRCErrs    OBJECT-TYPE
                SYNTAX  Counter
                ACCESS  read-only
                STATUS  mandatory
                DESCRIPTION
                        "MCM port's CRC errs counter less than 15 mins."
                ::= { mcmPortCurrEntry 8 }

        mcmPortCurrSESs      OBJECT-TYPE
                SYNTAX  Counter 
                ACCESS  read-only
                STATUS  mandatory
                DESCRIPTION
                        "mcm port's SESs counter less than 15 mins."
                ::= { mcmPortCurrEntry 9 }

        mcmPortCurrSEFSs      OBJECT-TYPE
                SYNTAX  Counter
                ACCESS  read-only
                STATUS  mandatory
                DESCRIPTION
                        "MCM port's SEFSs counter less than 15 mins."
                ::= { mcmPortCurrEntry 10 }

        mcmPortCurrUASs      OBJECT-TYPE
                SYNTAX  Counter
                ACCESS  read-only
                STATUS  mandatory
                DESCRIPTION
                        "MCM port's UASs counter less than 15 mins." 
                ::= { mcmPortCurrEntry 11 }

        mcmPortCurrLESs    OBJECT-TYPE
                SYNTAX  Counter
                ACCESS  read-only
                STATUS  mandatory
                DESCRIPTION
                        "MCM port's LESs counter less than 15 mins."
                ::= { mcmPortCurrEntry 12 }

        mcmPortCurrBESs    OBJECT-TYPE
                SYNTAX  Counter
                ACCESS  read-only
                STATUS  mandatory
                DESCRIPTION
                        "MCM port's BESs counter less than 15 mins."
                ::= { mcmPortCurrEntry 13 }

        mcmPortCurrDMs    OBJECT-TYPE
                SYNTAX  Counter
                ACCESS  read-only
                STATUS  mandatory
                DESCRIPTION
                        "MCM port's DMSs counter less than 15 mins."
                ::= { mcmPortCurrEntry 14 }

        mcmPortCurrLCVs    OBJECT-TYPE
                SYNTAX  Counter
                ACCESS  read-only
                STATUS  mandatory
                DESCRIPTION
                        "MCM port's LCVs counter less than 15 mins."
                ::= { mcmPortCurrEntry 15 }

        -- The elements in the fnPerf subgroup of the current subgroup

        fnNumEvents     OBJECT-TYPE
                SYNTAX  Counter
                ACCESS  read-only
                STATUS  mandatory
                DESCRIPTION
                        "Total number of all traps (events) generated by all
                         Fans in this time slot (15 minutes)."
                ::= { fnPerf 1 }

        fnPerfTable     OBJECT-TYPE
                SYNTAX  SEQUENCE OF FnPerfEntry
                ACCESS  not-accessible
                STATUS  mandatory
                DESCRIPTION
                        "This table represents the information for performance
                         data collected for each fan module."
                ::= { fnPerf 2 }

        fnPerfEntry     OBJECT-TYPE
                SYNTAX  FnPerfEntry
                ACCESS  not-accessible
                STATUS  mandatory
                DESCRIPTION
                        "Specifies the index for each row in the table below"
                INDEX { fnPerfID }
                ::= { fnPerfTable 1 }

        FnPerfEntry     ::=
                SEQUENCE {
                        fnPerfID	INTEGER,
                        fnPerfState     INTEGER,
                        fnPerfStatus    CardStatus
                }

        fnPerfID     OBJECT-TYPE
                SYNTAX  INTEGER
                ACCESS  read-only
                STATUS  mandatory
                DESCRIPTION
                        "The module ID where the fan module is plugged in."
                ::= { fnPerfEntry 1 }

        fnPerfState     OBJECT-TYPE
                SYNTAX  INTEGER  { fnEmpty(1),
				   fnOK(2),
				   fnFailed(3),
				   fnDegrade(4)
				 }
                ACCESS  read-only
                STATUS  mandatory
                DESCRIPTION
                        "The state of the fan module."
                ::= { fnPerfEntry 2 }

        fnPerfStatus    OBJECT-TYPE
                SYNTAX  CardStatus
                ACCESS  read-only
                STATUS  mandatory
                DESCRIPTION
                        "The status of the fan module.  This status
                         represents the status of the fan module and in general is
                         different from the status of the system."
                ::= { fnPerfEntry 3 }

	   -- The elements in the csimPerf subgroup of the current subgroup
	csimNumEvents     OBJECT-TYPE
                SYNTAX  Counter
                ACCESS  not-accessible
                STATUS  mandatory
                DESCRIPTION
                        "This variable keeps track of the number of events
			 related to ColorSIM. The reason this has been made obsolete
			 is that all colorsim related events would eventually be part
			 of ocm events"
                ::= { csimPerf 1 }
     
	csimCurrentTable       OBJECT-TYPE
                SYNTAX  SEQUENCE OF CsimCurrentEntry
                ACCESS  not-accessible
                STATUS  mandatory
                DESCRIPTION
                        "This table represents the information for each
                         colorsim card in the most current interval"
                ::= { csimPerf 2 }

        csimCurrentEntry       OBJECT-TYPE
                SYNTAX  CsimCurrentEntry
                ACCESS  not-accessible
                STATUS  mandatory
                DESCRIPTION
                        "Specifies the index for each row in the table below."
                INDEX { csimCurrentLocation, csimCurrentShelf, csimCurrentSlot }
                ::= { csimCurrentTable 1 }

        CsimCurrentEntry         ::=
                SEQUENCE {
                        csimCurrentLocation 	CardLocation,
                        csimCurrentShelf        CardShelf,
                        csimCurrentSlot         INTEGER,
				csimCurrentEFIs		INTEGER,
				csimCurrentEIs		INTEGER,
				csimCurrentSEIs		INTEGER,
				csimCurrentBERs		DisplayString,
				csimCurrentUAIs		INTEGER,
				csimCurrentGIs    	INTEGER,
				csimCurrentDateTime INTEGER
			}
	
        csimCurrentLocation  OBJECT-TYPE
                SYNTAX  CardLocation
                ACCESS  read-only
                STATUS  mandatory
                DESCRIPTION
                        " Location of the ColorSIM module"
                ::= { csimCurrentEntry 1 }

        csimCurrentShelf     OBJECT-TYPE
                SYNTAX  CardShelf
                ACCESS  read-only
                STATUS  mandatory
                DESCRIPTION
                        "The shelf of the ColorSIM module"
                ::= { csimCurrentEntry 2 }

        csimCurrentSlot      OBJECT-TYPE
                SYNTAX  CardSlot
                ACCESS  read-only 
                STATUS  mandatory
                DESCRIPTION
                        "The Slot of the ColorSIM module"
                ::= { csimCurrentEntry 3 }

        csimCurrentEFIs OBJECT-TYPE
                SYNTAX  INTEGER
                ACCESS  read-only
                STATUS  mandatory
                DESCRIPTION
			"The counter associated with the number of Error Free
			 Interval Counts in the current update (default: 15
			 minutes) interval."
                ::= { csimCurrentEntry 4 }

        csimCurrentEIs OBJECT-TYPE
                SYNTAX  INTEGER
                ACCESS  read-only
                STATUS  mandatory
                DESCRIPTION
			"The counter associated with the number of Errored
			 Interval Counts in the current update (default: 15
			 minutes) interval."
                ::= { csimCurrentEntry 5 }

        csimCurrentSEIs OBJECT-TYPE
                SYNTAX  INTEGER
                ACCESS  read-only
                STATUS  mandatory
                DESCRIPTION
			"The counter associated with the number of Severly
			 Errored Interval Counts in the current update
			 (default:15 minutes) interval."
                ::= { csimCurrentEntry 6}

        csimCurrentBERs OBJECT-TYPE
                SYNTAX  DisplayString
                ACCESS  read-only
                STATUS  mandatory
                DESCRIPTION
			"The counter associated with the number of Bit Error
			 Rates Counts in the current update (default: 15
			 minutes) interval. The unit will be in the form of
			 x.ye-z."
                ::= { csimCurrentEntry 7 }

        csimCurrentUAIs OBJECT-TYPE
                SYNTAX  INTEGER
                ACCESS  read-only
                STATUS  mandatory
                DESCRIPTION
			"The counter associated with the number of Unavailable
			 Interval Counts in the current update (default: 15
			 minutes) interval."
                ::= { csimCurrentEntry 8 }

        csimCurrentGIs OBJECT-TYPE
                SYNTAX  INTEGER
                ACCESS  read-only
                STATUS  mandatory
                DESCRIPTION
			"The number of gating intervals over which the data was
			 collected."
                ::= { csimCurrentEntry 9 }

        csimCurrentDateTime OBJECT-TYPE
                SYNTAX  INTEGER
                ACCESS  read-only
                STATUS  mandatory
                DESCRIPTION
			"Time in seconds elasped since 01/01/1970 00:00:00 GMT. Assuming
			 local time is same as GMT"
                ::= { csimCurrentEntry 10 }

       -- The elements in the rpsmPerf subgroup of the current subgroup

        rpsmNumEvents    OBJECT-TYPE
                SYNTAX  Counter
                ACCESS  read-only
                STATUS  mandatory
                DESCRIPTION
                        "Total number of all traps (events) generated by all
                         RPSM's in this time slot (15 minutes)."
                ::= { rpsmPerf 1 }
	

        rpsmPerfTable    OBJECT-TYPE
                SYNTAX  SEQUENCE OF RpsmPerfEntry
                ACCESS  not-accessible
                STATUS  mandatory
                DESCRIPTION
                        "This table represents the information for performance
                         data collected for each rpsm card"
                ::= { rpsmPerf 2 }

        rpsmPerfEntry    OBJECT-TYPE
                SYNTAX  RpsmPerfEntry
                ACCESS  not-accessible
                STATUS  mandatory
                DESCRIPTION
                        "Specifies the index for each row in the table below"
                INDEX { rpsmPerfLocation, rpsmPerfShelf, rpsmPerfSlot }
                ::= { rpsmPerfTable 1 }

        RpsmPerfEntry    ::=
                SEQUENCE {
                        rpsmPerfLocation 	CardLocation,
                        rpsmPerfShelf    	CardShelf,
                        rpsmPerfSlot     	INTEGER,
                        rpsmPerfState    	CardState,
                        rpsmPerfStatus   	CardStatus,
                        rpsmLinkEastState   	INTEGER,
                        rpsmLinkEastStatus  	INTEGER,
                        rpsmLinkWestState   	INTEGER,
                        rpsmLinkWestStatus  	INTEGER,
                        rpsmLastBootTime 	DateAndTime,
                        rpsmAvailTime    	Counter,
                        rpsmErrFreeSecs  	Counter,
			rpsmWorkingPower	INTEGER,
			rpsmProtectionPower	INTEGER
                }

        rpsmPerfLocation OBJECT-TYPE
                SYNTAX  CardLocation
                ACCESS  read-only
                STATUS  mandatory
                DESCRIPTION
                        "The location of the card.  Choices are local or
                         remote."
                ::= { rpsmPerfEntry 1 }

        rpsmPerfShelf    OBJECT-TYPE
                SYNTAX  CardShelf
                ACCESS  read-only
                STATUS  mandatory
                DESCRIPTION
                        "The shelf the card is in.  Valid values are: 1 to 10"
                ::= { rpsmPerfEntry 2 }

        rpsmPerfSlot     OBJECT-TYPE
                SYNTAX  CardSlot
                ACCESS  read-only
                STATUS  mandatory
                DESCRIPTION
                        "The slot within the shelf the card is in."
                ::= { rpsmPerfEntry 3 }

        rpsmPerfState    OBJECT-TYPE
                SYNTAX  CardState
                ACCESS  read-only
                STATUS  mandatory
                DESCRIPTION
                        "The state of the rpsm card.  The possible states
			 are: online, offline, empty, loopback or diag."
                ::= { rpsmPerfEntry 4 }

        rpsmPerfStatus   OBJECT-TYPE
                SYNTAX  CardStatus
                ACCESS  read-only
                STATUS  mandatory
                DESCRIPTION
                        "The status of the rpsm card.  This status represents
                         the status of the rpsm card and in general is
                         different from the status of the system."
                ::= { rpsmPerfEntry 5 }

        rpsmLinkEastState    OBJECT-TYPE
                SYNTAX  INTEGER  {
					linked(1),
					notLinked(2),
					unknown(3)
				}
                ACCESS  read-only
                STATUS  mandatory
                DESCRIPTION
                        "The link state of path East, whether light
			 is being detected.  The states are:
                         linked, notLinked."
                ::= { rpsmPerfEntry 6 }

        rpsmLinkEastStatus   OBJECT-TYPE
                SYNTAX  INTEGER {
					active(1),
					standby(2),
					hibernation(3)
				}
                ACCESS  read-only
                STATUS  mandatory
                DESCRIPTION
                        "The status of the card channel.  This status represents
                         the status of the link East of the card and in general
			 is different from the status of the card."
                ::= { rpsmPerfEntry 7 }


        rpsmLinkWestState    OBJECT-TYPE
                SYNTAX  INTEGER  {
					linked(1),
					notLinked(2),
					unknown(3)
				}
                ACCESS  read-only
                STATUS  mandatory
                DESCRIPTION
                        "The link state of path West, whether light
			 is being detected.  The states are:
                         linked, notLinked."
                ::= { rpsmPerfEntry 8 }

        rpsmLinkWestStatus   OBJECT-TYPE
                SYNTAX  INTEGER {
					active(1),
					standby(2),
					hibernation(3)
				}
                ACCESS  read-only
                STATUS  mandatory
                DESCRIPTION
                        "The status of the card channel.  This status represents
                         the status of the link West of the card and in general
			 is different from the status of the card."
                ::= { rpsmPerfEntry 9 }


        rpsmLastBootTime OBJECT-TYPE
                SYNTAX  DateAndTime
                ACCESS  read-only
                STATUS  mandatory
                DESCRIPTION
                        "The date and time of the last boot for this card."
                ::= { rpsmPerfEntry 10 }

        rpsmAvailTime    OBJECT-TYPE
                SYNTAX  Counter
                ACCESS  read-only
                STATUS  mandatory
                DESCRIPTION
                        "The number of seconds in this time slot (15 minutes)
                         that this rpsm has been up and running.  This will
                         generally be the same as 15 minutes in seconds (900)."
                ::= { rpsmPerfEntry 11 }

        rpsmErrFreeSecs  OBJECT-TYPE
                SYNTAX  Counter
                ACCESS  read-only
                STATUS  mandatory
                DESCRIPTION
                        "The number of seconds in this time slot (15 minutes)
                         that this rpsm has not experienced any alarms."
                ::= { rpsmPerfEntry 12 }

        rpsmWorkingPower OBJECT-TYPE
                SYNTAX  INTEGER 
                ACCESS  read-only
                STATUS  mandatory
                DESCRIPTION
                        "Working link power of the RPSM card in dBm."
                ::= { rpsmPerfEntry 13 }

        rpsmProtectionPower OBJECT-TYPE
                SYNTAX  INTEGER 
                ACCESS  read-only
                STATUS  mandatory
                DESCRIPTION
                        "Protection link power of the RPSM card in dBm."
                ::= { rpsmPerfEntry 14 }

        -- The elements in the rsdmPerf subgroup of the current subgroup

        rsdmNumEvents    OBJECT-TYPE
                SYNTAX  Counter
                ACCESS  not-accessible
                STATUS  mandatory
                DESCRIPTION
                        "Total number of all traps (events) generated by all
                         RSDM's in this time slot (15 minutes)."
                ::= { rsdmPerf 1 }

        rsdmPerfTable    OBJECT-TYPE
                SYNTAX  SEQUENCE OF RsdmPerfEntry
                ACCESS  not-accessible
                STATUS  mandatory
                DESCRIPTION
                        "This table represents the information for performance
                         data collected for each rsdm card"
                ::= { rsdmPerf 2 }

	rsdmPerfEntry    OBJECT-TYPE
                SYNTAX  RsdmPerfEntry
                ACCESS  not-accessible
                STATUS  mandatory
                DESCRIPTION
                        "Specifies the index for each row in the table below"
                INDEX { rsdmPerfLocation, rsdmPerfShelf, rsdmPerfSlot }
                ::= { rsdmPerfTable 1 }

        RsdmPerfEntry    ::=
                SEQUENCE {
                        rsdmPerfLocation		CardLocation,
                        rsdmPerfShelf    		CardShelf,
                        rsdmPerfSlot     		INTEGER,
                        rsdmPerfState    		CardState,
                        rsdmPerfStatus   		CardStatus,
                        rsdmLinkEastState    		INTEGER,
                        rsdmLinkEastStatus   		INTEGER,
                        rsdmLinkWestState    		INTEGER,
                        rsdmLinkWestStatus   		INTEGER,
			rsdmLastBootTime		DateAndTime,
                        rsdmAvailTime     		Counter,
                        rsdmErrFreeSecs   		Counter,
			rsdmWorkingPower		INTEGER,
			rsdmProtectionPower		INTEGER
                }

        rsdmPerfLocation OBJECT-TYPE
                SYNTAX  CardLocation
                ACCESS  read-only
                STATUS  mandatory
                DESCRIPTION
                        "The location of the card.  Choices are local or remote."
                ::= { rsdmPerfEntry 1 }

        rsdmPerfShelf    OBJECT-TYPE
                SYNTAX  CardShelf
                ACCESS  read-only
                STATUS  mandatory
                DESCRIPTION
                        "The shelf the card is in."
                ::= { rsdmPerfEntry 2 }

        rsdmPerfSlot     OBJECT-TYPE
                SYNTAX  CardSlot
                ACCESS  read-only
                STATUS  mandatory
                DESCRIPTION
                        "The slot within the shelf the card is in."
                ::= { rsdmPerfEntry 3 }


        rsdmPerfState    OBJECT-TYPE
                SYNTAX  CardState
                ACCESS  read-only
                STATUS  mandatory
                DESCRIPTION
                        "The state of the rsdm card.  The states are:
                         online, offline."
                ::= { rsdmPerfEntry 4 }

        rsdmPerfStatus   OBJECT-TYPE
                SYNTAX  CardStatus 
                ACCESS  read-only
                STATUS  mandatory
                DESCRIPTION
                        "The status of the rsdm card.  This status represents
                         the status of the rsdm card and in general is
                         different from the status of the system."
                ::= { rsdmPerfEntry 5 }

        rsdmLinkEastState    OBJECT-TYPE
                SYNTAX  INTEGER  {
					linked(1),
					notLinked(2),
					unknown(3)
				}
                ACCESS  read-only
                STATUS  mandatory
                DESCRIPTION
                        "The link state of path A, whether light
			 is being detected.  The states are:
                         linked, notLinked."
                ::= { rsdmPerfEntry 6 }

        rsdmLinkEastStatus   OBJECT-TYPE
                SYNTAX  INTEGER {
					active(1),
					standby(2),
					hibernation(3)
				}
                ACCESS  read-only
                STATUS  mandatory
                DESCRIPTION
                        "The status of the card channel.  This status represents
                         the status of the link East of the card and in general is
                         different from the status of the card."
                ::= { rsdmPerfEntry 7 }


        rsdmLinkWestState    OBJECT-TYPE
                SYNTAX  INTEGER  {
					linked(1),
					notLinked(2),
					unknown(3)
				}
                ACCESS  read-only
                STATUS  mandatory
                DESCRIPTION
                        "The link state of path West, whether light
			 is being detected.  The states are:
                         linked, notLinked."
                ::= { rsdmPerfEntry 8 }

        rsdmLinkWestStatus   OBJECT-TYPE
                SYNTAX  INTEGER {
					active(1),
					standby(2),
					hibernation(3)
				}
                ACCESS  read-only
                STATUS  mandatory
                DESCRIPTION
                        "The status of the card channel.  This status represents
                         the status of the link West of the card and in general
			 is different from the status of the card."
                ::= { rsdmPerfEntry 9 }

	rsdmLastBootTime OBJECT-TYPE
                SYNTAX  DateAndTime
                ACCESS  read-only
                STATUS  mandatory
                DESCRIPTION
                        "The date and time of the last boot for this card."
                ::= { rsdmPerfEntry 10 }

	rsdmAvailTime    OBJECT-TYPE
                SYNTAX  Counter
                ACCESS  read-only
                STATUS  mandatory
                DESCRIPTION
                        "The number of seconds in this time slot (15 minutes)
                         that this rsdm card has been up and running.  This will
                         generally be the same as 15 minutes in seconds (900)."
                ::= { rsdmPerfEntry 11 }

	rsdmErrFreeSecs  OBJECT-TYPE
                SYNTAX  Counter
                ACCESS  read-only
                STATUS  mandatory
                DESCRIPTION
                        "The number of seconds in this time slot (15 minutes)
                         that this rsdm card has not experienced any alarms."
                ::= { rsdmPerfEntry 12 }

        rsdmWorkingPower OBJECT-TYPE
                SYNTAX  INTEGER 
                ACCESS  read-only
                STATUS  mandatory
                DESCRIPTION
                        "Working link power of the RSDM card in dBm."
                ::= { rsdmPerfEntry 13 }

        rsdmProtectionPower OBJECT-TYPE
                SYNTAX  INTEGER 
                ACCESS  read-only
                STATUS  mandatory
                DESCRIPTION
                        "Protection link power of the RSDM card in dBm."
                ::= { rsdmPerfEntry 14 }


       -- The elements in the rtdmPerf subgroup of the current subgroup

        rtdmNumEvents    OBJECT-TYPE
                SYNTAX  Counter
                ACCESS  read-only
                STATUS  mandatory
                DESCRIPTION
                        "Total number of all traps (events) generated by all
                         RTDM's in this time slot (15 minutes)."
                ::= { rtdmPerf 1 }
	

        rtdmPerfTable    OBJECT-TYPE
                SYNTAX  SEQUENCE OF RtdmPerfEntry
                ACCESS  not-accessible
                STATUS  mandatory
                DESCRIPTION
                        "This table represents the information for performance
                         data collected for each rtdm card"
                ::= { rtdmPerf 2 }

        rtdmPerfEntry    OBJECT-TYPE
                SYNTAX  RtdmPerfEntry
                ACCESS  not-accessible
                STATUS  mandatory
                DESCRIPTION
                        "Specifies the index for each row in the table below"
                INDEX { rtdmPerfLocation, rtdmPerfShelf, rtdmPerfSlot }
                ::= { rtdmPerfTable 1 }

        RtdmPerfEntry    ::=
                SEQUENCE {
                        rtdmPerfLocation CardLocation,
                        rtdmPerfShelf    CardShelf,
                        rtdmPerfSlot     INTEGER,
                        rtdmPerfState    CardState,
                        rtdmPerfStatus   CardStatus,
                        rtdmLastBootTime DateAndTime,
                        rtdmAvailTime    Counter,
                        rtdmErrFreeSecs  Counter
                }

        rtdmPerfLocation OBJECT-TYPE
                SYNTAX  CardLocation
                ACCESS  read-only
                STATUS  mandatory
                DESCRIPTION
                        "The location of the card.  Choices are local or
                         remote."
                ::= { rtdmPerfEntry 1 }

        rtdmPerfShelf    OBJECT-TYPE
                SYNTAX  CardShelf
                ACCESS  read-only
                STATUS  mandatory
                DESCRIPTION
                        "The shelf the card is in."
                ::= { rtdmPerfEntry 2 }

        rtdmPerfSlot     OBJECT-TYPE
                SYNTAX  CardSlot
                ACCESS  read-only
                STATUS  mandatory
                DESCRIPTION
                        "The slot within the shelf the card is in."
                ::= { rtdmPerfEntry 3 }

        rtdmPerfState    OBJECT-TYPE
                SYNTAX  CardState
                ACCESS  read-only
                STATUS  mandatory
                DESCRIPTION
                        "The state of the rtdm card.  The states are:
                         online, offline, empty, loopback or diag."
                ::= { rtdmPerfEntry 4 }

        rtdmPerfStatus   OBJECT-TYPE
                SYNTAX  CardStatus
                ACCESS  read-only
                STATUS  mandatory
                DESCRIPTION
                        "The status of the rtdm card.  This status represents
                         the status of the rtdm card and in general is
                         different from the status of the system."
                ::= { rtdmPerfEntry 5 }

        rtdmLastBootTime OBJECT-TYPE
                SYNTAX  DateAndTime
                ACCESS  read-only
                STATUS  mandatory
                DESCRIPTION
                        "The date and time of the last boot for this card."
                ::= { rtdmPerfEntry 6 }

        rtdmAvailTime    OBJECT-TYPE
                SYNTAX  Counter
                ACCESS  read-only
                STATUS  mandatory
                DESCRIPTION
                        "The number of seconds in this time slot (15 minutes)
                         that this rtdm has been up and running.  This will
                         generally be the same as 15 minutes in seconds (900)."
                ::= { rtdmPerfEntry 7 }

        rtdmErrFreeSecs  OBJECT-TYPE
                SYNTAX  Counter
                ACCESS  read-only
                STATUS  mandatory
                DESCRIPTION
                        "The number of seconds in this time slot (15 minutes)
                         that this rtdm has not experienced any alarms."
                ::= { rtdmPerfEntry 8 }


        -- The elements in the osamPerf subgroup of the current subgroup

        osamNumEvents     OBJECT-TYPE
                SYNTAX  Counter
                ACCESS  read-only
                STATUS  mandatory
                DESCRIPTION
                        "Total number of events received for all osam's in
                         the most current 15 minutes slot."
                ::= { osamPerf 1 }

        osamCntrTable     OBJECT-TYPE
                SYNTAX  SEQUENCE OF OsamCntrEntry
                ACCESS  not-accessible
                STATUS  mandatory
                DESCRIPTION
                        "This table represents the information for each
                         entry for the software counters."
                ::= { osamPerf 2 }

        osamCntrEntry     OBJECT-TYPE
                SYNTAX  OsamCntrEntry
                ACCESS  not-accessible
                STATUS  mandatory
                DESCRIPTION
                        "Specifies the index for each row in the table below"
                INDEX { osamCntrLocation, osamCntrShelf, osamCntrSlot }
                ::= { osamCntrTable 1 }

        OsamCntrEntry     ::=
                SEQUENCE {
                        osamCntrLocation            CardLocation,
                        osamCntrShelf               CardShelf,
                        osamCntrSlot                INTEGER,
                        osamCntrKeepAlivePktSent    Counter,
                        osamCntrKeepAlivePktRcvd    Counter,
                        osamCntrKeepAliveBadPktRcvd Counter
                }

        osamCntrLocation  OBJECT-TYPE
                SYNTAX  CardLocation
                ACCESS  read-only
                STATUS  mandatory
                DESCRIPTION
                        "Location of the module."
                ::= { osamCntrEntry 1 }

        osamCntrShelf     OBJECT-TYPE
                SYNTAX  CardShelf
                ACCESS  read-only
                STATUS  mandatory
                DESCRIPTION
                        "The shelf number in which the module is plugged in."
                ::= { osamCntrEntry 2 }

        osamCntrSlot      OBJECT-TYPE
                SYNTAX  INTEGER (1..16)
                ACCESS  read-only
                STATUS  mandatory
                DESCRIPTION
                        "The slot number in which the module is plugged in."
                ::= { osamCntrEntry 3 }

        osamCntrKeepAlivePktSent    OBJECT-TYPE
                SYNTAX  Counter
                ACCESS  read-only
                STATUS  mandatory
                DESCRIPTION
                        "The total number of keep alive packets sent."
                ::= { osamCntrEntry 4 }

        osamCntrKeepAlivePktRcvd    OBJECT-TYPE
                SYNTAX  Counter
                ACCESS  read-only
                STATUS  mandatory
                DESCRIPTION
                        "The total number of keep alive packets received."
                ::= { osamCntrEntry 5 }

        osamCntrKeepAliveBadPktRcvd    OBJECT-TYPE
                SYNTAX  Counter
                ACCESS  read-only
                STATUS  mandatory
                DESCRIPTION
                        "The total number of bad keep alive data packets 
                         received."
                ::= { osamCntrEntry 6 }

        osamPerfTable     OBJECT-TYPE
                SYNTAX  SEQUENCE OF OsamPerfEntry
                ACCESS  not-accessible
                STATUS  mandatory
                DESCRIPTION
                        "This table represents the information for performance
                         data collected for each osam card"
                ::= { osamPerf 3 }

        osamPerfEntry     OBJECT-TYPE
                SYNTAX  OsamPerfEntry
                ACCESS  not-accessible
                STATUS  mandatory
                DESCRIPTION
                        "Specifies the index for each row in the table below"
                INDEX { osamPerfLocation, osamPerfShelf, osamPerfSlot }
                ::= { osamPerfTable 1 }

        OsamPerfEntry     ::=
                SEQUENCE {
                        osamPerfLocation              CardLocation,
                        osamPerfShelf                 CardShelf,
                        osamPerfSlot                  INTEGER,
                        osamPerfState                 CardState,
                        osamPerfStatus                CardStatus,
                        osamPerfLastBootTime          DateAndTime,
                        osamPerfAvailTime             Counter,
                        osamPerfErrFreeSecs           Counter,
                        osamPerfAprStatus             FlagType,
                        osamPerfInputPower            DisplayString,
                        osamPerfBFDPower              DisplayString,
                        osamPerfOutputPower           DisplayString,
                        osamPerfAPRDetector1Power     DisplayString,
                        osamPerfAPRDetector2Power     DisplayString,
                        osamPerfLaserTemperature      INTEGER,
                        osamPerfTecCurrent            INTEGER,
                        osamPerfBiasCurrent           INTEGER,
                        osamPerfAmplifierGain         DisplayString,
                        osamPerfPCBTemperature        INTEGER,
						osam2PerfPump1BFDPower		  INTEGER,
						osam2PerfPump2BFDPower        INTEGER,
						osam2PerfPump1IBias			  INTEGER,	
						osam2PerfPump2IBias			  INTEGER,
						osam2PerfPump1ITEC			  INTEGER,
						osam2PerfPump2ITEC			  INTEGER,
						osam2PerfPump1Temp			  DisplayString,
						osam2PerfPump2Temp			  DisplayString,	
						osam2PerfGBInputPower		  DisplayString,
						osam2PerfGBOutputPower        DisplayString,
						osam2PerfAttenuation		  DisplayString			
                }

        osamPerfLocation  OBJECT-TYPE
                SYNTAX  CardLocation
                ACCESS  read-only
                STATUS  mandatory
                DESCRIPTION
                        "Location of the module."
                ::= { osamPerfEntry 1 }

        osamPerfShelf     OBJECT-TYPE
                SYNTAX  CardShelf
                ACCESS  read-only
                STATUS  mandatory
                DESCRIPTION
                        "The shelf number in which the module is plugged in."
                ::= { osamPerfEntry 2 }

        osamPerfSlot      OBJECT-TYPE
                SYNTAX  INTEGER (1..16)
                ACCESS  read-only
                STATUS  mandatory
                DESCRIPTION
                        "The slot number in which the module is plugged in."
                ::= { osamPerfEntry 3 }

        osamPerfState     OBJECT-TYPE
                SYNTAX  CardState
                ACCESS  read-only
                STATUS  mandatory
                DESCRIPTION
                        "The current state of the module."
                ::= { osamPerfEntry 4 }

        osamPerfStatus    OBJECT-TYPE
                SYNTAX  CardStatus
                ACCESS  read-only
                STATUS  mandatory
                DESCRIPTION
                        "The current alarm status of the channel."
                ::= { osamPerfEntry 5 }

        osamPerfLastBootTime  OBJECT-TYPE
                SYNTAX  DateAndTime
                ACCESS  read-only
                STATUS  mandatory
                DESCRIPTION
                        "The date and time of the last boot for this module."
                ::= { osamPerfEntry 6 }

        osamPerfAvailTime     OBJECT-TYPE
                SYNTAX  Counter
                ACCESS  read-only
                STATUS  mandatory
                DESCRIPTION
                        "The number of seconds in the most current 15 minutes
                         interval that this module has been up and running."
                ::= { osamPerfEntry 7 }

        osamPerfErrFreeSecs   OBJECT-TYPE
                SYNTAX  Counter
                ACCESS  read-only
                STATUS  mandatory
                DESCRIPTION
                        "The number of seconds in the most current 15 minutes
                         interval that this module has not experienced any
                         alarms."
                ::= { osamPerfEntry 8 }

        osamPerfAprStatus   OBJECT-TYPE
                SYNTAX  FlagType
                ACCESS  read-only
                STATUS  mandatory
                DESCRIPTION
                        "The status of the automatic power reduction mode.
						 Not applicable to OSAM-HP/LP module"
                ::= { osamPerfEntry 9 }

        osamPerfInputPower   OBJECT-TYPE
                SYNTAX  DisplayString
                ACCESS  read-only
                STATUS  mandatory
                DESCRIPTION
                        "The power at the input in dBm.
						 Not applicable to OSAM-HP/LP 
						 module"
                ::= { osamPerfEntry 10 }

        osamPerfBFDPower   OBJECT-TYPE
                SYNTAX  DisplayString
                ACCESS  read-only
                STATUS  mandatory
                DESCRIPTION
                        "The back facet diode reading in the pump laser;
                         related to the power output of the pump laser.
                         This values isn't calibrated and doesn't have a
                         unit.
						 Not applicable to OSAM-HP/LP module"
                ::= { osamPerfEntry 11 }

        osamPerfOutputPower   OBJECT-TYPE
                SYNTAX  DisplayString
                ACCESS  read-only
                STATUS  mandatory
                DESCRIPTION
                        "The power at the output port in dBm."
                ::= { osamPerfEntry 12 }

        osamPerfAPRDetector1Power   OBJECT-TYPE
                SYNTAX  DisplayString
                ACCESS  read-only
                STATUS  mandatory
                DESCRIPTION
                        "The automatic power reduction detector 1 reading 
                         in dBm. Two readings are provided for redundancy
                         purposes.
						 Not applicable to OSAM-HP/LP module"
                ::= { osamPerfEntry 13 }

        osamPerfAPRDetector2Power   OBJECT-TYPE
                SYNTAX  DisplayString
                ACCESS  read-only
                STATUS  mandatory
                DESCRIPTION
                        "The automatic power reduction detector 2 reading 
                         in dBm. Two readings are provided for redundancy
                         purposes.
						 Not applicable to OSAM-HP/LP module"
                ::= { osamPerfEntry 14 }

        osamPerfLaserTemperature   OBJECT-TYPE
                SYNTAX  INTEGER (15..35)
                ACCESS  read-only
                STATUS  mandatory
                DESCRIPTION
                        "The pump laser temperature in degree Celsius.
						 Not applicable to OSAM-HP/LP module"
                ::= { osamPerfEntry 15 }

        osamPerfTecCurrent   OBJECT-TYPE
                SYNTAX  INTEGER (0..1500)
                ACCESS  read-only
                STATUS  mandatory
                DESCRIPTION
                        "The Thermo-Electric Cooler current in mA.
						 Not applicable to OSAM-HP/LP module"
                ::= { osamPerfEntry 16 }

        osamPerfBiasCurrent   OBJECT-TYPE
                SYNTAX  INTEGER (0..255)
                ACCESS  read-only
                STATUS  mandatory
                DESCRIPTION
                        "The measured pump laser bias current in mA.
						 Not applicable to OSAM-HP/LP module"
                ::= { osamPerfEntry 17 }

        osamPerfAmplifierGain   OBJECT-TYPE
                SYNTAX  DisplayString
                ACCESS  read-only
                STATUS  mandatory
                DESCRIPTION
                        "The measured overall amplifier gain in dB."
                ::= { osamPerfEntry 18 }

        osamPerfPCBTemperature   OBJECT-TYPE
                SYNTAX  INTEGER (0..75)
                ACCESS  read-only
                STATUS  mandatory
                DESCRIPTION
                        "The temperature of the printed circuit board in
                         degree Celsius."
                ::= { osamPerfEntry 19 }

        osam2PerfPump1BFDPower   OBJECT-TYPE
                SYNTAX  INTEGER 
                ACCESS  read-only
                STATUS  mandatory
                DESCRIPTION
                        "The back facet diode reading in pump 1 laser;
                         related to the power output of the pump laser.
                         Unit to represent the value is DAC (Digital to
						 Analog converter)"
                ::= { osamPerfEntry 20 }

        osam2PerfPump2BFDPower   OBJECT-TYPE
                SYNTAX  INTEGER 
                ACCESS  read-only
                STATUS  mandatory
                DESCRIPTION
                        "The back facet diode reading in pump 2 laser;
                         related to the power output of the pump laser.
                         Unit to represent the value is DAC (Digital to
						 Analog converter).
						 Applicable only for OSAM-HP module"
                ::= { osamPerfEntry 21 }

        osam2PerfPump1IBias   OBJECT-TYPE
                SYNTAX  INTEGER 
                ACCESS  read-only
                STATUS  mandatory
                DESCRIPTION
                        "Indicates the bias current of Pump 1 in mA. 
						 The range of values of bias current range from 40 mA - 
						 barely turning on, to MaxIbias - maximum operating current 
						 recommended by the manufacturer.  
						 Pump IBias is used internally to set off alarms and to indicate the 
						 health of the module."
                ::= { osamPerfEntry 22 }

        osam2PerfPump2IBias   OBJECT-TYPE
                SYNTAX  INTEGER 
                ACCESS  read-only
                STATUS  mandatory
                DESCRIPTION
                        "Indicates the bias current of Pump 2 in mA. 
						 The range of values of bias current range from 40 mA - 
						 barely turning on, to MaxIbias - maximum operating current 
						 recommended by the manufacturer.  
						 Pump IBias is used internally to set off alarms and to indicate the 
						 health of the module.
						 Applicable only for OSAM-HP module"
                ::= { osamPerfEntry 23 }

        osam2PerfPump1ITEC   OBJECT-TYPE
                SYNTAX  INTEGER 
                ACCESS  read-only
                STATUS  mandatory
                DESCRIPTION
                        "Indicates the current level in mA of Thermal Electric Cooler (TEC)
						 used for cooling laser pump 1. "
                ::= { osamPerfEntry 24 }

        osam2PerfPump2ITEC   OBJECT-TYPE
                SYNTAX  INTEGER 
                ACCESS  read-only
                STATUS  mandatory
                DESCRIPTION
                        "Indicates the current level in mA of Thermal Electric Cooler (TEC)
						 used for cooling laser pump 2. 
						 Applicable only for OSAM-HP"
                ::= { osamPerfEntry 25 }

        osam2PerfPump1Temp   OBJECT-TYPE
                SYNTAX  DisplayString
                ACCESS  read-only
                STATUS  mandatory
                DESCRIPTION
                        "Laser pump (#1) temperature in degree celcius"
                ::= { osamPerfEntry 26 }

        osam2PerfPump2Temp   OBJECT-TYPE
                SYNTAX  DisplayString
                ACCESS  read-only
                STATUS  mandatory
                DESCRIPTION
                        "Laser pump (#2) temperature in degree celcius
						 Applicable only for OSAM-HP module"
                ::= { osamPerfEntry 27 }

        osam2PerfGBInputPower   OBJECT-TYPE
                SYNTAX  DisplayString
                ACCESS  read-only
                STATUS  mandatory
                DESCRIPTION
                        "Gain block input power in dBm."
                ::= { osamPerfEntry 28 }

        osam2PerfGBOutputPower   OBJECT-TYPE
                SYNTAX  DisplayString
                ACCESS  read-only
                STATUS  mandatory
                DESCRIPTION
                        "Gain block output power in dBm with attenuation
						 set to zero."
                ::= { osamPerfEntry 29 }

        osam2PerfAttenuation   OBJECT-TYPE
                SYNTAX  DisplayString
                ACCESS  read-only
                STATUS  mandatory
                DESCRIPTION
                        "Indicates optical attenuation in dB imposed by
						 variable optical attenuator(VOA)"
                ::= { osamPerfEntry 30 }

-- The elements in the rsmPerf subgroup of the current subgroup

        rsmNumEvents    OBJECT-TYPE
                SYNTAX  Counter
                ACCESS  read-only
                STATUS  mandatory
                DESCRIPTION
                        "Total number of all traps (events) generated by all
                         RSM's in this time slot (15 minutes)."
                ::= { rsmPerf 1 }
	

        rsmPerfTable    OBJECT-TYPE
                SYNTAX  SEQUENCE OF RsmPerfEntry
                ACCESS  not-accessible
                STATUS  mandatory
                DESCRIPTION
                        "This table represents the information for performance
                         data collected for each rsm card"
                ::= { rsmPerf 2 }

        rsmPerfEntry    OBJECT-TYPE
                SYNTAX  RsmPerfEntry
                ACCESS  not-accessible
                STATUS  mandatory
                DESCRIPTION
                        "Specifies the index for each row in the table below"
                INDEX { rsmPerfLocation, rsmPerfShelf, rsmPerfSlot }
                ::= { rsmPerfTable 1 }

        RsmPerfEntry    ::=
                SEQUENCE {
                        rsmPerfLocation 		CardLocation,
                        rsmPerfShelf    		CardShelf,
                        rsmPerfSlot     		CardSlot,
                        rsmPerfState    		CardState,
                        rsmPerfStatus   		CardStatus,
                        rsmLinkAState   		INTEGER,
                        rsmLinkAStatus  		INTEGER,
                        rsmLinkBState   		INTEGER,
                        rsmLinkBStatus  		INTEGER,
                        rsmLastBootTime 		DateAndTime,
                        rsmAvailTime    		Counter,
                        rsmErrFreeSecs  		Counter,
						rsmWorkingPower			INTEGER,
						rsmProtectionPower		INTEGER
                }

        rsmPerfLocation OBJECT-TYPE
                SYNTAX  CardLocation
                ACCESS  read-only
                STATUS  mandatory
                DESCRIPTION
                        "The location of the card."
                ::= { rsmPerfEntry 1 }

        rsmPerfShelf    OBJECT-TYPE
                SYNTAX  CardShelf
                ACCESS  read-only
                STATUS  mandatory
                DESCRIPTION
                        "The shelf the card is in."
                ::= { rsmPerfEntry 2 }

        rsmPerfSlot     OBJECT-TYPE
                SYNTAX  CardSlot
                ACCESS  read-only
                STATUS  mandatory
                DESCRIPTION
                        "The slot within the shelf the card is in."
                ::= { rsmPerfEntry 3 }

        rsmPerfState    OBJECT-TYPE
                SYNTAX  CardState
                ACCESS  read-only
                STATUS  mandatory
                DESCRIPTION
                        "The state of the rsm card.  The possible states
						 are: online, offline, empty, loopback or diag."
                ::= { rsmPerfEntry 4 }

        rsmPerfStatus   OBJECT-TYPE
                SYNTAX  CardStatus
                ACCESS  read-only
                STATUS  mandatory
                DESCRIPTION
                        "The status of the rsm card.  This status represents
                         the status of the rsm card and in general is
                         different from the status of the system."
                ::= { rsmPerfEntry 5 }

        rsmLinkAState    OBJECT-TYPE
                SYNTAX  INTEGER  {
					linked(1),
					notLinked(2),
					unknown(3)
				}
                ACCESS  read-only
                STATUS  mandatory
                DESCRIPTION
                        "The link state of path A (East), whether light
						 is being detected.  The states are:
                         linked, notLinked."
                ::= { rsmPerfEntry 6 }

        rsmLinkAStatus   OBJECT-TYPE
                SYNTAX  INTEGER 
					{
						active(1),
						standby(2),
						na(3)
					}
                ACCESS  read-only
                STATUS  mandatory
                DESCRIPTION
                        "The status of the card channel.  This status represents
                         the status of the link A (East) of the card and in general
						 is different from the status of the card."
                ::= { rsmPerfEntry 7 }


        rsmLinkBState    OBJECT-TYPE
                SYNTAX  INTEGER  
					{
						linked(1),
						notLinked(2),
						unknown(3)
					}
                ACCESS  read-only
                STATUS  mandatory
                DESCRIPTION
                        "The link state of path B (West), whether light
						 is being detected.  The states are:
                         linked, notLinked."
                ::= { rsmPerfEntry 8 }

        rsmLinkBStatus   OBJECT-TYPE
                SYNTAX  INTEGER 
					{
						active(1),
						standby(2),
						na(3)
					}
                ACCESS  read-only
                STATUS  mandatory
                DESCRIPTION
                        "The status of the card channel.  This status represents
                         the status of the link B (West) of the card and in general
						 is different from the status of the card."
                ::= { rsmPerfEntry 9 }

        rsmLastBootTime OBJECT-TYPE
                SYNTAX  DateAndTime
                ACCESS  read-only
                STATUS  mandatory
                DESCRIPTION
                        "The date and time of the last boot for this card."
                ::= { rsmPerfEntry 10 }

        rsmAvailTime    OBJECT-TYPE
                SYNTAX  Counter
                ACCESS  read-only
                STATUS  mandatory
                DESCRIPTION
                        "The number of seconds in this time slot (15 minutes)
                         that this rsm has been up and running.  This will
                         generally be the same as 15 minutes in seconds (900)."
                ::= { rsmPerfEntry 11 }

        rsmErrFreeSecs  OBJECT-TYPE
                SYNTAX  Counter
                ACCESS  read-only
                STATUS  mandatory
                DESCRIPTION
                        "The number of seconds in this time slot (15 minutes)
                         that this rsm has not experienced any alarms."
                ::= { rsmPerfEntry 12 }

        rsmWorkingPower OBJECT-TYPE
                SYNTAX  INTEGER 
                ACCESS  read-only
                STATUS  mandatory
                DESCRIPTION
                        "Working link power of the RSM card in dBm."
                ::= { rsmPerfEntry 13 }

        rsmProtectionPower OBJECT-TYPE
                SYNTAX  INTEGER 
                ACCESS  read-only
                STATUS  mandatory
                DESCRIPTION
                        "Protection link power of the RSM card in dBm."
                ::= { rsmPerfEntry 14 }

-- The elements in the upsmPerf subgroup of the current subgroup

        upsmNumEvents	OBJECT-TYPE
                SYNTAX  Counter
                ACCESS  read-only
                STATUS  mandatory
                DESCRIPTION
                        "Total number of all traps (events) generated by all
                         UPSM's in this time slot (15 minutes)."
                ::= { upsmPerf 1 }
	

        upsmPerfTable	OBJECT-TYPE
                SYNTAX  SEQUENCE OF UpsmPerfEntry
                ACCESS  not-accessible
                STATUS  mandatory
                DESCRIPTION
                        "This table represents the information for performance
                         data collected for each upsm card"
                ::= { upsmPerf 2 }

        upsmPerfEntry	OBJECT-TYPE
                SYNTAX  UpsmPerfEntry
                ACCESS  not-accessible
                STATUS  mandatory
                DESCRIPTION
                        "Specifies the index for each row in the table below"
                INDEX { upsmPerfLocation, upsmPerfShelf, upsmPerfSlot }
                ::= { upsmPerfTable 1 }

        UpsmPerfEntry    ::=
                SEQUENCE {
                        upsmPerfLocation 		CardLocation,
                        upsmPerfShelf    		CardShelf,
                        upsmPerfSlot     		CardSlot,
                        upsmPerfState    		CardState,
                        upsmPerfStatus   		CardStatus,
                        upsmLinkAState   		INTEGER,
                        upsmLinkAStatus  		INTEGER,
                        upsmLinkBState   		INTEGER,
                        upsmLinkBStatus  		INTEGER,
                        upsmLastBootTime 		DateAndTime,
                        upsmAvailTime    		Counter,
                        upsmErrFreeSecs  		Counter,
						upsmWorkingPower		INTEGER,
						upsmProtectionPower		INTEGER
                }

        upsmPerfLocation OBJECT-TYPE
                SYNTAX  CardLocation
                ACCESS  read-only
                STATUS  mandatory
                DESCRIPTION
                        "The location of the card."
                ::= { upsmPerfEntry 1 }

        upsmPerfShelf	OBJECT-TYPE
                SYNTAX  CardShelf
                ACCESS  read-only
                STATUS  mandatory
                DESCRIPTION
                        "The shelf the card is in."
                ::= { upsmPerfEntry 2 }

        upsmPerfSlot	OBJECT-TYPE
                SYNTAX  CardSlot
                ACCESS  read-only
                STATUS  mandatory
                DESCRIPTION
                        "The slot within the shelf the card is in."
                ::= { upsmPerfEntry 3 }

        upsmPerfState	OBJECT-TYPE
                SYNTAX  CardState
                ACCESS  read-only
                STATUS  mandatory
                DESCRIPTION
                        "The state of the upsm card.  The possible states
						 are: online, offline, empty, loopback or diag."
                ::= { upsmPerfEntry 4 }

        upsmPerfStatus	OBJECT-TYPE
                SYNTAX  CardStatus
                ACCESS  read-only
                STATUS  mandatory
                DESCRIPTION
                        "The status of the upsm card.  This status represents
                         the status of the upsm card and in general is
                         different from the status of the system."
                ::= { upsmPerfEntry 5 }

        upsmLinkAState	OBJECT-TYPE
                SYNTAX  INTEGER  
					{
						linked(1),
						notLinked(2),
						unknown(3)
					}
                ACCESS  read-only
                STATUS  mandatory
                DESCRIPTION
                        "The link state of path A (East), whether light
						 is being detected.  The states are:
                         linked, notLinked."
                ::= { upsmPerfEntry 6 }

        upsmLinkAStatus   OBJECT-TYPE
                SYNTAX  INTEGER 
					{
						active(1),
						standby(2),
						hibernation(3)
					}
                ACCESS  read-only
                STATUS  mandatory
                DESCRIPTION
                        "The status of the card channel.  This status represents
                         the status of the link A (East) of the card and in general
						 is different from the status of the card."
                ::= { upsmPerfEntry 7 }

        upsmLinkBState	OBJECT-TYPE
                SYNTAX  INTEGER  
					{
						linked(1),
						notLinked(2),
						unknown(3)
					}
                ACCESS  read-only
                STATUS  mandatory
                DESCRIPTION
                        "The link state of path B (West), whether light
						 is being detected.  The states are:
                         linked, notLinked."
                ::= { upsmPerfEntry 8 }

        upsmLinkBStatus	OBJECT-TYPE
                SYNTAX  INTEGER 
					{
						active(1),
						standby(2),
						hibernation(3)
					}
                ACCESS  read-only
                STATUS  mandatory
                DESCRIPTION
                        "The status of the card channel.  This status represents
                         the status of the link B (West) of the card and in general
						 is different from the status of the card."
                ::= { upsmPerfEntry 9 }

        upsmLastBootTime OBJECT-TYPE
                SYNTAX  DateAndTime
                ACCESS  read-only
                STATUS  mandatory
                DESCRIPTION
                        "The date and time of the last boot for this card."
                ::= { upsmPerfEntry 10 }

        upsmAvailTime	OBJECT-TYPE
                SYNTAX  Counter
                ACCESS  read-only
                STATUS  mandatory
                DESCRIPTION
                        "The number of seconds in this time slot (15 minutes)
                         that this upsm has been up and running.  This will
                         generally be the same as 15 minutes in seconds (900)."
                ::= { upsmPerfEntry 11 }

        upsmErrFreeSecs	OBJECT-TYPE
                SYNTAX  Counter
                ACCESS  read-only
                STATUS  mandatory
                DESCRIPTION
                        "The number of seconds in this time slot (15 minutes)
                         that this upsm has not experienced any alarms."
                ::= { upsmPerfEntry 12 }

        upsmWorkingPower OBJECT-TYPE
                SYNTAX  INTEGER 
                ACCESS  read-only
                STATUS  mandatory
                DESCRIPTION
                        "Working link power of the UPSM card in dBm."
                ::= { upsmPerfEntry 13 }

        upsmProtectionPower OBJECT-TYPE
                SYNTAX  INTEGER 
                ACCESS  read-only
                STATUS  mandatory
                DESCRIPTION
                        "Protection link power of the UPSM card in dBm."
                ::= { upsmPerfEntry 14 }

     -- The elements in the routingPerf subgroup of the current subgroup
	

        imnRoutingPerfTable    OBJECT-TYPE
                SYNTAX  SEQUENCE OF ImnRoutingPerfEntry
                ACCESS  not-accessible
                STATUS  mandatory
                DESCRIPTION
                        "This table represents the information for performance
                         data collected for each route"
                ::= { routingPerf 1 }

        imnRoutingPerfEntry    OBJECT-TYPE
                SYNTAX  ImnRoutingPerfEntry
                ACCESS  not-accessible
                STATUS  mandatory
                DESCRIPTION
                        "Specifies the index for each row in the table below"
                INDEX { imnRoutePerfIpDest}
                ::= { imnRoutingPerfTable 1 }

        ImnRoutingPerfEntry    ::=
                SEQUENCE {
						imnRoutePerfIpDest	IPADDRESS,
						imnRoutePerfStatus	INTEGER
                }


        imnRoutePerfIpDest OBJECT-TYPE
                SYNTAX  IpAddress
                ACCESS  read-only
                STATUS  mandatory
                DESCRIPTION
                       "Destination IP address. Not supported for
						remote TMM masters."
                ::= { imnRoutingPerfEntry 1}

		imnRoutePerfStatus     OBJECT-TYPE
                SYNTAX  INTEGER { 
					dead(1),
					comatose(2),
					active(3)
					}
                ACCESS  read-only
                STATUS  mandatory
                DESCRIPTION
				"Is the route active, comatose or dead"
                ::= { imnRoutingPerfEntry 2}



        -- The elements in the systemHist subgroup of the historical subgroup

        sysHistTable    OBJECT-TYPE
                SYNTAX  SEQUENCE OF SysHistEntry
                ACCESS  not-accessible
                STATUS  mandatory
                DESCRIPTION
                        "This table represents the information for historical
                         data collected for the overall system"
                ::= { systemHist 1 }

        sysHistEntry    OBJECT-TYPE
                SYNTAX  SysHistEntry
                ACCESS  not-accessible
                STATUS  mandatory
                DESCRIPTION
                        "Specifies the index for each row in the table below"
                INDEX { sysHMode }
                ::= { sysHistTable 1 }

        SysHistEntry    ::=
                SEQUENCE {
                        sysHMode          HistoryMode,
                        sysHLastBootTime  DateAndTime,
                        sysHAvailTime     Counter,
                        sysHErrFreeSecs   Counter
                }

        sysHMode        OBJECT-TYPE
                SYNTAX  HistoryMode
                ACCESS  read-only
                STATUS  mandatory
                DESCRIPTION
                        "The mode of the data collection.  Valid values are:
                         daily or longterm."
                ::= { sysHistEntry 1 }

        sysHLastBootTime  OBJECT-TYPE
                SYNTAX  DateAndTime
                ACCESS  read-only
                STATUS  mandatory
                DESCRIPTION
                        "The date and time of the last system boot.  This time
                         represents the boot time of a CP card.  It is also
                         anonymous with the power-up cycle of the chassis."
                ::= { sysHistEntry 2 }

        sysHAvailTime   OBJECT-TYPE
                SYNTAX  Counter
                ACCESS  read-only
                STATUS  mandatory
                DESCRIPTION
                        "The number of seconds since the system has been up
                         and running.  The criteria for the system
                         available time is having at least one CP
                         running with atmost non-service affecting minor
                         alarm system status"
                ::= { sysHistEntry 3 }

        sysHErrFreeSecs OBJECT-TYPE
                SYNTAX  Counter
                ACCESS  read-only
                STATUS  mandatory
                DESCRIPTION
                        "The number of seconds that the device has not
                         experienced any alarms.  This counter is across all
                         cards in the chassis.  The system must be in Normal
                         status for this counter to be incremented."
                ::= { sysHistEntry 4 }


        -- The elements in the downloadHist subgroup of the historical subgroup

        dlHistTable     OBJECT-TYPE
                SYNTAX  SEQUENCE OF DlHistEntry
                ACCESS  not-accessible
                STATUS  mandatory
                DESCRIPTION
                        "This table represents the information for historical
                         data collected for the download process"
                ::= { downloadHist 1 }

        dlHistEntry     OBJECT-TYPE
                SYNTAX  DlHistEntry
                ACCESS  not-accessible
                STATUS  mandatory
                DESCRIPTION
                        "Specifies the index for each row in the table below"
                INDEX { dlHMode }
                ::= { dlHistTable 1 }

        DlHistEntry     ::=
                SEQUENCE {
                        dlHMode         HistoryMode,
                        dlHOkDownloads  Counter,
                        dlHBadDownloads Counter,
                        dlHLongestTime  Gauge,
                        dlHLongestSize  Gauge
                }

        dlHMode         OBJECT-TYPE
                SYNTAX  HistoryMode
                ACCESS  read-only 
                STATUS  mandatory
                DESCRIPTION
                        "The mode of the data collection.  Valid values are:
                         daily or longterm."
                ::= { dlHistEntry 1 }

        dlHOkDownloads  OBJECT-TYPE
                SYNTAX  Counter
                ACCESS  read-only 
                STATUS  mandatory
                DESCRIPTION
                        "The number of successful downloads"
                ::= { dlHistEntry 2 }

        dlHBadDownloads OBJECT-TYPE
                SYNTAX  Counter
                ACCESS  read-only 
                STATUS  mandatory
                DESCRIPTION
                        "The number of failed downloads"
                ::= { dlHistEntry 3 }

        dlHLongestTime  OBJECT-TYPE
                SYNTAX  Gauge
                ACCESS  read-only 
                STATUS  mandatory
                DESCRIPTION
                        "Longest time for any download, in seconds"
                ::= { dlHistEntry 4 }

        dlHLongestSize  OBJECT-TYPE
                SYNTAX  Gauge
                ACCESS  read-only 
                STATUS  mandatory
                DESCRIPTION
                        "Longest download size for any download, in bytes"
                ::= { dlHistEntry 5 }


        -- The elements in the cpHist subgroup of the historical subgroup

        cpHistTable     OBJECT-TYPE
                SYNTAX  SEQUENCE OF CpHistEntry
                ACCESS  not-accessible
                STATUS  mandatory
                DESCRIPTION
                        "This table represents the information for historical
                         data collected for the communication card"
                ::= { cpHist 1 }

        cpHistEntry     OBJECT-TYPE
                SYNTAX  CpHistEntry
                ACCESS  not-accessible
                STATUS  mandatory
                DESCRIPTION
                        "Specifies the index for each row in the table below"
                INDEX { cpHMode }
                ::= { cpHistTable 1 }

        CpHistEntry     ::=
                SEQUENCE {
                        cpHMode         HistoryMode,
                        cpHNumEvents    Counter,
                        cpHTrapsSent    Counter,
                        cpHSNMPCmdsRcvd Counter
                }

        cpHMode         OBJECT-TYPE
                SYNTAX  HistoryMode
                ACCESS  read-only
                STATUS  mandatory
                DESCRIPTION
                        "The mode of the data collection.  Valid values are:
                         daily or longterm."
                ::= { cpHistEntry 1 }

        cpHNumEvents    OBJECT-TYPE
                SYNTAX  Counter
                ACCESS  read-only
                STATUS  mandatory
                DESCRIPTION
                        "Total number of events received by the active CP"
                ::= { cpHistEntry 2 }

        cpHTrapsSent    OBJECT-TYPE
                SYNTAX  Counter
                ACCESS  read-only
                STATUS  mandatory
                DESCRIPTION
                        "Total number of traps sent by the active CP"
                ::= { cpHistEntry 3 }

        cpHSNMPCmdsRcvd OBJECT-TYPE
                SYNTAX  Counter
                ACCESS  read-only
                STATUS  mandatory
                DESCRIPTION
                        "Total number of SNMP commands received by the active
                         CP."
                ::= { cpHistEntry 4 }

        cpHCntrTable    OBJECT-TYPE
                SYNTAX  SEQUENCE OF CpHCntrEntry
                ACCESS  not-accessible
                STATUS  mandatory
                DESCRIPTION
                        "This table represents the information for each
                         entry for the software counters.  It is only
			 applicable to the active MPM card."
                ::= { cpHist 2 }

        cpHCntrEntry    OBJECT-TYPE
                SYNTAX  CpHCntrEntry
                ACCESS  not-accessible
                STATUS  mandatory
                DESCRIPTION
                        "Specifies the index for each row in the table below"
                INDEX { cpHCntrMode, cpCntrShelf, cpCntrSlot, cpCntrType }
                ::= { cpHCntrTable 1 }

        CpHCntrEntry    ::=
                SEQUENCE {
                        cpHCntrMode     HistoryMode,
                        cpHCntrShelf    CardShelf,
                        cpHCntrSlot     INTEGER,
                        cpHCntrType     INTEGER,
                        cpHTotPktSent   Counter,
                        cpHTotPktRcvd   Counter,
                        cpHBadPktRcvd   Counter,
                        cpHTotBadTrans  Counter,
                        cpHBytesSent    Counter,
                        cpHBytesRcvd    Counter,
                        cpHMsgsDlvrd    Counter,
                        cpHBufAllocFail Counter,
                        cpHEcbAllocFail Counter
                }

        cpHCntrMode     OBJECT-TYPE
                SYNTAX  HistoryMode
                ACCESS  read-only
                STATUS  mandatory
                DESCRIPTION
                        "The mode of the data collection.  Valid values are:
                         daily or longterm."
                ::= { cpHCntrEntry 1 }

        cpHCntrShelf    OBJECT-TYPE
                SYNTAX  CardShelf
                ACCESS  read-only
                STATUS  mandatory
                DESCRIPTION
                        "The shelf the card is in.  Valid values are: 1 to 10.
                         The system automatically determines the right value
                         for this entry based on the value of the current
                         active CP card."
                ::= { cpHCntrEntry 2 }

        cpHCntrSlot     OBJECT-TYPE
                SYNTAX  CardSlot
                ACCESS  read-only
                STATUS  mandatory
                DESCRIPTION
                        "The slot within the shelf the card is in. The
                         system automatically determines the right value
                         for this entry based on the value of the current
                         active CP card."
                ::= { cpHCntrEntry 3 }

        cpHCntrType     OBJECT-TYPE
                SYNTAX  INTEGER { spi(1) }
                ACCESS  read-only
                STATUS  mandatory
                DESCRIPTION
                        "The type of the software counter data in this row.
                         The data is collected for the SPI data channels."
                ::= { cpHCntrEntry 4 }

        cpHTotPktSent   OBJECT-TYPE
                SYNTAX  Counter
                ACCESS  read-only
                STATUS  mandatory
                DESCRIPTION
                        "The number of data packets sent over the given data
                         channel."
                ::= { cpHCntrEntry 5 }

        cpHTotPktRcvd   OBJECT-TYPE
                SYNTAX  Counter
                ACCESS  read-only
                STATUS  mandatory
                DESCRIPTION
                        "The number of data packets received over the given
                         data channel."
                ::= { cpHCntrEntry 6 }

        cpHBadPktRcvd   OBJECT-TYPE
                SYNTAX  Counter
                ACCESS  read-only
                STATUS  mandatory
                DESCRIPTION
                        "The number of bad data packets received over the given
                         data channel."
                ::= { cpHCntrEntry 7 }

        cpHTotBadTrans  OBJECT-TYPE
                SYNTAX  Counter
                ACCESS  read-only
                STATUS  mandatory
                DESCRIPTION
                        "The number of bad data transmissions over the given
                         data channel."
                ::= { cpHCntrEntry 8 }

        cpHBytesSent    OBJECT-TYPE
                SYNTAX  Counter
                ACCESS  read-only
                STATUS  mandatory
                DESCRIPTION
                        "Total number of bytes sent over the given
                         data channel."
                ::= { cpHCntrEntry 9 }

        cpHBytesRcvd    OBJECT-TYPE
                SYNTAX  Counter
                ACCESS  read-only
                STATUS  mandatory
                DESCRIPTION
                        "Total number of data bytes received over the given
                         data channel."
                ::= { cpHCntrEntry 10 }

        cpHMsgsDlvrd    OBJECT-TYPE
                SYNTAX  Counter
                ACCESS  read-only
                STATUS  mandatory
                DESCRIPTION
                        "The number of complete messages delivered over the
                         given data channel."
                ::= { cpHCntrEntry 11 }

        cpHBufAllocFail OBJECT-TYPE
                SYNTAX  Counter
                ACCESS  read-only
                STATUS  mandatory
                DESCRIPTION
                        "Number of buffer allocation failures for the given
                         data channel."
                ::= { cpHCntrEntry 12 }

        cpHEcbAllocFail OBJECT-TYPE
                SYNTAX  Counter
                ACCESS  read-only
                STATUS  mandatory
                DESCRIPTION
                        "Number of Event Control Block allocation failures
                         for the given data channel."
                ::= { cpHCntrEntry 13 }

        cpHHistTable    OBJECT-TYPE
                SYNTAX  SEQUENCE OF CpHHistEntry
                ACCESS  not-accessible
                STATUS  mandatory
                DESCRIPTION
                        "This table represents the information for performance
                         data collected for each communication processor"
                ::= { cpHist 3 }

        cpHHistEntry    OBJECT-TYPE
                SYNTAX  CpHHistEntry
                ACCESS  not-accessible
                STATUS  mandatory
                DESCRIPTION
                        "Specifies the index for each row in the table below"
                INDEX { cpHHistMode, cpHHistShelf, cpHHistSlot }
                ::= { cpHHistTable 1 }

        CpHHistEntry    ::=
                SEQUENCE {
                        cpHHistMode     HistoryMode,
                        cpHHistShelf    CardShelf,
                        cpHHistSlot     INTEGER,
                        cpHLastBootTime DateAndTime,
                        cpHAvailTime    Counter,
                        cpHErrFreeSecs  Counter
                }

        cpHHistMode     OBJECT-TYPE
                SYNTAX  HistoryMode
                ACCESS  read-only
                STATUS  mandatory
                DESCRIPTION
                        "The mode of the data collection.  Valid values are:
                         daily or longterm."
                ::= { cpHHistEntry 1 }

        cpHHistShelf    OBJECT-TYPE
                SYNTAX  CardShelf
                ACCESS  read-only
                STATUS  mandatory
                DESCRIPTION
                        "The shelf the card is in.  Valid values are: 1 to 10"
                ::= { cpHHistEntry 2 }

        cpHHistSlot     OBJECT-TYPE
                SYNTAX  CardSlot
                ACCESS  read-only
                STATUS  mandatory
                DESCRIPTION
                        "The slot within the shelf the card is in."
                ::= { cpHHistEntry 3 }

        cpHLastBootTime OBJECT-TYPE
                SYNTAX  DateAndTime
                ACCESS  read-only
                STATUS  mandatory
                DESCRIPTION
                        "The date and time of the last boot for this CP."
                ::= { cpHHistEntry 4 }

        cpHAvailTime    OBJECT-TYPE
                SYNTAX  Counter
                ACCESS  read-only
                STATUS  mandatory
                DESCRIPTION
                        "The number of seconds that this CP has been up and
			 running."
                ::= { cpHHistEntry 5 }

        cpHErrFreeSecs  OBJECT-TYPE
                SYNTAX  Counter
                ACCESS  read-only
                STATUS  mandatory
                DESCRIPTION
                        "The number of seconds that this CP has not
                         experienced any alarms."
                ::= { cpHHistEntry 6 }


        -- The elements in the ccHist subgroup of the historical subgroup

        ccHistTable     OBJECT-TYPE
                SYNTAX  SEQUENCE OF CcHistEntry
                ACCESS  not-accessible
                STATUS  mandatory
                DESCRIPTION
                        "This table represents the information for historical
                         data collected for the channel card"
                ::= { ccHist 1 }

        ccHistEntry     OBJECT-TYPE
                SYNTAX  CcHistEntry
                ACCESS  not-accessible
                STATUS  mandatory
                DESCRIPTION
                        "Specifies the index for each row in the table below"
                INDEX { ccHMode }
                ::= { ccHistTable 1 }

        CcHistEntry     ::=
                SEQUENCE {
                        ccHMode         HistoryMode,
                        ccHNumEvents    Counter
                }

        ccHMode         OBJECT-TYPE
                SYNTAX  HistoryMode
                ACCESS  read-only
                STATUS  mandatory
                DESCRIPTION
                        "The mode of the data collection.  Valid values are:
                         daily or longterm."
                ::= { ccHistEntry 1 }

        ccHNumEvents    OBJECT-TYPE
                SYNTAX  Counter
                ACCESS  read-only
                STATUS  mandatory
                DESCRIPTION
                        "Total number of events received for all CC's"
                ::= { ccHistEntry 2 }

        ccHCntrTable    OBJECT-TYPE
                SYNTAX  SEQUENCE OF CcHCntrEntry
                ACCESS  not-accessible
                STATUS  mandatory
                DESCRIPTION
                        "This table represents the information for each
                         entry for the software counters."
                ::= { ccHist 2 }

        ccHCntrEntry    OBJECT-TYPE
                SYNTAX  CcHCntrEntry
                ACCESS  not-accessible
                STATUS  mandatory
                DESCRIPTION
                        "Specifies the index for each row in the table below"
                INDEX { ccHCntrMode, ccHCntrLocation, ccHCntrShelf,
                        ccHCntrSlot, ccHCntrType }
                ::= { ccHCntrTable 1 }

        CcHCntrEntry    ::=
                SEQUENCE {
                        ccHCntrMode     HistoryMode,
                        ccHCntrLocation CardLocation,
                        ccHCntrShelf    CardShelf,
                        ccHCntrSlot     INTEGER,
                        ccHCntrType     INTEGER,
                        ccHTotPktSent   Counter,
                        ccHTotPktRcvd   Counter,
                        ccHBadPktRcvd   Counter,
                        ccHTotBadTrans  Counter,
                        ccHBytesSent    Counter,
                        ccHBytesRcvd    Counter,
                        ccHMsgsDlvrd    Counter,
                        ccHBufAllocFail Counter,
                        ccHEcbAllocFail Counter
                }

        ccHCntrMode     OBJECT-TYPE
                SYNTAX  HistoryMode
                ACCESS  read-only
                STATUS  mandatory
                DESCRIPTION
                        "The mode of the data collection.  Valid values are:
                         daily or longterm."
                ::= { ccHCntrEntry 1 }

        ccHCntrLocation OBJECT-TYPE
                SYNTAX  CardLocation
                ACCESS  read-only
                STATUS  mandatory
                DESCRIPTION
                        "The location of the CC card.  The values are: Local
                         or Remote.  The system automatically determines the
                         right value for this entry based on the known
                         CC cards."
                ::= { ccHCntrEntry 2 }

        ccHCntrShelf    OBJECT-TYPE
                SYNTAX  CardShelf
                ACCESS  read-only
                STATUS  mandatory
                DESCRIPTION
                        "The shelf the card is in.  Valid values are: 1 to 10.
                         The system automatically determines the right value
                         for this entry based on the known (available) CC
                         cards."
                ::= { ccHCntrEntry 3 }

        ccHCntrSlot     OBJECT-TYPE
                SYNTAX  CardSlot
                ACCESS  read-only
                STATUS  mandatory
                DESCRIPTION
                        "The slot within the shelf the card is in.  The
                         system automatically determines the right value
                         for this entry based on the known (available)
                         CC cards."
                ::= { ccHCntrEntry 4 }

        ccHCntrType     OBJECT-TYPE
                SYNTAX  INTEGER { spi(1), iwm(2) }
                ACCESS  read-only
                STATUS  mandatory
                DESCRIPTION
                        "The type of the software counter data in this row.
                         The data is collected for the SPI data channels."
                ::= { ccHCntrEntry 5 }

        ccHTotPktSent   OBJECT-TYPE
                SYNTAX  Counter
                ACCESS  read-only
                STATUS  mandatory
                DESCRIPTION
                        "The number of data packets sent over the given data
                         channel."
                ::= { ccHCntrEntry 6 }

        ccHTotPktRcvd   OBJECT-TYPE
                SYNTAX  Counter
                ACCESS  read-only
                STATUS  mandatory
                DESCRIPTION
                        "The number of data packets received over the given
                         data channel."
                ::= { ccHCntrEntry 7 }

        ccHBadPktRcvd   OBJECT-TYPE
                SYNTAX  Counter
                ACCESS  read-only
                STATUS  mandatory
                DESCRIPTION
                        "The number of bad data packets received over the given
                         data channel."
                ::= { ccHCntrEntry 8 }

        ccHTotBadTrans  OBJECT-TYPE
                SYNTAX  Counter
                ACCESS  read-only
                STATUS  mandatory
                DESCRIPTION
                        "The number of bad data transmissions over the given
                         data channel."
                ::= { ccHCntrEntry 9 }

        ccHBytesSent    OBJECT-TYPE
                SYNTAX  Counter
                ACCESS  read-only
                STATUS  mandatory
                DESCRIPTION
                        "Total number of bytes sent over the given
                         data channel."
                ::= { ccHCntrEntry 10 }

        ccHBytesRcvd    OBJECT-TYPE
                SYNTAX  Counter
                ACCESS  read-only
                STATUS  mandatory
                DESCRIPTION
                        "Total number of data bytes received over the given
                         data channel."
                ::= { ccHCntrEntry 11 }

        ccHMsgsDlvrd    OBJECT-TYPE
                SYNTAX  Counter
                ACCESS  read-only
                STATUS  mandatory
                DESCRIPTION
                        "The number of complete messages delivered over the
                         given data channel."
                ::= { ccHCntrEntry 12 }

        ccHBufAllocFail OBJECT-TYPE
                SYNTAX  Counter
                ACCESS  read-only
                STATUS  mandatory
                DESCRIPTION
                        "Number of buffer allocation failures for the given
                         data channel."
                ::= { ccHCntrEntry 13 }

        ccHEcbAllocFail OBJECT-TYPE
                SYNTAX  Counter
                ACCESS  read-only
                STATUS  mandatory
                DESCRIPTION
                        "Number of Event Control Block allocation failures
                         for the given data channel."
                ::= { ccHCntrEntry 14 }

        ccHHistTable    OBJECT-TYPE
                SYNTAX  SEQUENCE OF CcHHistEntry
                ACCESS  not-accessible
                STATUS  mandatory
                DESCRIPTION
                        "This table represents the information for performance
                         data collected for each channel card"
                ::= { ccHist 3 }

        ccHHistEntry    OBJECT-TYPE
                SYNTAX  CcHHistEntry
                ACCESS  not-accessible
                STATUS  mandatory
                DESCRIPTION
                        "Specifies the index for each row in the table below"
                INDEX { ccHHistMode, ccHHistLocation, ccHHistShelf,
                        ccHHistSlot }
                ::= { ccHHistTable 1 }

        CcHHistEntry    ::=
                SEQUENCE {
                        ccHHistMode     HistoryMode,
                        ccHHistLocation CardLocation,
                        ccHHistShelf    CardShelf,
                        ccHHistSlot     INTEGER,
                        ccHLastBootTime DateAndTime,
                        ccHAvailTime    Counter,
                        ccHErrFreeSecs  Counter
                }

        ccHHistMode     OBJECT-TYPE
                SYNTAX  HistoryMode
                ACCESS  read-only
                STATUS  mandatory
                DESCRIPTION
                        "The mode of the data collection.  Valid values are:
                         daily or longterm."
                ::= { ccHHistEntry 1 }

        ccHHistLocation OBJECT-TYPE
                SYNTAX  CardLocation
                ACCESS  read-only
                STATUS  mandatory
                DESCRIPTION
                        "The location of the card.  Valid choices are Local
                         or Remote.  The system automatically selects this
                         value based on the known (available) CC cards."
                ::= { ccHHistEntry 2 }

        ccHHistShelf    OBJECT-TYPE
                SYNTAX  CardShelf
                ACCESS  read-only
                STATUS  mandatory
                DESCRIPTION
                        "The shelf the card is in.  Valid values are: 1 to 10"
                ::= { ccHHistEntry 3 }

        ccHHistSlot     OBJECT-TYPE
                SYNTAX  CardSlot
                ACCESS  read-only
                STATUS  mandatory
                DESCRIPTION
                        "The slot within the shelf the card is in."
                ::= { ccHHistEntry 4 }

        ccHLastBootTime OBJECT-TYPE
                SYNTAX  DateAndTime
                ACCESS  read-only
                STATUS  mandatory
                DESCRIPTION
                        "The date and time of the last boot for this card."
                ::= { ccHHistEntry 5 }

        ccHAvailTime    OBJECT-TYPE
                SYNTAX  Counter
                ACCESS  read-only
                STATUS  mandatory
                DESCRIPTION
                        "The number of seconds that this CC has been up and
			 running."
                ::= { ccHHistEntry 6 }

        ccHErrFreeSecs  OBJECT-TYPE
                SYNTAX  Counter
                ACCESS  read-only
                STATUS  mandatory
                DESCRIPTION
                        "The number of seconds that this CC has not experienced
			 any alarms."
                ::= { ccHHistEntry 7 }


        -- The elements in the muxHist subgroup of the historical subgroup

        muxHistTable    OBJECT-TYPE
                SYNTAX  SEQUENCE OF MuxHistEntry
                ACCESS  not-accessible
                STATUS  mandatory
                DESCRIPTION
                        "This table represents the information for historical
                         data collected for the mux/demux card"
                ::= { muxHist 1 }

        muxHistEntry    OBJECT-TYPE
                SYNTAX  MuxHistEntry
                ACCESS  not-accessible
                STATUS  mandatory
                DESCRIPTION
                        "Specifies the index for each row in the table below"
                INDEX { muxHMode }
                ::= { muxHistTable 1 }

        MuxHistEntry    ::=
                SEQUENCE {
                        muxHMode        HistoryMode,
                        muxHNumEvents   Counter
                }

        muxHMode        OBJECT-TYPE
                SYNTAX  HistoryMode
                ACCESS  read-only
                STATUS  mandatory
                DESCRIPTION
                        "The mode of the data collection.  Valid values are:
                         daily or longterm."
                ::= { muxHistEntry 1 }

        muxHNumEvents   OBJECT-TYPE
                SYNTAX  Counter
                ACCESS  read-only
                STATUS  mandatory
                DESCRIPTION
                        "Total number of all traps (events) generated by all
                         MUX's."
                ::= { muxHistEntry 2 }

        muxHHistTable   OBJECT-TYPE
                SYNTAX  SEQUENCE OF MuxHHistEntry
                ACCESS  not-accessible
                STATUS  mandatory
                DESCRIPTION
                        "This table represents the information for performance
                         data collected for each mux/demux card"
                ::= { muxHist 2 }

        muxHHistEntry   OBJECT-TYPE
                SYNTAX  MuxHHistEntry
                ACCESS  not-accessible
                STATUS  mandatory
                DESCRIPTION
                        "Specifies the index for each row in the table below"
                INDEX { muxHHistMode, muxHHistLocation, muxHHistShelf,
                        muxHHistSlot }
                ::= { muxHHistTable 1 }

        MuxHHistEntry   ::=
                SEQUENCE {
                        muxHHistMode      HistoryMode,
                        muxHHistLocation  CardLocation,
                        muxHHistShelf     CardShelf,
                        muxHHistSlot      INTEGER,
                        muxHHistType      INTEGER,
                        muxHLastBootTime  DateAndTime,
                        muxHAvailTime     Counter,
                        muxHErrFreeSecs   Counter
                }

        muxHHistMode    OBJECT-TYPE
                SYNTAX  HistoryMode
                ACCESS  read-only
                STATUS  mandatory
                DESCRIPTION
                        "The mode of the data collection.  Valid values are:
                         daily or longterm."
                ::= { muxHHistEntry 1 }

        muxHHistLocation  OBJECT-TYPE
                SYNTAX  CardLocation
                ACCESS  read-only
                STATUS  mandatory
                DESCRIPTION
                        "The location of the card.  Choices are local or
                         remote."
                ::= { muxHHistEntry 2 }

        muxHHistShelf   OBJECT-TYPE
                SYNTAX  CardShelf
                ACCESS  read-only
                STATUS  mandatory
                DESCRIPTION
                        "The shelf the card is in.  Valid values are: 1 to 10"
                ::= { muxHHistEntry 3 }

        muxHHistSlot    OBJECT-TYPE
                SYNTAX  CardSlot
                ACCESS  read-only
                STATUS  mandatory
                DESCRIPTION
                        "The slot within the shelf the card is in."
                ::= { muxHHistEntry 4 }

        muxHHistType    OBJECT-TYPE
                SYNTAX  INTEGER { mux(4), demux(5), w4cd(10), w2cmd(13), w4cm(21)}
                ACCESS  read-only
                STATUS  mandatory
                DESCRIPTION
                        "The type of the mux.  The choices are: mux or demux."
                ::= { muxHHistEntry 5 }

        muxHLastBootTime  OBJECT-TYPE
                SYNTAX  DateAndTime
                ACCESS  read-only
                STATUS  mandatory
                DESCRIPTION
                        "The date and time of the last boot for this card."
                ::= { muxHHistEntry 6 }

        muxHAvailTime   OBJECT-TYPE
                SYNTAX  Counter
                ACCESS  read-only
                STATUS  mandatory
                DESCRIPTION
                        "The number of seconds that this Mux has been up and
                         running."
                ::= { muxHHistEntry 7 }

        muxHErrFreeSecs OBJECT-TYPE
                SYNTAX  Counter
                ACCESS  read-only
                STATUS  mandatory
                DESCRIPTION
                        "The number of seconds that this mux has not
                         experienced any alarms."
                ::= { muxHHistEntry 8 }


        -- The elements in the psHist subgroup of the historical subgroup

        psHistTable     OBJECT-TYPE
                SYNTAX  SEQUENCE OF PsHistEntry
                ACCESS  not-accessible
                STATUS  mandatory
                DESCRIPTION
                        "This table represents the information for historical
                         data collected for the power supply card"
                ::= { psHist 1 }

        psHistEntry     OBJECT-TYPE
                SYNTAX  PsHistEntry
                ACCESS  not-accessible
                STATUS  mandatory
                DESCRIPTION
                        "Specifies the index for each row in the table below"
                INDEX { psHMode }
                ::= { psHistTable 1 }

        PsHistEntry     ::=
                SEQUENCE {
                        psHMode         HistoryMode,
                        psHNumEvents    Counter
                }

        psHMode         OBJECT-TYPE
                SYNTAX  HistoryMode
                ACCESS  not-accessible
                STATUS  mandatory
                DESCRIPTION
                        "The mode of the data collection.  Valid values are:
                         daily or longterm."
                ::= { psHistEntry 1 }

        psHNumEvents    OBJECT-TYPE
                SYNTAX  Counter
                ACCESS  not-accessible
                STATUS  mandatory
                DESCRIPTION
                        "Total number of all traps (events) generated by all
                         Power Supplies."
                ::= { psHistEntry 2 }


        -- The elements in the muxHist subgroup of the historical subgroup

        fadmHistTable    OBJECT-TYPE
                SYNTAX  SEQUENCE OF FadmHistEntry
                ACCESS  not-accessible
                STATUS  mandatory
                DESCRIPTION
                        "This table represents the information for historical
                         data collected for the fadm card"
                ::= { fadmHist 1 }

        fadmHistEntry    OBJECT-TYPE
                SYNTAX  FadmHistEntry
                ACCESS  not-accessible
                STATUS  mandatory
                DESCRIPTION
                        "Specifies the index for each row in the table below"
                INDEX { fadmHMode }
                ::= { fadmHistTable 1 }

        FadmHistEntry    ::=
                SEQUENCE {
                        fadmHMode        HistoryMode,
                        fadmHNumEvents   Counter
                }

        fadmHMode        OBJECT-TYPE
                SYNTAX  HistoryMode
                ACCESS  read-only
                STATUS  mandatory
                DESCRIPTION
                        "The mode of the data collection.  Valid values are:
                         daily or longterm."
                ::= { fadmHistEntry 1 }

        fadmHNumEvents   OBJECT-TYPE
                SYNTAX  Counter
                ACCESS  read-only
                STATUS  mandatory
                DESCRIPTION
                        "Total number of all traps (events) generated by all
                         FADM's."
                ::= { fadmHistEntry 2 }

        fadmHHistTable   OBJECT-TYPE
                SYNTAX  SEQUENCE OF FadmHHistEntry
                ACCESS  not-accessible
                STATUS  mandatory
                DESCRIPTION
                        "This table represents the information for performance
                         data collected for each fadm card"
                ::= { fadmHist 2 }

        fadmHHistEntry   OBJECT-TYPE
                SYNTAX  FadmHHistEntry
                ACCESS  not-accessible
                STATUS  mandatory
                DESCRIPTION
                        "Specifies the index for each row in the table below"
                INDEX { fadmHHistMode, fadmHHistLocation, fadmHHistShelf,
                        fadmHHistSlot }
                ::= { fadmHHistTable 1 }

        FadmHHistEntry   ::=
                SEQUENCE {
                        fadmHHistMode      HistoryMode,
                        fadmHHistLocation  CardLocation,
                        fadmHHistShelf     CardShelf,
                        fadmHHistSlot      INTEGER,
                        fadmHLastBootTime  DateAndTime,
                        fadmHAvailTime     Counter,
                        fadmHErrFreeSecs   Counter
                }

        fadmHHistMode    OBJECT-TYPE
                SYNTAX  HistoryMode
                ACCESS  read-only
                STATUS  mandatory
                DESCRIPTION
                        "The mode of the data collection.  Valid values are:
                         daily or longterm."
                ::= { fadmHHistEntry 1 }

        fadmHHistLocation  OBJECT-TYPE
                SYNTAX  CardLocation
                ACCESS  read-only
                STATUS  mandatory
                DESCRIPTION
                        "The location of the card.  Choices are local or
                         remote."
                ::= { fadmHHistEntry 2 }

        fadmHHistShelf   OBJECT-TYPE
                SYNTAX  CardShelf
                ACCESS  read-only
                STATUS  mandatory
                DESCRIPTION
                        "The shelf the card is in.  Valid values are: 1 to 10"
                ::= { fadmHHistEntry 3 }

        fadmHHistSlot    OBJECT-TYPE
                SYNTAX  CardSlot
                ACCESS  read-only
                STATUS  mandatory
                DESCRIPTION
                        "The slot within the shelf the card is in."
                ::= { fadmHHistEntry 4 }

        fadmHLastBootTime  OBJECT-TYPE
                SYNTAX  DateAndTime
                ACCESS  read-only
                STATUS  mandatory
                DESCRIPTION
                        "The date and time of the last boot for this card."
                ::= { fadmHHistEntry 6 }

        fadmHAvailTime   OBJECT-TYPE
                SYNTAX  Counter
                ACCESS  read-only
                STATUS  mandatory
                DESCRIPTION
                        "The number of seconds that this Mux has been up and
                         running."
                ::= { fadmHHistEntry 7 }

        fadmHErrFreeSecs OBJECT-TYPE
                SYNTAX  Counter
                ACCESS  read-only
                STATUS  mandatory
                DESCRIPTION
                        "The number of seconds that this mux has not
                         experienced any alarms."
                ::= { fadmHHistEntry 8 }

-- The elements in the oppmHist subgroup of the historical subgroup

	  oppmHistTable    OBJECT-TYPE
                SYNTAX  SEQUENCE OF OppmHistEntry
                ACCESS  not-accessible
                STATUS  mandatory
                DESCRIPTION
                        "This table represents the information for historical
                         data collected for the oppm card"
                ::= { oppmHist 1 }

        oppmHistEntry    OBJECT-TYPE
                SYNTAX  OppmHistEntry
                ACCESS  not-accessible
                STATUS  mandatory
                DESCRIPTION
                        "Specifies the index for each row in the table below"
                INDEX { oppmHMode }
                ::= { oppmHistTable 1 }

        OppmHistEntry    ::=
                SEQUENCE {
                        oppmHMode        HistoryMode,
                        oppmHNumEvents   Counter
                }

        oppmHMode        OBJECT-TYPE
                SYNTAX  HistoryMode
                ACCESS  read-only
                STATUS  mandatory
                DESCRIPTION
                        "The mode of the data collection.  Valid values are:
                         daily or longterm."
                ::= { oppmHistEntry 1 }

        oppmHNumEvents   OBJECT-TYPE
                SYNTAX  Counter
                ACCESS  read-only
                STATUS  mandatory
                DESCRIPTION
                        "Total number of all traps (events) generated by all
                         OPPM's."
                ::= { oppmHistEntry 2 }

        oppmHHistTable   OBJECT-TYPE
                SYNTAX  SEQUENCE OF OppmHHistEntry
                ACCESS  not-accessible
                STATUS  mandatory
                DESCRIPTION
                        "This table represents the information for performance
                         data collected for each fadm card"
                ::= { oppmHist 2 }

        oppmHHistEntry   OBJECT-TYPE
                SYNTAX  OppmHHistEntry
                ACCESS  not-accessible
                STATUS  mandatory
                DESCRIPTION
                        "Specifies the index for each row in the table below"
                INDEX { oppmHHistMode, oppmHHistLocation, oppmHHistShelf,
                        oppmHHistSlot }
                ::= { oppmHHistTable 1 }

        OppmHHistEntry   ::=
                SEQUENCE {
                        oppmHHistMode      HistoryMode,
                        oppmHHistLocation  CardLocation,
                        oppmHHistShelf     CardShelf,
                        oppmHHistSlot      INTEGER,
                        oppmHLastBootTime  DateAndTime,
                        oppmHAvailTime     Counter,
                        oppmHErrFreeSecs   Counter
                }

        oppmHHistMode    OBJECT-TYPE
                SYNTAX  HistoryMode
                ACCESS  read-only
                STATUS  mandatory
                DESCRIPTION
                        "The mode of the data collection.  Valid values are:
                         daily or longterm."
                ::= { oppmHHistEntry 1 }

        oppmHHistLocation  OBJECT-TYPE
                SYNTAX  CardLocation
                ACCESS  read-only
                STATUS  mandatory
                DESCRIPTION
                        "The location of the card.  Choices are local or
                         remote."
                ::= { oppmHHistEntry 2 }

        oppmHHistShelf   OBJECT-TYPE
                SYNTAX  CardShelf
                ACCESS  read-only
                STATUS  mandatory
                DESCRIPTION
                        "The shelf the card is in.  Valid values are: 1 to 10"
                ::= { oppmHHistEntry 3 }

        oppmHHistSlot    OBJECT-TYPE
                SYNTAX  CardSlot
                ACCESS  read-only
                STATUS  mandatory
                DESCRIPTION
                        "The slot within the shelf the card is in."
                ::= { oppmHHistEntry 4 }

        oppmHLastBootTime  OBJECT-TYPE
                SYNTAX  DateAndTime
                ACCESS  read-only
                STATUS  mandatory
                DESCRIPTION
                        "The date and time of the last boot for this card."
                ::= { oppmHHistEntry 6 }

        oppmHAvailTime   OBJECT-TYPE
                SYNTAX  Counter
                ACCESS  read-only
                STATUS  mandatory
                DESCRIPTION
                        "The number of seconds that this Mux has been up and
                         running."
                ::= { oppmHHistEntry 7 }

        oppmHErrFreeSecs OBJECT-TYPE
                SYNTAX  Counter
                ACCESS  read-only
                STATUS  mandatory
                DESCRIPTION
                        "The number of seconds that this mux has not
                         experienced any alarms."
                ::= { oppmHHistEntry 8 }


        -- The elements in the mcmHist subgroup of the historical subgroup

        mcmHistTable     OBJECT-TYPE
                SYNTAX  SEQUENCE OF McmHistEntry
                ACCESS  not-accessible
                STATUS  mandatory
                DESCRIPTION
                        "This table represents the information for historical
                         data collected for the channel card"
                ::= { mcmHist 1 }

        mcmHistEntry     OBJECT-TYPE
                SYNTAX  McmHistEntry
                ACCESS  not-accessible
                STATUS  mandatory
                DESCRIPTION
                        "Specifies the index for each row in the table below"
                INDEX { mcmHMode }
                ::= { mcmHistTable 1 }

        McmHistEntry     ::=
                SEQUENCE {
                        mcmHMode         HistoryMode,
                        mcmHNumEvents    Counter
                }

        mcmHMode         OBJECT-TYPE
                SYNTAX  HistoryMode
                ACCESS  read-only
                STATUS  mandatory
                DESCRIPTION
                        "The mode of the data collection.  Valid values are:
                         daily or longterm."
                ::= { mcmHistEntry 1 }

        mcmHNumEvents    OBJECT-TYPE
                SYNTAX  Counter
                ACCESS  read-only
                STATUS  mandatory
                DESCRIPTION
                        "Total number of events received for all mcm's"
                ::= { mcmHistEntry 2 }

        mcmHCntrTable    OBJECT-TYPE
                SYNTAX  SEQUENCE OF McmHCntrEntry
                ACCESS  not-accessible
                STATUS  mandatory
                DESCRIPTION
                        "This table represents the information for each
                         entry for the software counters."
                ::= { mcmHist 2 }

        mcmHCntrEntry    OBJECT-TYPE
                SYNTAX  McmHCntrEntry
                ACCESS  not-accessible
                STATUS  mandatory
                DESCRIPTION
                        "Specifies the index for each row in the table below"
                INDEX { mcmHCntrMode, mcmHCntrLocation, mcmHCntrShelf,
                        mcmHCntrSlot, mcmHCntrType }
                ::= { mcmHCntrTable 1 }

        McmHCntrEntry    ::=
                SEQUENCE {
                        mcmHCntrMode     HistoryMode,
                        mcmHCntrLocation CardLocation,
                        mcmHCntrShelf    CardShelf,
                        mcmHCntrSlot     INTEGER,
                        mcmHCntrType     INTEGER,
                        mcmHTotPktSent   Counter,
                        mcmHTotPktRcvd   Counter,
                        mcmHBadPktRcvd   Counter,
                        mcmHTotBadTrans  Counter,
                        mcmHBytesSent    Counter,
                        mcmHBytesRcvd    Counter,
                        mcmHMsgsDlvrd    Counter,
                        mcmHBufAllocFail Counter,
                        mcmHEcbAllocFail Counter
                }

        mcmHCntrMode     OBJECT-TYPE
                SYNTAX  HistoryMode
                ACCESS  read-only
                STATUS  mandatory
                DESCRIPTION
                        "The mode of the data collection.  Valid values are:
                         daily or longterm."
                ::= { mcmHCntrEntry 1 }

        mcmHCntrLocation OBJECT-TYPE
                SYNTAX  CardLocation
                ACCESS  read-only
                STATUS  mandatory
                DESCRIPTION
                        "The location of the mcm card.  The values are: Local
                         or Remote.  The system automatically determines the
                         right value for this entry based on the known
                         mcm cards."
                ::= { mcmHCntrEntry 2 }

        mcmHCntrShelf    OBJECT-TYPE
                SYNTAX  CardShelf
                ACCESS  read-only
                STATUS  mandatory
                DESCRIPTION
                        "The shelf the card is in.  Valid values are: 1 to 3.
                         The system automatically determines the right value
                         for this entry based on the known (available) mcm
                         cards."
                ::= { mcmHCntrEntry 3 }

        mcmHCntrSlot     OBJECT-TYPE
                SYNTAX  CardSlot
                ACCESS  read-only
                STATUS  mandatory
                DESCRIPTION
                        "The slot within the shelf the card is in. The
                         system automatically determines the right
                         value for this entry based on the known
                         (available) mcm cards."
                ::= { mcmHCntrEntry 4 }

        mcmHCntrType     OBJECT-TYPE
                SYNTAX  INTEGER { spi(1), iwm(2) }
                ACCESS  read-only
                STATUS  mandatory
                DESCRIPTION
                        "The type of the software counter data in this row.
                         The data is collected for the SPI data channels."
                ::= { mcmHCntrEntry 5 }

        mcmHTotPktSent   OBJECT-TYPE
                SYNTAX  Counter
                ACCESS  read-only
                STATUS  mandatory
                DESCRIPTION
                        "The number of data packets sent over the given data
                         channel."
                ::= { mcmHCntrEntry 6 }

        mcmHTotPktRcvd   OBJECT-TYPE
                SYNTAX  Counter
                ACCESS  read-only
                STATUS  mandatory
                DESCRIPTION
                        "The number of data packets received over the given
                         data channel."
                ::= { mcmHCntrEntry 7 }

        mcmHBadPktRcvd   OBJECT-TYPE
                SYNTAX  Counter
                ACCESS  read-only
                STATUS  mandatory
                DESCRIPTION
                        "The number of bad data packets received over the given
                         data channel."
                ::= { mcmHCntrEntry 8 }

        mcmHTotBadTrans  OBJECT-TYPE
                SYNTAX  Counter
                ACCESS  read-only
                STATUS  mandatory
                DESCRIPTION
                        "The number of bad data transmissions over the given
                         data channel."
                ::= { mcmHCntrEntry 9 }

        mcmHBytesSent    OBJECT-TYPE
                SYNTAX  Counter
                ACCESS  read-only
                STATUS  mandatory
                DESCRIPTION
                        "Total number of bytes sent over the given
                         data channel."
                ::= { mcmHCntrEntry 10 }

        mcmHBytesRcvd    OBJECT-TYPE
                SYNTAX  Counter
                ACCESS  read-only
                STATUS  mandatory
                DESCRIPTION
                        "Total number of data bytes received over the given
                         data channel."
                ::= { mcmHCntrEntry 11 }

        mcmHMsgsDlvrd    OBJECT-TYPE
                SYNTAX  Counter
                ACCESS  read-only
                STATUS  mandatory
                DESCRIPTION
                        "The number of complete messages delivered over the
                         given data channel."
                ::= { mcmHCntrEntry 12 }

        mcmHBufAllocFail OBJECT-TYPE
                SYNTAX  Counter
                ACCESS  read-only
                STATUS  mandatory
                DESCRIPTION
                        "Number of buffer allocation failures for the given
                         data channel."
                ::= { mcmHCntrEntry 13 }

        mcmHEcbAllocFail OBJECT-TYPE
                SYNTAX  Counter
                ACCESS  read-only
                STATUS  mandatory
                DESCRIPTION
                        "Number of Event Control Block allocation failures
                         for the given data channel."
                ::= { mcmHCntrEntry 14 }


------       port entries

        mcmPortHIntervalTable    OBJECT-TYPE
                SYNTAX  SEQUENCE OF McmPortHIntervalEntry
                ACCESS  not-accessible
                STATUS  mandatory
                DESCRIPTION
                        "This table represents the information for each
                         entry for the mcm port counters."
                ::= { mcmHist 3 }

        mcmPortHIntervalEntry    OBJECT-TYPE
                SYNTAX  McmPortHIntervalEntry
                ACCESS  not-accessible
                STATUS  mandatory
                DESCRIPTION
                        "Specifies the index for each row in the table below"
                INDEX { mcmPortHIntervalLocation, mcmPortHIntervalShelf,
                        mcmPortHIntervalSlot, mcmPortHIntervalPort,
				mcmPortHIntervalNumber }
                ::= { mcmPortHIntervalTable 1 }

        McmPortHIntervalEntry    ::=
                SEQUENCE {
                        mcmPortHIntervalLocation     CardLocation,
                        mcmPortHIntervalShelf		CardShelf,
                        mcmPortHIntervalSlot    	INTEGER,
                        mcmPortHIntervalPort     	INTEGER,
                        mcmPortHIntervalNumber     	INTEGER,
                        mcmPortHIntervalASs    	Counter,
                 --       mcmPortHIntervalFrameASs 	Counter,
                        mcmPortHIntervalFEs 		Counter,
                        mcmPortHIntervalCRCErrs 	Counter,
				mcmPortHIntervalSESs				Counter,
                        mcmPortHIntervalSEFSs				Counter,
                        mcmPortHIntervalUASs				Counter,
				mcmPortHIntervalLESs				Counter,
                        mcmPortHIntervalBESs				Counter,
                        mcmPortHIntervalDMs				Counter,
				mcmPortHIntervalLCVs				Counter
                }


        mcmPortHIntervalLocation OBJECT-TYPE
                SYNTAX  CardLocation
                ACCESS  read-only
                STATUS  mandatory
                DESCRIPTION
                        "The location of the mcm card.  The values are: Local
                         or Remote.  The system automatically determines the
                         right value for this entry based on the known
                         mcm cards."
                ::= { mcmPortHIntervalEntry 1 }

        mcmPortHIntervalShelf    OBJECT-TYPE
                SYNTAX  CardShelf
                ACCESS  read-only
                STATUS  mandatory
                DESCRIPTION
                        "The shelf the card is in.  Valid values are: 1 to 3.
                         The system automatically determines the right value
                         for this entry based on the known (available) mcm
                         cards."
                ::= { mcmPortHIntervalEntry 2 }

        mcmPortHIntervalSlot     OBJECT-TYPE
                SYNTAX  CardSlot
                ACCESS  read-only
                STATUS  mandatory
                DESCRIPTION
                        "The slot within the shelf the card is in.  The
                         system automatically determines the right value
                         for this entry based on the known (available)
                         mcm cards."
                ::= { mcmPortHIntervalEntry 3 }



        mcmPortHIntervalPort     OBJECT-TYPE
                SYNTAX  INTEGER
                ACCESS  read-only
                STATUS  mandatory
                DESCRIPTION
                        "The port within the shelf the card is in.  Valid
                         values are: 1 to 4.  The system automatically
                         determines the right value for this entry based
                         on the known (available) mcm cards."
                ::= { mcmPortHIntervalEntry 4 }


        mcmPortHIntervalNumber     OBJECT-TYPE
                SYNTAX  INTEGER
                ACCESS  read-only
                STATUS  mandatory
                DESCRIPTION
                        "The Interval number of the ds1 port.  Valid
                         values are: 1 to 96.  The system automatically
                         determines the right value for this entry based
                         on the known (available) interval number."
                ::= { mcmPortHIntervalEntry 5 }

        mcmPortHIntervalASs      OBJECT-TYPE
                SYNTAX  Counter 
                ACCESS  read-only
                STATUS  mandatory
                DESCRIPTION
                        "mcm port's ASs counter for specific interval."
                ::= { mcmPortHIntervalEntry 6 }

        --mcmPortHIntervals      OBJECT-TYPE
        --        SYNTAX  Counter
        --        ACCESS  read-only
        --        STATUS  mandatory
        --        DESCRIPTION
        --                "MCM port's FrameASs counter for specific interval."
        --        ::= { mcmPortHIntervalEntry 7 }

        mcmPortHIntervalFEs      OBJECT-TYPE
                SYNTAX  Counter
                ACCESS  read-only
                STATUS  mandatory
                DESCRIPTION
                        "MCM port's FEs counter for specific interval." 
                ::= { mcmPortHIntervalEntry 8 }

        mcmPortHIntervalCRCErrs    OBJECT-TYPE
                SYNTAX  Counter
                ACCESS  read-only
                STATUS  mandatory
                DESCRIPTION
                        "MCM port's CRC errs counter for specific interval."
                ::= { mcmPortHIntervalEntry 9 }

        mcmPortHIntervalSESs      OBJECT-TYPE
                SYNTAX  Counter 
                ACCESS  read-only
                STATUS  mandatory
                DESCRIPTION
                        "mcm port's SESs counter less than 15 mins."
                ::= { mcmPortHIntervalEntry 10 }

        mcmPortHIntervalSEFSs      OBJECT-TYPE
                SYNTAX  Counter
                ACCESS  read-only
                STATUS  mandatory
                DESCRIPTION
                        "MCM port's SEFSs counter less than 15 mins."
                ::= { mcmPortHIntervalEntry 11 }

        mcmPortHIntervalUASs      OBJECT-TYPE
                SYNTAX  Counter
                ACCESS  read-only
                STATUS  mandatory
                DESCRIPTION
                        "MCM port's UASs counter less than 15 mins." 
                ::= { mcmPortHIntervalEntry 12 }

        mcmPortHIntervalLESs    OBJECT-TYPE
                SYNTAX  Counter
                ACCESS  read-only
                STATUS  mandatory
                DESCRIPTION
                        "MCM port's LESs counter less than 15 mins."
                ::= { mcmPortHIntervalEntry 13 }

        mcmPortHIntervalBESs    OBJECT-TYPE
                SYNTAX  Counter
                ACCESS  read-only
                STATUS  mandatory
                DESCRIPTION
                        "MCM port's BESs counter less than 15 mins."
                ::= { mcmPortHIntervalEntry 14 }

        mcmPortHIntervalDMs    OBJECT-TYPE
                SYNTAX  Counter
                ACCESS  read-only
                STATUS  mandatory
                DESCRIPTION
                        "MCM port's DMSs counter less than 15 mins."
                ::= { mcmPortHIntervalEntry 15 }

        mcmPortHIntervalLCVs    OBJECT-TYPE
                SYNTAX  Counter
                ACCESS  read-only
                STATUS  mandatory
                DESCRIPTION
                        "MCM port's LCVs counter less than 15 mins."
                ::= { mcmPortHIntervalEntry 16 }




------  24 hr total port entries

        mcmPortHTotalTable    OBJECT-TYPE
                SYNTAX  SEQUENCE OF McmPortHTotalEntry
                ACCESS  not-accessible
                STATUS  mandatory
                DESCRIPTION
                        "This table represents the information for each
                         entry for the mcm port counters."
                ::= { mcmHist 4 }

        mcmPortHTotalEntry    OBJECT-TYPE
                SYNTAX  McmPortHTotalEntry
                ACCESS  not-accessible
                STATUS  mandatory
                DESCRIPTION
                        "Specifies the index for each row in the table below"
                INDEX { mcmPortHTotalLocation, mcmPortHTotalShelf,
                        mcmPortHTotalSlot, mcmPortHTotalPort }
                ::= { mcmPortHTotalTable 1 }

        McmPortHTotalEntry    ::=
                SEQUENCE {
                        mcmPortHTotalLocation     	CardLocation,
                        mcmPortHTotalShelf		CardShelf,
                        mcmPortHTotalSlot    		INTEGER,
                        mcmPortHTotalPort     		INTEGER,
                        mcmPortHTotalASs    		Counter,
             --           mcmPortHTotalFrameASs 		Counter,
                        mcmPortHTotalFEs 		Counter,
                        mcmPortHTotalCRCErrs 		Counter,
				mcmPortHTotalSESs				Counter,
                        mcmPortHTotalSEFSs				Counter,
                        mcmPortHTotalUASs				Counter,
				mcmPortHTotalLESs				Counter,
                        mcmPortHTotalBESs				Counter,
                        mcmPortHTotalDMs				Counter,
				mcmPortHTotalLCVs				Counter
                }


        mcmPortHTotalLocation OBJECT-TYPE
                SYNTAX  CardLocation
                ACCESS  read-only
                STATUS  mandatory
                DESCRIPTION
                        "The location of the mcm card.  The values are: Local
                         or Remote.  The system automatically determines the
                         right value for this entry based on the known
                         mcm cards."
                ::= { mcmPortHTotalEntry 1 }

        mcmPortHTotalShelf    OBJECT-TYPE
                SYNTAX  CardShelf
                ACCESS  read-only
                STATUS  mandatory
                DESCRIPTION
                        "The shelf the card is in.  Valid values are: 1 to 3.
                         The system automatically determines the right value
                         for this entry based on the known (available) mcm
                         cards."
                ::= { mcmPortHTotalEntry 2 }

        mcmPortHTotalSlot     OBJECT-TYPE
                SYNTAX  CardSlot
                ACCESS  read-only
                STATUS  mandatory
                DESCRIPTION
                        "The slot within the shelf the card is in.  The
                         system automatically determines the right
                         value for this entry based on the known
                         (available) mcm cards."
                ::= { mcmPortHTotalEntry 3 }



        mcmPortHTotalPort     OBJECT-TYPE
                SYNTAX  INTEGER
                ACCESS  read-only
                STATUS  mandatory
                DESCRIPTION
                        "The port within the shelf the card is in.  Valid
                         values are: 1 to 4.  The system automatically
                         determines the right value for this entry based
                         on the known (available) mcm cards."
                ::= { mcmPortHTotalEntry 4 }


        mcmPortHTotalASs      OBJECT-TYPE
                SYNTAX  Counter 
                ACCESS  read-only
                STATUS  mandatory
                DESCRIPTION
                        "mcm port's ASs counter for the last 24 hrs."
                ::= { mcmPortHTotalEntry 5 }

        --mcmPortHTotals      OBJECT-TYPE
        --        SYNTAX  Counter
        --        ACCESS  read-only
        --        STATUS  mandatory
        --        DESCRIPTION
        --                "MCM port's FrameASs counter for the last 24 hrs."
        --        ::= { mcmPortHTotalEntry 6 }

        mcmPortHTotalFEs      OBJECT-TYPE
                SYNTAX  Counter
                ACCESS  read-only
                STATUS  mandatory
                DESCRIPTION
                        "MCM port's FEs counter for the last 24 hrs." 
                ::= { mcmPortHTotalEntry 7 }

        mcmPortHTotalCRCErrs    OBJECT-TYPE
                SYNTAX  Counter
                ACCESS  read-only
                STATUS  mandatory
                DESCRIPTION
                        "MCM port's CRC errs counter for the last 24 hrs."
                ::= { mcmPortHTotalEntry 8 }

        mcmPortHTotalSESs      OBJECT-TYPE
                SYNTAX  Counter 
                ACCESS  read-only
                STATUS  mandatory
                DESCRIPTION
                        "mcm port's SESs counter less than 15 mins."
                ::= { mcmPortHTotalEntry 9 }

        mcmPortHTotalSEFSs      OBJECT-TYPE
                SYNTAX  Counter
                ACCESS  read-only
                STATUS  mandatory
                DESCRIPTION
                        "MCM port's SEFSs counter less than 15 mins."
                ::= { mcmPortHTotalEntry 10 }

        mcmPortHTotalUASs      OBJECT-TYPE
                SYNTAX  Counter
                ACCESS  read-only
                STATUS  mandatory
                DESCRIPTION
                        "MCM port's UASs counter less than 15 mins." 
                ::= { mcmPortHTotalEntry 11 }

        mcmPortHTotalLESs    OBJECT-TYPE
                SYNTAX  Counter
                ACCESS  read-only
                STATUS  mandatory
                DESCRIPTION
                        "MCM port's LESs counter less than 15 mins."
                ::= { mcmPortHTotalEntry 12 }

        mcmPortHTotalBESs    OBJECT-TYPE
                SYNTAX  Counter
                ACCESS  read-only
                STATUS  mandatory
                DESCRIPTION
                        "MCM port's BESs counter less than 15 mins."
                ::= { mcmPortHTotalEntry 13 }

        mcmPortHTotalDMs    OBJECT-TYPE
                SYNTAX  Counter
                ACCESS  read-only
                STATUS  mandatory
                DESCRIPTION
                        "MCM port's DMSs counter less than 15 mins."
                ::= { mcmPortHTotalEntry 14 }

        mcmPortHTotalLCVs    OBJECT-TYPE
                SYNTAX  Counter
                ACCESS  read-only
                STATUS  mandatory
                DESCRIPTION
                        "MCM port's LCVs counter less than 15 mins."
                ::= { mcmPortHTotalEntry 15 }

        -- The elements in the fnHist subgroup of the historical subgroup

        fnHistTable     OBJECT-TYPE
                SYNTAX  SEQUENCE OF FnHistEntry
                ACCESS  not-accessible
                STATUS  mandatory
                DESCRIPTION
                        "This table represents the information for historical
                         data collected for the fan modules"
                ::= { fnHist 1 }

        fnHistEntry     OBJECT-TYPE
                SYNTAX  FnHistEntry
                ACCESS  not-accessible
                STATUS  mandatory
                DESCRIPTION
                        "Specifies the index for each row in the table below"
                INDEX { fnHMode }
                ::= { fnHistTable 1 }

        FnHistEntry     ::=
                SEQUENCE {
                        fnHMode         HistoryMode,
                        fnHNumEvents    Counter
                }

        fnHMode         OBJECT-TYPE
                SYNTAX  HistoryMode
                ACCESS  not-accessible 
                STATUS  mandatory
                DESCRIPTION
                        "The mode of the data collection.  Valid values are:
                         daily or longterm."
                ::= { fnHistEntry 1 }

        fnHNumEvents    OBJECT-TYPE
                SYNTAX  Counter
                ACCESS  not-accessible 
                STATUS  mandatory
                DESCRIPTION
                        "Total number of all traps (events) generated by all
                         fan modules."
                ::= { fnHistEntry 2 }


       -- The elements in the csimHist subgroup of the historical subgroup

        csimHistTable     OBJECT-TYPE
                SYNTAX  SEQUENCE OF CsimHistEntry
                ACCESS  not-accessible
                STATUS  mandatory
                DESCRIPTION
                        "This table represents the information for historical
                         data collected for the ColorSIM "
                ::= { csimHist 1 }

        csimHistEntry     OBJECT-TYPE
                SYNTAX  CsimHistEntry
                ACCESS  not-accessible
                STATUS  mandatory
                DESCRIPTION
                        "Specifies the index for each row in the table below"
                INDEX { csimHMode }
                ::= { csimHistTable 1 }

        CsimHistEntry     ::=
                SEQUENCE {
                        csimHMode         HistoryMode,
                        csimHNumEvents    Counter
                }

        csimHMode         OBJECT-TYPE
                SYNTAX  HistoryMode
                ACCESS  not-accessible
                STATUS  mandatory
                DESCRIPTION
                        "The mode of the data collection.  Valid values are:
                         daily or longterm. The reason this has been made obsolete
			 is that all colorsim related events would eventually be part
			 of ocm events"
                ::= { csimHistEntry 1 }

        csimHNumEvents    OBJECT-TYPE
                SYNTAX  Counter
                ACCESS  not-accessible
                STATUS  mandatory
                DESCRIPTION
                        "This variable keeps track of the number of events
			 related to ColorSIM. The reason this has been made obsolete
			 is that all colorsim related events would eventually be part
			 of ocm events"
                ::= { csimHistEntry 2 }
     
	  csimHistIntervalTable       OBJECT-TYPE
                SYNTAX  SEQUENCE OF CsimHistIntervalEntry
                ACCESS  not-accessible
                STATUS  mandatory
                DESCRIPTION
                        "This table represents the information for each
                         colorsim card."
                ::= { csimHist 2 }

        csimHistIntervalEntry       OBJECT-TYPE
                SYNTAX  CsimHistIntervalEntry
                ACCESS  not-accessible
                STATUS  mandatory
                DESCRIPTION
                        "Specifies the index for each row in the table below"
                INDEX { csimIntervalLocation, csimIntervalShelf,
			csimIntervalSlot, csimIntervalNumber }
                ::= { csimHistIntervalTable 1 }

        CsimHistIntervalEntry   ::=
                SEQUENCE {
                        csimIntervalLocation 	CardLocation,
                        csimIntervalShelf       CardShelf,
                        csimIntervalSlot        INTEGER,
			csimIntervalNumber	INTEGER,
			csimIntervalEFIs	INTEGER,
			csimIntervalEIs		INTEGER,
			csimIntervalSEIs	INTEGER,
			csimIntervalBERs	DisplayString,
			csimIntervalUAIs	INTEGER,
			csimIntervalValidData	Boolean,
			csimIntervalDateTime  INTEGER
			}
	
        csimIntervalLocation  OBJECT-TYPE
                SYNTAX  CardLocation
                ACCESS  read-only
                STATUS  mandatory
                DESCRIPTION
                        " Location of the ColorSIM module"
                ::= { csimHistIntervalEntry 1 }

        csimIntervalShelf     OBJECT-TYPE
                SYNTAX  CardShelf
                ACCESS  read-only
                STATUS  mandatory
                DESCRIPTION
                        "The shelf of the ColorSIM module"
                ::= { csimHistIntervalEntry 2 }

        csimIntervalSlot      OBJECT-TYPE
                SYNTAX  CardSlot
                ACCESS  read-only 
                STATUS  mandatory
                DESCRIPTION
                        "The Slot of the ColorSIM module"
                ::= { csimHistIntervalEntry 3 }

        csimIntervalNumber OBJECT-TYPE
                SYNTAX  INTEGER (1..96)
                ACCESS  read-only
                STATUS  mandatory
                DESCRIPTION
                        "This variable indicates the interval for which
			 the set of statistics data is available."
                ::= { csimHistIntervalEntry 4 }

        csimIntervalEFIs OBJECT-TYPE
                SYNTAX  INTEGER
                ACCESS  read-only
                STATUS  mandatory
                DESCRIPTION
			"The counter associated with the number of Error Free
			 Interval Counts in this interval."
                ::= { csimHistIntervalEntry 5 }

        csimIntervalEIs OBJECT-TYPE
                SYNTAX  INTEGER
                ACCESS  read-only
                STATUS  mandatory
                DESCRIPTION
			"The counter associated with the number of Errored
			 Interval Counts in this interval."
                ::= { csimHistIntervalEntry 6 }

        csimIntervalSEIs OBJECT-TYPE
                SYNTAX  INTEGER
                ACCESS  read-only
                STATUS  mandatory
                DESCRIPTION
			"The counter associated with the number of Severely
			 Errored Interval Counts in this interval."
                ::= { csimHistIntervalEntry 7 }

        csimIntervalBERs OBJECT-TYPE
                SYNTAX  DisplayString
                ACCESS  read-only
                STATUS  mandatory
                DESCRIPTION
			"The counter associated with the number of Bit
			 Error Rate Counts in this interval.  The unit
			 is in the form of x.ye-z."
                ::= { csimHistIntervalEntry 8 }

        csimIntervalUAIs OBJECT-TYPE
                SYNTAX  INTEGER
                ACCESS  read-only
                STATUS  mandatory
                DESCRIPTION
			"The counter associated with the number of Unavailable
			 Interval Counts in this interval."
                ::= { csimHistIntervalEntry 9 }

        csimIntervalValidData OBJECT-TYPE
                SYNTAX  Boolean
                ACCESS  not-accessible
                STATUS  mandatory
                DESCRIPTION
			"This variable indicates if the data for this interval
			 is valid. Not supported"
                ::= { csimHistIntervalEntry 10 }

        csimIntervalDateTime OBJECT-TYPE
                SYNTAX  INTEGER
                ACCESS  read-only
                STATUS  mandatory
                DESCRIPTION
			"Time in seconds elasped since 01/01/1970 00:00:00 GMT for this interval. 
			 Assuming local time is same as GMT" 
                ::= { csimHistIntervalEntry 11 }




-- The elements in the rpsmHist subgroup of the historical subgroup

	  rpsmHistTable    OBJECT-TYPE
                SYNTAX  SEQUENCE OF RpsmHistEntry
                ACCESS  not-accessible
                STATUS  mandatory
                DESCRIPTION
                        "This table represents the information for historical
                         data collected for the rpsm card"
                ::= { rpsmHist 1 }

        rpsmHistEntry    OBJECT-TYPE
                SYNTAX  RpsmHistEntry
                ACCESS  not-accessible
                STATUS  mandatory
                DESCRIPTION
                        "Specifies the index for each row in the table below"
                INDEX { oppmHMode }
                ::= { rpsmHistTable 1 }

        RpsmHistEntry    ::=
                SEQUENCE {
                        rpsmHMode        HistoryMode,
                        rpsmHNumEvents   Counter
                }

        rpsmHMode        OBJECT-TYPE
                SYNTAX  HistoryMode
                ACCESS  read-only
                STATUS  mandatory
                DESCRIPTION
                        "The mode of the data collection.  Valid values are:
                         daily or longterm."
                ::= { rpsmHistEntry 1 }

        rpsmHNumEvents   OBJECT-TYPE
                SYNTAX  Counter
                ACCESS  read-only
                STATUS  mandatory
                DESCRIPTION
                        "Total number of all traps (events) generated by all
                         RPSM's."
                ::= { rpsmHistEntry 2 }

        rpsmHHistTable   OBJECT-TYPE
                SYNTAX  SEQUENCE OF RpsmHHistEntry
                ACCESS  not-accessible
                STATUS  mandatory
                DESCRIPTION
                        "This table represents the information for performance
                         data collected for each rpsm card"
                ::= { rpsmHist 2 }

        rpsmHHistEntry   OBJECT-TYPE
                SYNTAX  RpsmHHistEntry
                ACCESS  not-accessible
                STATUS  mandatory
                DESCRIPTION
                        "Specifies the index for each row in the table below"
                INDEX { rpsmHHistMode, rpsmHHistLocation, rpsmHHistShelf,
                        rpsmHHistSlot }
                ::= { rpsmHHistTable 1 }

        RpsmHHistEntry   ::=
                SEQUENCE {
                        rpsmHHistMode      HistoryMode,
                        rpsmHHistLocation  CardLocation,
                        rpsmHHistShelf     CardShelf,
                        rpsmHHistSlot      INTEGER,
                        rpsmHLastBootTime  DateAndTime,
                        rpsmHAvailTime     Counter,
                        rpsmHErrFreeSecs   Counter
                }

        rpsmHHistMode    OBJECT-TYPE
                SYNTAX  HistoryMode
                ACCESS  read-only
                STATUS  mandatory
                DESCRIPTION
                        "The mode of the data collection.  Valid values are:
                         daily or longterm."
                ::= { rpsmHHistEntry 1 }

        rpsmHHistLocation  OBJECT-TYPE
                SYNTAX  CardLocation
                ACCESS  read-only
                STATUS  mandatory
                DESCRIPTION
                        "The location of the card.  Choices are local or
                         remote."
                ::= { rpsmHHistEntry 2 }

        rpsmHHistShelf   OBJECT-TYPE
                SYNTAX  CardShelf
                ACCESS  read-only
                STATUS  mandatory
                DESCRIPTION
                        "The shelf the card is in.  Valid values are: 1 to 10"
                ::= { rpsmHHistEntry 3 }

        rpsmHHistSlot    OBJECT-TYPE
                SYNTAX  CardSlot
                ACCESS  read-only
                STATUS  mandatory
                DESCRIPTION
                        "The slot within the shelf the card is in."
                ::= { rpsmHHistEntry 4 }

        rpsmHLastBootTime  OBJECT-TYPE
                SYNTAX  DateAndTime
                ACCESS  read-only
                STATUS  mandatory
                DESCRIPTION
                        "The date and time of the last boot for this card."
                ::= { rpsmHHistEntry 6 }

        rpsmHAvailTime   OBJECT-TYPE
                SYNTAX  Counter
                ACCESS  read-only
                STATUS  mandatory
                DESCRIPTION
                        "The number of seconds that this rpsm has been up and
                         running."
                ::= { rpsmHHistEntry 7 }

        rpsmHErrFreeSecs OBJECT-TYPE
                SYNTAX  Counter
                ACCESS  read-only
                STATUS  mandatory
                DESCRIPTION
                        "The number of seconds that this rpsm has not
                         experienced any alarms."
                ::= { rpsmHHistEntry 8 }

-- The elements in the rsdmHist subgroup of the historical subgroup

	  rsdmHistTable    OBJECT-TYPE
                SYNTAX  SEQUENCE OF RsdmHistEntry
                ACCESS  not-accessible
                STATUS  mandatory
                DESCRIPTION
                        "This table represents the information for historical
                         data collected for the rsdm card"
                ::= { rsdmHist 1 }

        rsdmHistEntry    OBJECT-TYPE
                SYNTAX  RsdmHistEntry
                ACCESS  not-accessible
                STATUS  mandatory
                DESCRIPTION
                        "Specifies the index for each row in the table below"
                INDEX { rsdmHMode }
                ::= { rsdmHistTable 1 }

        RsdmHistEntry    ::=
                SEQUENCE {
                        rsdmHMode        HistoryMode,
                        rsdmHNumEvents   Counter
                }

        rsdmHMode        OBJECT-TYPE
                SYNTAX  HistoryMode
                ACCESS  read-only
                STATUS  mandatory
                DESCRIPTION
                        "The mode of the data collection.  Valid values are:
                         daily or longterm."
                ::= { rsdmHistEntry 1 }

        rsdmHNumEvents   OBJECT-TYPE
                SYNTAX  Counter
                ACCESS  read-only
                STATUS  mandatory
                DESCRIPTION
                        "Total number of all traps (events) generated by all
                         RSDM's."
                ::= { rsdmHistEntry 2 }

        rsdmHHistTable   OBJECT-TYPE
                SYNTAX  SEQUENCE OF RsdmHHistEntry
                ACCESS  not-accessible
                STATUS  mandatory
                DESCRIPTION
                        "This table represents the information for performance
                         data collected for each rsdm card."
                ::= { rsdmHist 2 }

        rsdmHHistEntry   OBJECT-TYPE
                SYNTAX  RsdmHHistEntry
                ACCESS  not-accessible
                STATUS  mandatory
                DESCRIPTION
                        "Specifies the index for each row in the table below"
                INDEX { rsdmHHistMode, rsdmHHistLocation, rsdmHHistShelf,
                        rsdmHHistSlot }
                ::= {rsdmHHistTable 1 }

        RsdmHHistEntry   ::=
                SEQUENCE {
                        rsdmHHistMode      HistoryMode,
                        rsdmHHistLocation  CardLocation,
                        rsdmHHistShelf     CardShelf,
                        rsdmHHistSlot      INTEGER,
                        rsdmHLastBootTime  DateAndTime,
                        rsdmHAvailTime     Counter,
                        rsdmHErrFreeSecs   Counter
                }

        rsdmHHistMode    OBJECT-TYPE
                SYNTAX  HistoryMode
                ACCESS  read-only
                STATUS  mandatory
                DESCRIPTION
                        "The mode of the data collection.  Valid values are:
                         daily or longterm."
                ::= { rsdmHHistEntry 1 }

        rsdmHHistLocation  OBJECT-TYPE
                SYNTAX  CardLocation
                ACCESS  read-only
                STATUS  mandatory
                DESCRIPTION
                        "The location of the card.  Choices are local or
                         remote."
                ::= { rsdmHHistEntry 2 }

        rsdmHHistShelf   OBJECT-TYPE
                SYNTAX  CardShelf
                ACCESS  read-only
                STATUS  mandatory
                DESCRIPTION
                        "The shelf the card is in.  Valid values are: 1 to 10"
                ::= { rsdmHHistEntry 3 }

        rsdmHHistSlot    OBJECT-TYPE
                SYNTAX  CardSlot
                ACCESS  read-only
                STATUS  mandatory
                DESCRIPTION
                        "The slot within the shelf the card is in."
                ::= { rsdmHHistEntry 4 }

        rsdmHLastBootTime  OBJECT-TYPE
                SYNTAX  DateAndTime
                ACCESS  read-only
                STATUS  mandatory
                DESCRIPTION
                        "The date and time of the last boot for this card."
                ::= { rsdmHHistEntry 6 }

        rsdmHAvailTime   OBJECT-TYPE
                SYNTAX  Counter
                ACCESS  read-only
                STATUS  mandatory
                DESCRIPTION
                        "The number of seconds that this rsdm has been up and
                         running."
                ::= { rsdmHHistEntry 7 }

        rsdmHErrFreeSecs OBJECT-TYPE
                SYNTAX  Counter
                ACCESS  read-only
                STATUS  mandatory
                DESCRIPTION
                        "The number of seconds that this rsdm has not
                         experienced any alarms."
                ::= { rsdmHHistEntry 8 }

        -- The elements in the rtdmHist subgroup of the historical subgroup

        rtdmHistTable    OBJECT-TYPE
                SYNTAX  SEQUENCE OF RtdmHistEntry
                ACCESS  not-accessible
                STATUS  mandatory
                DESCRIPTION
                        "This table represents the information for historical
                         data collected for the rtdm card"
                ::= { rtdmHist 1 }

        rtdmHistEntry    OBJECT-TYPE
                SYNTAX  RtdmHistEntry
                ACCESS  not-accessible
                STATUS  mandatory
                DESCRIPTION
                        "Specifies the index for each row in the table below"
                INDEX { rtdmHMode }
                ::= { rtdmHistTable 1 }

        RtdmHistEntry    ::=
                SEQUENCE {
                        rtdmHMode        HistoryMode,
                        rtdmHNumEvents   Counter
                }

        rtdmHMode        OBJECT-TYPE
                SYNTAX  HistoryMode
                ACCESS  read-only
                STATUS  mandatory
                DESCRIPTION
                        "The mode of the data collection.  Valid values are:
                         daily or longterm."
                ::= { rtdmHistEntry 1 }

        rtdmHNumEvents   OBJECT-TYPE
                SYNTAX  Counter
                ACCESS  read-only
                STATUS  mandatory
                DESCRIPTION
                        "Total number of all traps (events) generated by all
                         rtdm's."
                ::= { rtdmHistEntry 2 }

        rtdmHHistTable   OBJECT-TYPE
                SYNTAX  SEQUENCE OF RtdmHHistEntry
                ACCESS  not-accessible
                STATUS  mandatory
                DESCRIPTION
                        "This table represents the information for performance
                         data collected for each rtdm card."
                ::= { rtdmHist 2 }

        rtdmHHistEntry   OBJECT-TYPE
                SYNTAX  RtdmHHistEntry
                ACCESS  not-accessible
                STATUS  mandatory
                DESCRIPTION
                        "Specifies the index for each row in the table below"
                INDEX { rtdmHHistMode, rtdmHHistLocation, rtdmHHistShelf,
                        rtdmHHistSlot }
                ::= { rtdmHHistTable 1 }

        RtdmHHistEntry   ::=
                SEQUENCE {
                        rtdmHHistMode      HistoryMode,
                        rtdmHHistLocation  CardLocation,
                        rtdmHHistShelf     CardShelf,
                        rtdmHHistSlot      INTEGER,
                        rtdmHLastBootTime  DateAndTime,
                        rtdmHAvailTime     Counter,
                        rtdmHErrFreeSecs   Counter
                }

        rtdmHHistMode    OBJECT-TYPE
                SYNTAX  HistoryMode
                ACCESS  read-only
                STATUS  mandatory
                DESCRIPTION
                        "The mode of the data collection.  Valid values are:
                         daily or longterm."
                ::= { rtdmHHistEntry 1 }

        rtdmHHistLocation  OBJECT-TYPE
                SYNTAX  CardLocation
                ACCESS  read-only
                STATUS  mandatory
                DESCRIPTION
                        "The location of the card.  Choices are local or
                         remote."
                ::= { rtdmHHistEntry 2 }

        rtdmHHistShelf   OBJECT-TYPE
                SYNTAX  CardShelf
                ACCESS  read-only
                STATUS  mandatory
                DESCRIPTION
                        "The shelf the card is in.  Valid values are: 1 to 10"
                ::= { rtdmHHistEntry 3 }

        rtdmHHistSlot    OBJECT-TYPE
                SYNTAX  CardSlot
                ACCESS  read-only
                STATUS  mandatory
                DESCRIPTION
                        "The slot within the shelf the card is in."
                ::= { rtdmHHistEntry 4 }

        rtdmHLastBootTime  OBJECT-TYPE
                SYNTAX  DateAndTime
                ACCESS  read-only
                STATUS  mandatory
                DESCRIPTION
                        "The date and time of the last boot for this card."
                ::= { rtdmHHistEntry 5 }

       rtdmHAvailTime   OBJECT-TYPE
                SYNTAX  Counter
                ACCESS  read-only
                STATUS  mandatory
                DESCRIPTION
                        "The number of seconds that this rtdm has been up and
                         running."
                ::= { rtdmHHistEntry 6 }

       rtdmHErrFreeSecs OBJECT-TYPE
                SYNTAX  Counter
                ACCESS  read-only
                STATUS  mandatory
                DESCRIPTION
                        "The number of seconds that this rtdm has not
                         experienced any alarms."
                ::= { rtdmHHistEntry 7 }


        -- The elements in the osamHist subgroup of the historical subgroup

        osamHistTable    OBJECT-TYPE
                SYNTAX  SEQUENCE OF OsamHistEntry
                ACCESS  not-accessible
                STATUS  mandatory
                DESCRIPTION
                        "This table represents the information for historical
                         data collected for the osam module."
                ::= { osamHist 1 }

        osamHistEntry    OBJECT-TYPE
                SYNTAX  OsamHistEntry
                ACCESS  not-accessible
                STATUS  mandatory
                DESCRIPTION
                        "Specifies the index for each row in the table below"
                INDEX { osamHMode }
                ::= { osamHistTable 1 }

        OsamHistEntry    ::=
                SEQUENCE {
                        osamHMode        HistoryMode,
                        osamHNumEvents   Counter
                }

        osamHMode        OBJECT-TYPE
                SYNTAX  HistoryMode
                ACCESS  read-only
                STATUS  mandatory
                DESCRIPTION
                        "The mode of data collection."
                ::= { osamHistEntry 1 }

        osamHNumEvents   OBJECT-TYPE
                SYNTAX  Counter
                ACCESS  read-only
                STATUS  mandatory
                DESCRIPTION
                        "Total number of events received for all osam's."
                ::= { osamHistEntry 2 }

        osamHHistTable   OBJECT-TYPE
                SYNTAX  SEQUENCE OF OsamHHistEntry
                ACCESS  not-accessible
                STATUS  mandatory
                DESCRIPTION
                        "This table represents the information for 
                         historical performance data collected for each 
                         osam module."
                ::= { osamHist 2 }

        osamHHistEntry   OBJECT-TYPE
                SYNTAX  OsamHHistEntry
                ACCESS  not-accessible
                STATUS  mandatory
                DESCRIPTION
                        "Specifies the index for each row in the table below"
                INDEX { osamHHistMode, osamHHistLocation, osamHHistShelf,
                        osamHHistSlot }
                ::= { osamHHistTable 1 }

        OsamHHistEntry   ::=
                SEQUENCE {
                        osamHHistMode                HistoryMode,
                        osamHHistLocation            CardLocation,
                        osamHHistShelf               CardShelf,
                        osamHHistSlot                INTEGER,
                        osamHHistLastBootTime        DateAndTime,
                        osamHHistAvailTime           Counter,
                        osamHHistErrFreeSecs         Counter
                }

        osamHHistMode    OBJECT-TYPE
                SYNTAX  HistoryMode
                ACCESS  read-only
                STATUS  mandatory
                DESCRIPTION
                        "The mode of the data collection."
                ::= { osamHHistEntry 1 }

        osamHHistLocation  OBJECT-TYPE
                SYNTAX  CardLocation
                ACCESS  read-only
                STATUS  mandatory
                DESCRIPTION
                        "Location of the module."
                ::= { osamHHistEntry 2 }

        osamHHistShelf   OBJECT-TYPE
                SYNTAX  CardShelf
                ACCESS  read-only
                STATUS  mandatory
                DESCRIPTION
                        "The shelf number in which the module is plugged in."
                ::= { osamHHistEntry 3 }

        osamHHistSlot    OBJECT-TYPE
                SYNTAX  INTEGER (1..16)
                ACCESS  read-only
                STATUS  mandatory
                DESCRIPTION
                        "The slot number  in which the module is plugged in."
                ::= { osamHHistEntry 4 }

        osamHHistLastBootTime  OBJECT-TYPE
                SYNTAX  DateAndTime
                ACCESS  read-only
                STATUS  mandatory
                DESCRIPTION
                        "The date and time of the last boot for this module."
                ::= { osamHHistEntry 5 }

        osamHHistAvailTime   OBJECT-TYPE
                SYNTAX  Counter
                ACCESS  read-only
                STATUS  mandatory
                DESCRIPTION
                        "The number of seconds since the start of this 
                         historical mode that this module has been up and
                         running."
                ::= { osamHHistEntry 6 }

        osamHHistErrFreeSecs OBJECT-TYPE
                SYNTAX  Counter
                ACCESS  read-only
                STATUS  mandatory
                DESCRIPTION
                        "The number of seconds since the start of this 
                         historical mode that this module has not experienced
                         any alarms."
                ::= { osamHHistEntry 7 }

-- The elements in the rsmHist subgroup of the historical subgroup

	  rsmHistTable    OBJECT-TYPE
                SYNTAX  SEQUENCE OF RsmHistEntry
                ACCESS  not-accessible
                STATUS  mandatory
                DESCRIPTION
                        "This table represents the information for historical
                         data collected for the rsm card"
                ::= { rsmHist 1 }

        rsmHistEntry    OBJECT-TYPE
                SYNTAX  RsmHistEntry
                ACCESS  not-accessible
                STATUS  mandatory
                DESCRIPTION
                        "Specifies the index for each row in the table below"
                INDEX { rsmHMode }
                ::= { rsmHistTable 1 }

        RsmHistEntry    ::=
                SEQUENCE {
                        rsmHMode        HistoryMode,
                        rsmHNumEvents   Counter
                }

        rsmHMode        OBJECT-TYPE
                SYNTAX  HistoryMode
                ACCESS  read-only
                STATUS  mandatory
                DESCRIPTION
                        "The mode of the data collection.  Valid values are:
                         daily or longterm."
                ::= { rsmHistEntry 1 }

        rsmHNumEvents   OBJECT-TYPE
                SYNTAX  Counter
                ACCESS  read-only
                STATUS  mandatory
                DESCRIPTION
                        "Total number of all traps (events) generated by all
                         RSM's."
                ::= { rsmHistEntry 2 }

        rsmHHistTable   OBJECT-TYPE
                SYNTAX  SEQUENCE OF RsmHHistEntry
                ACCESS  not-accessible
                STATUS  mandatory
                DESCRIPTION
                        "This table represents the information for performance
                         data collected for each rsm card."
                ::= { rsmHist 2 }

        rsmHHistEntry   OBJECT-TYPE
                SYNTAX  RsmHHistEntry
                ACCESS  not-accessible
                STATUS  mandatory
                DESCRIPTION
                        "Specifies the index for each row in the table below"
                INDEX { rsmHHistMode, rsmHHistLocation, rsmHHistShelf,
                        rsmHHistSlot }
                ::= {rsmHHistTable 1 }

        RsmHHistEntry   ::=
                SEQUENCE {
                        rsmHHistMode      HistoryMode,
                        rsmHHistLocation  CardLocation,
                        rsmHHistShelf     CardShelf,
                        rsmHHistSlot      CardSlot,
                        rsmHLastBootTime  DateAndTime,
                        rsmHAvailTime     Counter,
                        rsmHErrFreeSecs   Counter
                }

        rsmHHistMode    OBJECT-TYPE
                SYNTAX  HistoryMode
                ACCESS  read-only
                STATUS  mandatory
                DESCRIPTION
                        "The mode of the data collection.  Valid values are:
                         daily or longterm."
                ::= { rsmHHistEntry 1 }

        rsmHHistLocation  OBJECT-TYPE
                SYNTAX  CardLocation
                ACCESS  read-only
                STATUS  mandatory
                DESCRIPTION
                        "The location of the card."
                ::= { rsmHHistEntry 2 }

        rsmHHistShelf   OBJECT-TYPE
                SYNTAX  CardShelf
                ACCESS  read-only
                STATUS  mandatory
                DESCRIPTION
                        "The shelf the card is in."
                ::= { rsmHHistEntry 3 }

        rsmHHistSlot    OBJECT-TYPE
                SYNTAX  CardSlot
                ACCESS  read-only
                STATUS  mandatory
                DESCRIPTION
                        "The slot within the shelf the card is in."
                ::= { rsmHHistEntry 4 }

        rsmHLastBootTime  OBJECT-TYPE
                SYNTAX  DateAndTime
                ACCESS  read-only
                STATUS  mandatory
                DESCRIPTION
                        "The date and time of the last boot for this card."
                ::= { rsmHHistEntry 6 }

        rsmHAvailTime   OBJECT-TYPE
                SYNTAX  Counter
                ACCESS  read-only
                STATUS  mandatory
                DESCRIPTION
                        "The number of seconds that this rsm has been up and
                         running."
                ::= { rsmHHistEntry 7 }

        rsmHErrFreeSecs OBJECT-TYPE
                SYNTAX  Counter
                ACCESS  read-only
                STATUS  mandatory
                DESCRIPTION
                        "The number of seconds that this rsm has not
                         experienced any alarms."
                ::= { rsmHHistEntry 8 }


-- The elements in the upsmHist subgroup of the historical subgroup

		upsmHistTable	OBJECT-TYPE
                SYNTAX  SEQUENCE OF UpsmHistEntry
                ACCESS  not-accessible
                STATUS  mandatory
                DESCRIPTION
                        "This table represents the information for historical
                         data collected for the upsm card"
                ::= { upsmHist 1 }

        upsmHistEntry	OBJECT-TYPE
                SYNTAX  UpsmHistEntry
                ACCESS  not-accessible
                STATUS  mandatory
                DESCRIPTION
                        "Specifies the index for each row in the table below"
                INDEX { upsmHMode }
                ::= { upsmHistTable 1 }

        UpsmHistEntry    ::=
                SEQUENCE {
                        upsmHMode        HistoryMode,
                        upsmHNumEvents   Counter
                }

        upsmHMode		OBJECT-TYPE
                SYNTAX  HistoryMode
                ACCESS  read-only
                STATUS  mandatory
                DESCRIPTION
                        "The mode of the data collection.  Valid values are:
                         daily or longterm."
                ::= { upsmHistEntry 1 }

        upsmHNumEvents	OBJECT-TYPE
                SYNTAX  Counter
                ACCESS  read-only
                STATUS  mandatory
                DESCRIPTION
                        "Total number of all traps (events) generated by all
                         UPSM's."
                ::= { upsmHistEntry 2 }

        upsmHHistTable	OBJECT-TYPE
                SYNTAX  SEQUENCE OF UpsmHHistEntry
                ACCESS  not-accessible
                STATUS  mandatory
                DESCRIPTION
                        "This table represents the information for performance
                         data collected for each upsm card."
                ::= { upsmHist 2 }

        upsmHHistEntry	OBJECT-TYPE
                SYNTAX  UpsmHHistEntry
                ACCESS  not-accessible
                STATUS  mandatory
                DESCRIPTION
                        "Specifies the index for each row in the table below"
                INDEX { upsmHHistMode, upsmHHistLocation, upsmHHistShelf,
                        upsmHHistSlot }
                ::= {upsmHHistTable 1 }

        UpsmHHistEntry   ::=
                SEQUENCE {
                        upsmHHistMode		HistoryMode,
                        upsmHHistLocation	CardLocation,
                        upsmHHistShelf		CardShelf,
                        upsmHHistSlot		CardSlot,
                        upsmHLastBootTime	DateAndTime,
                        upsmHAvailTime		Counter,
                        upsmHErrFreeSecs	Counter
                }

        upsmHHistMode	OBJECT-TYPE
                SYNTAX  HistoryMode
                ACCESS  read-only
                STATUS  mandatory
                DESCRIPTION
                        "The mode of the data collection.  Valid values are:
                         daily or longterm."
                ::= { upsmHHistEntry 1 }

        upsmHHistLocation  OBJECT-TYPE
                SYNTAX  CardLocation
                ACCESS  read-only
                STATUS  mandatory
                DESCRIPTION
                        "The location of the card."
                ::= { upsmHHistEntry 2 }

        upsmHHistShelf	OBJECT-TYPE
                SYNTAX  CardShelf
                ACCESS  read-only
                STATUS  mandatory
                DESCRIPTION
                        "The shelf the card is in."
                ::= { upsmHHistEntry 3 }

        upsmHHistSlot    OBJECT-TYPE
                SYNTAX  CardSlot
                ACCESS  read-only
                STATUS  mandatory
                DESCRIPTION
                        "The slot within the shelf the card is in."
                ::= { upsmHHistEntry 4 }

        upsmHLastBootTime  OBJECT-TYPE
                SYNTAX  DateAndTime
                ACCESS  read-only
                STATUS  mandatory
                DESCRIPTION
                        "The date and time of the last boot for this card."
                ::= { upsmHHistEntry 6 }

        upsmHAvailTime	OBJECT-TYPE
                SYNTAX  Counter
                ACCESS  read-only
                STATUS  mandatory
                DESCRIPTION
                        "The number of seconds that this upsm has been up and
                         running."
                ::= { upsmHHistEntry 7 }

        upsmHErrFreeSecs OBJECT-TYPE
                SYNTAX  Counter
                ACCESS  read-only
                STATUS  mandatory
                DESCRIPTION
                        "The number of seconds that this upsm has not
                         experienced any alarms."
                ::= { upsmHHistEntry 8 }



        -- The elements in the systemCond subgroup of the specialConditions

        sysCStatus      OBJECT-TYPE
                SYNTAX  CardStatus
                ACCESS  read-only
                STATUS  mandatory
                DESCRIPTION
                        "The global status of the system as computed based on
                         the traps (events) that are generated.  Choices are:
                         Critical, Major, Minor or Normal."
                ::= { systemCond 1 }

        sysCSetMode     OBJECT-TYPE
                SYNTAX  FlagType
                ACCESS  read-write
                STATUS  mandatory
                DESCRIPTION
                        "If on, the special conditions counters will be
                         activated.  These counters continue counting until
                         the mode is off.  On startup, this flag is off."
                ::= { systemCond 2 }

        sysCAvailTime   OBJECT-TYPE
                SYNTAX  Counter
                ACCESS  read-only
                STATUS  mandatory
                DESCRIPTION
                        "The number of seconds since this mode is started
                         that the system has been up and running. The Criteria
                         for the system available time is having at least one CP
                         running with atmost non-service affecting minor
                         alarm system status"
                ::= { systemCond 3 }

        sysCErrFreeSecs OBJECT-TYPE
                SYNTAX  Counter
                ACCESS  read-only
                STATUS  mandatory
                DESCRIPTION
                        "The number of seconds since this mode is started
                         that the device has not experienced any alarms.  This
                         counter is across all cards in the chassis.  The
                         system must be in Normal status for this counter to
                         be incremented."
                ::= { systemCond 4 }


        -- The elements in the downloadCond subgroup of the specialConditions

        dlCStatus       OBJECT-TYPE
                SYNTAX  DownloadStatus
                ACCESS  read-write 
                STATUS  mandatory
                DESCRIPTION
                        "The global status of the download task.  The download task 
				(download to the device) is either ftp-inprogress, module 
				update inprogress or currently idle.  Since only one download 
				at the time is handled by the system, this flag is set to 
				inprogress as soon as any download starts.  
				It is reset back to idle when the download is completed.  
				This flag is set to idle on system startup.  This flag 
				can be remotely set to idle if a previous FTP download 
				was interrupted."
                ::= { downloadCond 1 }

        dlCOkDownloads  OBJECT-TYPE
                SYNTAX  Counter
                ACCESS  read-only 
                STATUS  mandatory
                DESCRIPTION
                        "The number of successful downloads in this time
                         interval (15 minutes)."
                ::= { downloadCond 2 }

        dlCBadDownloads OBJECT-TYPE
                SYNTAX  Counter
                ACCESS  read-only 
                STATUS  mandatory
                DESCRIPTION
                        "The number of failed downloads in this time
                         interval (15 minutes)."
                ::= { downloadCond 3 }

        dlCLongestTime  OBJECT-TYPE
                SYNTAX  Gauge
                ACCESS  read-only 
                STATUS  mandatory
                DESCRIPTION
                        "Longest time for any download, in seconds, in this
                         time interval (15 minutes)."
                ::= { downloadCond 4 }

        dlCLongestSize  OBJECT-TYPE
                SYNTAX  Gauge
                ACCESS  read-only 
                STATUS  mandatory
                DESCRIPTION
                        "Longest download size for any download, in bytes, in
                         this time interval (15 minutes)."
                ::= { downloadCond 5 }

	dlCCounterFlag  OBJECT-TYPE
                SYNTAX  FlagType
                ACCESS  read-write
                STATUS  mandatory
                DESCRIPTION
                        "Turns software counters On or Off."
                ::= { downloadCond 6 }

        -- The elements in the cpCond subgroup of the specialConditions

        cpCNumEvents    OBJECT-TYPE
                SYNTAX  Counter
                ACCESS  read-only
                STATUS  mandatory
                DESCRIPTION
                        "Total number of events received by the active CP
                         since this mode was activated."
                ::= { cpCond 1 }

        cpCTrapsSent    OBJECT-TYPE
                SYNTAX  Counter
                ACCESS  read-only
                STATUS  mandatory
                DESCRIPTION
                        "Total number of traps sent by the active CP since
                         this mode was activated."
                ::= { cpCond 2 }

        cpCSNMPCmdsRcvd OBJECT-TYPE
                SYNTAX  Counter
                ACCESS  read-only
                STATUS  mandatory
                DESCRIPTION
                        "Total number of SNMP commands received by the active
                         CP since this mode was activated."
                ::= { cpCond 3 }

        cpCCounterFlag  OBJECT-TYPE
                SYNTAX  FlagType
                ACCESS  read-write
                STATUS  mandatory
                DESCRIPTION
                        "Turns software counters On or Off."
                ::= { cpCond 4 }

        cpCCntrTable    OBJECT-TYPE
                SYNTAX  SEQUENCE OF CpCCntrEntry
                ACCESS  not-accessible
                STATUS  mandatory
                DESCRIPTION
                        "This table represents the information for each
                         entry for the software counters.  It is only
			 applicable to the active MPM card."
                ::= { cpCond 5 }

        cpCCntrEntry    OBJECT-TYPE
                SYNTAX  CpCCntrEntry
                ACCESS  not-accessible
                STATUS  mandatory
                DESCRIPTION
                        "Specifies the index for each row in the table below"
                INDEX { cpCCntrShelf, cpCCntrSlot, cpCCntrType }
                ::= { cpCCntrTable 1 }

        CpCCntrEntry    ::=
                SEQUENCE {
                        cpCCntrShelf    CardShelf,
                        cpCCntrSlot     INTEGER,
                        cpCCntrType     INTEGER,
                        cpCTotPktSent   Counter,
                        cpCTotPktRcvd   Counter,
                        cpCBadPktRcvd   Counter,
                        cpCTotBadTrans  Counter,
                        cpCBytesSent    Counter,
                        cpCBytesRcvd    Counter,
                        cpCMsgsDlvrd    Counter,
                        cpCBufAllocFail Counter,
                        cpCEcbAllocFail Counter
                }

        cpCCntrShelf    OBJECT-TYPE
                SYNTAX  CardShelf
                ACCESS  read-only
                STATUS  mandatory
                DESCRIPTION
                        "The shelf the card is in.  Valid values are: 1 to 10.
                         The system automatically determines the right value
                         for this entry based on the value of the current
                         active CP card."
                ::= { cpCCntrEntry 1 }

        cpCCntrSlot     OBJECT-TYPE
                SYNTAX  CardSlot
                ACCESS  read-only
                STATUS  mandatory
                DESCRIPTION
                        "The slot within the shelf the card is in.  The
                         system automatically determines the right value
                         for this entry based on the value of the current
                         active CP card."
                ::= { cpCCntrEntry 2 }

        cpCCntrType     OBJECT-TYPE
                SYNTAX  INTEGER { spi(1) }
                ACCESS  read-only
                STATUS  mandatory
                DESCRIPTION
                        "The type of the software counter data in this row.
                         The data is collected for the SPI data channels."
                ::= { cpCCntrEntry 3 }

        cpCTotPktSent   OBJECT-TYPE
                SYNTAX  Counter
                ACCESS  read-only
                STATUS  mandatory
                DESCRIPTION
                        "The number of data packets sent over the given data
                         channel."
                ::= { cpCCntrEntry 4 }

        cpCTotPktRcvd   OBJECT-TYPE
                SYNTAX  Counter
                ACCESS  read-only
                STATUS  mandatory
                DESCRIPTION
                        "The number of data packets received over the given
                         data channel."
                ::= { cpCCntrEntry 5 }

        cpCBadPktRcvd   OBJECT-TYPE
                SYNTAX  Counter
                ACCESS  read-only
                STATUS  mandatory
                DESCRIPTION
                        "The number of bad data packets received over the given
                         data channel."
                ::= { cpCCntrEntry 6 }

        cpCTotBadTrans  OBJECT-TYPE
                SYNTAX  Counter
                ACCESS  read-only
                STATUS  mandatory
                DESCRIPTION
                        "The number of bad data transmissions over the given
                         data channel."
                ::= { cpCCntrEntry 7 }

        cpCBytesSent    OBJECT-TYPE
                SYNTAX  Counter
                ACCESS  read-only
                STATUS  mandatory
                DESCRIPTION
                        "Total number of bytes sent over the given
                         data channel."
                ::= { cpCCntrEntry 8 }

        cpCBytesRcvd    OBJECT-TYPE
                SYNTAX  Counter
                ACCESS  read-only
                STATUS  mandatory
                DESCRIPTION
                        "Total number of data bytes received over the given
                         data channel."
                ::= { cpCCntrEntry 9 }

        cpCMsgsDlvrd    OBJECT-TYPE
                SYNTAX  Counter
                ACCESS  read-only
                STATUS  mandatory
                DESCRIPTION
                        "The number of complete messages delivered over the
                         given data channel."
                ::= { cpCCntrEntry 10 }

        cpCBufAllocFail OBJECT-TYPE
                SYNTAX  Counter
                ACCESS  read-only
                STATUS  mandatory
                DESCRIPTION
                        "Number of buffer allocation failures for the given
                         data channel."
                ::= { cpCCntrEntry 11 }

        cpCEcbAllocFail OBJECT-TYPE
                SYNTAX  Counter
                ACCESS  read-only
                STATUS  mandatory
                DESCRIPTION
                        "Number of Event Control Block allocation failures
                         for the given data channel."
                ::= { cpCCntrEntry 12 }

        cpCPerfTable    OBJECT-TYPE
                SYNTAX  SEQUENCE OF CpCPerfEntry
                ACCESS  not-accessible
                STATUS  mandatory
                DESCRIPTION
                        "This table represents the information for performance
                         data collected for each communication processor"
                ::= { cpCond 6 }

        cpCPerfEntry    OBJECT-TYPE
                SYNTAX  CpCPerfEntry
                ACCESS  not-accessible
                STATUS  mandatory
                DESCRIPTION
                        "Specifies the index for each row in the table below"
                INDEX { cpCPerfShelf, cpCPerfSlot }
                ::= { cpCPerfTable 1 }

        CpCPerfEntry    ::=
                SEQUENCE {
                        cpCPerfShelf    CardShelf,
                        cpCPerfSlot     INTEGER,
                        cpCPerfMode     RedundancyMode,
                        cpCPerfState    CardState,
                        cpCPerfStatus   CardStatus,
                        cpCAvailTime    Counter,
                        cpCErrFreeSecs  Counter
                }

        cpCPerfShelf    OBJECT-TYPE
                SYNTAX  CardShelf
                ACCESS  read-only
                STATUS  mandatory
                DESCRIPTION
                        "The shelf the card is in.  Valid values are: 1 to 10"
                ::= { cpCPerfEntry 1 }

        cpCPerfSlot     OBJECT-TYPE
                SYNTAX  CardSlot
                ACCESS  read-only
                STATUS  mandatory
                DESCRIPTION
                        "The slot within the shelf the card is in."
                ::= { cpCPerfEntry 2 }

        cpCPerfMode     OBJECT-TYPE
                SYNTAX  RedundancyMode
                ACCESS  read-only
                STATUS  mandatory
                DESCRIPTION
                        "The valid types are: active CP or standby CP"
                ::= { cpCPerfEntry 3 }

        cpCPerfState    OBJECT-TYPE
                SYNTAX  CardState
                ACCESS  read-only
                STATUS  mandatory
                DESCRIPTION
                        "The state of the communication card.  The states
                         are: online, offline, empty, loopback or diagnostics."
                ::= { cpCPerfEntry 4 }

        cpCPerfStatus   OBJECT-TYPE
                SYNTAX  CardStatus
                ACCESS  read-only
                STATUS  mandatory
                DESCRIPTION
                        "The status of the communication processor.  This
                         status represents the state of the communication
                         processor and in general is different from the
                         status of the system."
                ::= { cpCPerfEntry 5 }

        cpCAvailTime    OBJECT-TYPE
                SYNTAX  Counter
                ACCESS  read-only
                STATUS  mandatory
                DESCRIPTION
                        "The number of seconds since this mode is started
                         that this CP has been up and running.  This will
                         generally be the same as 15 minutes in seconds (900)."
                ::= { cpCPerfEntry 7 }

        cpCErrFreeSecs  OBJECT-TYPE
                SYNTAX  Counter
                ACCESS  read-only
                STATUS  mandatory
                DESCRIPTION
                        "The number of seconds since this mode is started
                         that this CP has not experienced any alarms."
                ::= { cpCPerfEntry 8 }


        -- The elements in the ccCond subgroup of the specialConditions

        ccCNumEvents    OBJECT-TYPE
                SYNTAX  Counter
                ACCESS  read-only
                STATUS  mandatory
                DESCRIPTION
                        "Total number of events received for all CC's since
                         this mode was started."
                ::= { ccCond 1 }

        ccCCntrTable    OBJECT-TYPE
                SYNTAX  SEQUENCE OF CcCCntrEntry
                ACCESS  not-accessible
                STATUS  mandatory
                DESCRIPTION
                        "This table represents the information for each
                         entry for the software counters."
                ::= { ccCond 2 }

        ccCCntrEntry    OBJECT-TYPE
                SYNTAX  CcCCntrEntry
                ACCESS  not-accessible
                STATUS  mandatory
                DESCRIPTION
                        "Specifies the index for each row in the table below"
                INDEX { ccCCntrLocation, ccCCntrShelf, ccCCntrSlot,
                        ccCCntrType }
                ::= { ccCCntrTable 1 }

        CcCCntrEntry    ::=
                SEQUENCE {
                        ccCCntrLocation CardLocation,
                        ccCCntrShelf    CardShelf,
                        ccCCntrSlot     INTEGER,
                        ccCCntrType     INTEGER,
                        ccCCounterFlag  FlagType,
                        ccCTotPktSent   Counter,
                        ccCTotPktRcvd   Counter,
                        ccCBadPktRcvd   Counter,
                        ccCTotBadTrans  Counter,
                        ccCBytesSent    Counter,
                        ccCBytesRcvd    Counter,
                        ccCMsgsDlvrd    Counter,
                        ccCBufAllocFail Counter,
                        ccCEcbAllocFail Counter,
			ccCClearCntrs   ResetType 
                }

        ccCCntrLocation OBJECT-TYPE
                SYNTAX  CardLocation
                ACCESS  read-only
                STATUS  mandatory
                DESCRIPTION
                        "The location of the CC card.  The values are: Local
                         or Remote.  The system automatically determines the
                         right value for this entry based on the known
                         CC cards."
                ::= { ccCCntrEntry 1 }

        ccCCntrShelf    OBJECT-TYPE
                SYNTAX  CardShelf
                ACCESS  read-only
                STATUS  mandatory
                DESCRIPTION
                        "The shelf the card is in.  Valid values are: 1 to 10.
                         The system automatically determines the right value
                         for this entry based on the known (available) CC
                         cards."
                ::= { ccCCntrEntry 2 }

        ccCCntrSlot     OBJECT-TYPE
                SYNTAX  CardSlot
                ACCESS  read-only
                STATUS  mandatory
                DESCRIPTION
                        "The slot within the shelf the card is in.  The
                         system automatically determines the right value
                         for this entry based on the known (available)
                         CC cards."
                ::= { ccCCntrEntry 3 }

        ccCCntrType     OBJECT-TYPE
                SYNTAX  INTEGER { spi(1), iwm(2) }
                ACCESS  read-only
                STATUS  mandatory
                DESCRIPTION
                        "The type of the software counter data in this row.
                         The data is collected for the SPI data channels."
                ::= { ccCCntrEntry 4 }

        ccCCounterFlag  OBJECT-TYPE
                SYNTAX  FlagType
                ACCESS  read-write
                STATUS  mandatory
                DESCRIPTION
                        "Turns software counters, both On or both Off for this CC. When Off Clears both counters Statistic information "
                ::= { ccCCntrEntry 5 }

        ccCTotPktSent   OBJECT-TYPE
                SYNTAX  Counter
                ACCESS  read-only
                STATUS  mandatory
                DESCRIPTION
                        "The number of data packets sent over the given data
                         channel."
                ::= { ccCCntrEntry 6 }

        ccCTotPktRcvd   OBJECT-TYPE
                SYNTAX  Counter
                ACCESS  read-only
                STATUS  mandatory
                DESCRIPTION
                        "The number of data packets received over the given
                         data channel."
                ::= { ccCCntrEntry 7 }

        ccCBadPktRcvd   OBJECT-TYPE
                SYNTAX  Counter
                ACCESS  read-only
                STATUS  mandatory
                DESCRIPTION
                        "The number of bad data packets received over the given
                         data channel."
                ::= { ccCCntrEntry 8 }

        ccCTotBadTrans  OBJECT-TYPE
                SYNTAX  Counter
                ACCESS  read-only
                STATUS  mandatory
                DESCRIPTION
                        "The number of bad data transmissions over the given
                         data channel."
                ::= { ccCCntrEntry 9 }

        ccCBytesSent    OBJECT-TYPE
                SYNTAX  Counter
                ACCESS  read-only
                STATUS  mandatory
                DESCRIPTION
                        "Total number of bytes sent over the given
                         data channel."
                ::= { ccCCntrEntry 10 }

        ccCBytesRcvd    OBJECT-TYPE
                SYNTAX  Counter
                ACCESS  read-only
                STATUS  mandatory
                DESCRIPTION
                        "Total number of data bytes received over the given
                         data channel."
                ::= { ccCCntrEntry 11 }

        ccCMsgsDlvrd    OBJECT-TYPE
                SYNTAX  Counter
                ACCESS  read-only
                STATUS  mandatory
                DESCRIPTION
                        "The number of complete messages delivered over the
                         given data channel."
                ::= { ccCCntrEntry 12 }

        ccCBufAllocFail OBJECT-TYPE
                SYNTAX  Counter
                ACCESS  read-only
                STATUS  mandatory
                DESCRIPTION
                        "Number of buffer allocation failures for the given
                         data channel."
                ::= { ccCCntrEntry 13 }

        ccCEcbAllocFail OBJECT-TYPE
                SYNTAX  Counter
                ACCESS  read-only
                STATUS  mandatory
                DESCRIPTION
                        "Number of Event Control Block allocation failures
                         for the given data channel."
                ::= { ccCCntrEntry 14 }
	ccCClearCntrs    OBJECT-TYPE
		SYNTAX  ResetType
		ACCESS  read-write
		STATUS  mandatory
		DESCRIPTION
			"If the value is reset, all software counters for this
			 15 minute interval are reset to zero.  A get on this
			 will always return other."
		::= { ccCCntrEntry 15 }

        ccCPerfTable    OBJECT-TYPE
                SYNTAX  SEQUENCE OF CcCPerfEntry
                ACCESS  not-accessible
                STATUS  mandatory
                DESCRIPTION
                        "This table represents the information for performance
                         data collected for each channel card."
                ::= { ccCond 3 }

        ccCPerfEntry    OBJECT-TYPE
                SYNTAX  CcCPerfEntry
                ACCESS  not-accessible
                STATUS  mandatory
                DESCRIPTION
                        "Specifies the index for each row in the table below"
                INDEX { ccCPerfLocation, ccCPerfShelf, ccCPerfSlot }
                ::= { ccCPerfTable 1 }

        CcCPerfEntry    ::=
                SEQUENCE {
                        ccCPerfLocation   CardLocation,
                        ccCPerfShelf      CardShelf,
                        ccCPerfSlot       INTEGER,
                        ccCPerfState      CardState,
                        ccCPerfStatus     CardStatus,
                        ccCAvailTime      Counter,
                        ccCErrFreeSecs    Counter,
                        ccCBiasCurrent    INTEGER,
                        ccCModulation     INTEGER,
                        ccCApc            INTEGER,
                        ccCIwmModulation  INTEGER,
                        ccCLaserOnOff     FlagType,
                        ccCTemperature    Gauge,
                        ccCIntensity      Gauge,
                        ccCSignalStrength Gauge,
                        ccCLossOfLight    Boolean,
                        ccCSignalDetect   Boolean,
                        ccCRefClock       INTEGER,
                        ccCClockDiv       INTEGER,
						ccCProtectionMode	INTEGER
                }

        ccCPerfLocation OBJECT-TYPE
                SYNTAX  CardLocation
                ACCESS  read-only
                STATUS  mandatory
                DESCRIPTION
                        "The location of the card.  Valid choices are Local
                         or Remote.  The system automatically selects this
                         value based on the known (available) CC cards."
                ::= { ccCPerfEntry 1 }

        ccCPerfShelf    OBJECT-TYPE
                SYNTAX  CardShelf
                ACCESS  read-only
                STATUS  mandatory
                DESCRIPTION
                        "The shelf the card is in.  Valid values are: 1 to 10"
                ::= { ccCPerfEntry 2 }

        ccCPerfSlot     OBJECT-TYPE
                SYNTAX  CardSlot
                ACCESS  read-only
                STATUS  mandatory
                DESCRIPTION
                        "The slot within the shelf the card is in."
                ::= { ccCPerfEntry 3 }

        ccCPerfState    OBJECT-TYPE
                SYNTAX  CardState
                ACCESS  read-only
                STATUS  mandatory
                DESCRIPTION
                        "The state of the channel card.  The states'
                         are: online, offline, empty, loopback or diagnostics."
                ::= { ccCPerfEntry 4 }

        ccCPerfStatus   OBJECT-TYPE
                SYNTAX  CardStatus
                ACCESS  read-only
                STATUS  mandatory
                DESCRIPTION
                        "The status of the channel card.  This
                         status represents the status of the communication
                         processor and in general is different from the
                         status of the system."
                ::= { ccCPerfEntry 5 }

        ccCAvailTime    OBJECT-TYPE
                SYNTAX  Counter
                ACCESS  read-only
                STATUS  mandatory
                DESCRIPTION
                        "The number of seconds in this time slot (15 minutes)
                         that this CC has been up and running.  This will
                         generally be the same as 15 minutes in seconds (900)."
                ::= { ccCPerfEntry 6 }

        ccCErrFreeSecs  OBJECT-TYPE
                SYNTAX  Counter
                ACCESS  read-only
                STATUS  mandatory
                DESCRIPTION
                        "The number of seconds in this time slot (15 minutes)
                         that this CC has not experienced any alarms."
                ::= { ccCPerfEntry 7 }

        ccCBiasCurrent  OBJECT-TYPE
                SYNTAX  INTEGER
                ACCESS  read-only
                STATUS  mandatory
                DESCRIPTION
                        "Bias current for the optical laser."
                ::= { ccCPerfEntry 8 }

        ccCModulation   OBJECT-TYPE
                SYNTAX  INTEGER
                ACCESS  read-only
                STATUS  mandatory
                DESCRIPTION
                        "The frequency modulation for the optical laser."
                ::= { ccCPerfEntry 9 }

        ccCApc          OBJECT-TYPE
                SYNTAX  INTEGER
                ACCESS  read-only
                STATUS  mandatory
                DESCRIPTION
                        "The APC value."
                ::= { ccCPerfEntry 10 }

        ccCIwmModulation  OBJECT-TYPE
                SYNTAX  INTEGER
                ACCESS  read-only
                STATUS  mandatory
                DESCRIPTION
                        "The frequency modulation for the IWM channel."
                ::= { ccCPerfEntry 11 }

        ccCLaserOnOff   OBJECT-TYPE
                SYNTAX  FlagType
                ACCESS  read-only
                STATUS  mandatory
                DESCRIPTION
                        "The laser On/Off flag."
                ::= { ccCPerfEntry 12 }

        ccCTemperature  OBJECT-TYPE
                SYNTAX  Gauge
                ACCESS  read-only
                STATUS  mandatory
                DESCRIPTION
                        "The current temperature, or the operating temperature
                         of the optical device."
                ::= { ccCPerfEntry 13 }

        ccCIntensity    OBJECT-TYPE
                SYNTAX  Gauge
                ACCESS  read-only
                STATUS  mandatory
                DESCRIPTION
                        "The intensity of the optical light."
                ::= { ccCPerfEntry 14 }

        ccCSignalStrength OBJECT-TYPE
                SYNTAX  Gauge
                ACCESS  read-only
                STATUS  mandatory
                DESCRIPTION
                        "The current signal strength for the optical path."
                ::= { ccCPerfEntry 15 }

        ccCLossOfLight  OBJECT-TYPE
                SYNTAX  Boolean
                ACCESS  read-only
                STATUS  mandatory
                DESCRIPTION
                        "If set to true, no laser light is present.  If set to
                         false, no loss of light has occurred."
                ::= { ccCPerfEntry 16 }

        ccCSignalDetect OBJECT-TYPE
                SYNTAX  Boolean
                ACCESS  not-accessible
                STATUS  mandatory
                DESCRIPTION
                        "If set to true, signal is detected.  If set to false,
                         no signal is present."
                ::= { ccCPerfEntry 17 }

        ccCRefClock     OBJECT-TYPE
                SYNTAX  INTEGER { 	en1660 (1),
    						en1944(2),
    						en1953(3)
				} 
                ACCESS  not-accessible
                STATUS  mandatory
                DESCRIPTION
                        "The value of the reference clock in decimal notation.
                         For a given value, like 1660, the actual value is
                         16.60-EN.  In otherwords, assume a two digit decimal
                         point, plus any appropriate scaling factor."
                ::= { ccCPerfEntry 18 }

        ccCClockDiv     OBJECT-TYPE
                SYNTAX  INTEGER { dout-1250(1), dout-622(2), dout-155(3) }
                ACCESS  not-accessible
                STATUS  mandatory
                DESCRIPTION
                        "The clock divisor.  Values are 1250, 622 or 155 in the
                         appropriate clock frequency scale."
                ::= { ccCPerfEntry 19 }

		ccCProtectionMode     OBJECT-TYPE
                SYNTAX  INTEGER 
				{ 
						active(1), 
						standby(2), 
						na(3) 
				}
                ACCESS  read-only
                STATUS  mandatory
                DESCRIPTION
                        "UPSR Protection Mode:  active, standby and na."
                ::= { ccCPerfEntry 20 }


        -- The elements in the muxCond subgroup of the specialConditions

        muxCNumEvents   OBJECT-TYPE
                SYNTAX  Counter
                ACCESS  read-only
                STATUS  mandatory
                DESCRIPTION
                        "Total number of all traps (events) generated by all
                         MUX's since this mode is started."
                ::= { muxCond 1 }




        muxCPerfTable   OBJECT-TYPE
                SYNTAX  SEQUENCE OF MuxCPerfEntry
                ACCESS  not-accessible
                STATUS  mandatory
                DESCRIPTION
                        "This table represents the information for performance
                         data collected for each mux/demux card"
                ::= { muxCond 2 }

        muxCPerfEntry   OBJECT-TYPE
                SYNTAX  MuxCPerfEntry
                ACCESS  not-accessible
                STATUS  mandatory
                DESCRIPTION
                        "Specifies the index for each row in the table below"
                INDEX { muxCPerfLocation, muxCPerfShelf, muxCPerfSlot }
                ::= { muxCPerfTable 1 }

        MuxCPerfEntry   ::=
                SEQUENCE {
                        muxCPerfLocation  CardLocation,
                        muxCPerfShelf     CardShelf,
                        muxCPerfSlot      INTEGER,
                        muxCType          INTEGER,
                        muxCPerfState     CardState,
                        muxCPerfStatus    CardStatus,
                        muxCAvailTime     Counter,
                        muxCErrFreeSecs   Counter
                }

        muxCPerfLocation  OBJECT-TYPE
                SYNTAX  CardLocation
                ACCESS  read-only
                STATUS  mandatory
                DESCRIPTION
                        "The location of the card.  Choices are local or
                         remote."
                ::= { muxCPerfEntry 1 }

        muxCPerfShelf   OBJECT-TYPE
                SYNTAX  CardShelf
                ACCESS  read-only
                STATUS  mandatory
                DESCRIPTION
                        "The shelf the card is in.  Valid values are: 1 to 10"
                ::= { muxCPerfEntry 2 }

        muxCPerfSlot    OBJECT-TYPE
                SYNTAX  CardSlot
                ACCESS  read-only
                STATUS  mandatory
                DESCRIPTION
                        "The slot within the shelf the card is in."
                ::= { muxCPerfEntry 3 }

        muxCType        OBJECT-TYPE
                SYNTAX  INTEGER { mux(4), demux(5), w4cd(10), w2cmd(13), w4cm(21)}
                ACCESS  read-only
                STATUS  mandatory
                DESCRIPTION
                        "The type of the mux.  The choices are: mux or demux."
                ::= { muxCPerfEntry 4 }

        muxCPerfState   OBJECT-TYPE
                SYNTAX  CardState
                ACCESS  read-only
                STATUS  mandatory
                DESCRIPTION
                        "The status of the mux card.  The states are:
                         online, offline, empty, loopback or diag."
                ::= { muxCPerfEntry 5 }

        muxCPerfStatus  OBJECT-TYPE
                SYNTAX  CardStatus
                ACCESS  read-only
                STATUS  mandatory
                DESCRIPTION
                        "The status of the mux card.  This status represents
                         the status of the mux card and in general is
                         different from the status of the system."
                ::= { muxCPerfEntry 6 }

        muxCAvailTime   OBJECT-TYPE
                SYNTAX  Counter
                ACCESS  read-only
                STATUS  mandatory
                DESCRIPTION
                        "The number of seconds in this time slot (15 minutes)
                         that this Mux has been up and running.  This will
                         generally be the same as 15 minutes in seconds (900)."
                ::= { muxCPerfEntry 7 }

        muxCErrFreeSecs OBJECT-TYPE
                SYNTAX  Counter
                ACCESS  read-only
                STATUS  mandatory
                DESCRIPTION
                        "The number of seconds in this time slot (15 minutes)
                         that this mux has not experienced any alarms."
                ::= { muxCPerfEntry 8 }

        muxCCounterFlag   OBJECT-TYPE
                SYNTAX  FlagType
                ACCESS  read-write
                STATUS  mandatory
                DESCRIPTION
                        "Turns special condition software counters On or Off
			 for this card. Default is off."
                ::= { muxCond 3}


        -- The elements in the psCond subgroup of the specialConditions

        psCNumEvents    OBJECT-TYPE
                SYNTAX  Counter
                ACCESS  not-accessible
                STATUS  mandatory
                DESCRIPTION
                        "Total number of all traps (events) generated by all
                         Power Supplies since this mode is started."
                ::= { psCond 1 }

        psCVoltageLevel3pt3Volt     OBJECT-TYPE
                SYNTAX  INTEGER
                ACCESS  not-accessible
                STATUS  mandatory
                DESCRIPTION
                        "Voltage Level of the 3.3 V power supply.  Need to divide 
			 this value by ten to get the actual voltage level."  
                ::= { psCond 2 }

        psCVoltageLevel5Volt      OBJECT-TYPE
                SYNTAX  INTEGER
                ACCESS  not-accessible
                STATUS  mandatory
                DESCRIPTION
                        "Voltage Level of the 5 V power supply.  Need to divide 
			 this value by ten to get the actual voltage level."  
                ::= { psCond 3 }

        psCVoltageLevel12Volt     OBJECT-TYPE
                SYNTAX  INTEGER
                ACCESS  not-accessible
                STATUS  mandatory
                DESCRIPTION
                        "Voltage Level of the 12 V power supply.  Need to divide 
			 this value by ten to get the actual voltage level."  
                ::= { psCond 4 }


        psCPerfTable    OBJECT-TYPE
                SYNTAX  SEQUENCE OF PsCPerfEntry
                ACCESS  not-accessible
                STATUS  mandatory
                DESCRIPTION
                        "This table represents the information for performance
                         data collected for each power supply card"
                ::= { psCond 5 }

        psCPerfEntry    OBJECT-TYPE
                SYNTAX  PsCPerfEntry
                ACCESS  not-accessible
                STATUS  mandatory
                DESCRIPTION
                        "Specifies the index for each row in the table below"
                INDEX { psCPerfID }
                ::= { psCPerfTable 1 }

        PsCPerfEntry    ::=
                SEQUENCE {
                        psCPerfID    	INTEGER,
                        psCPerfType     RedundancyMode,
                        psCPerfState    CardState,
                        psCPerfStatus   CardStatus
                }

        psCPerfID    OBJECT-TYPE
                SYNTAX  INTEGER
                ACCESS  not-accessible
                STATUS  mandatory
                DESCRIPTION
                        "The module id where ps is in.  Valid values are: 1 to 4"
                ::= { psCPerfEntry 1 }

        psCPerfType     OBJECT-TYPE
                SYNTAX  RedundancyMode
                ACCESS  not-accessible
                STATUS  mandatory
                DESCRIPTION
                        "The type of the power supply card.  The choices are:
                         active (primary PS) or standby."
                ::= { psCPerfEntry 2 }

        psCPerfState    OBJECT-TYPE
                SYNTAX  CardState
                ACCESS  not-accessible
                STATUS  mandatory
                DESCRIPTION
                        "The state of the power supply card.  The states are:
                         online, offline, empty, loopback or diagnostics."
                ::= { psCPerfEntry 3 }

        psCPerfStatus   OBJECT-TYPE
                SYNTAX  CardStatus
                ACCESS  not-accessible
                STATUS  mandatory
                DESCRIPTION
                        "The status of the power supply card.  This status
                         represents the status of the ps card and in general is
                         different from the status of the system."
                ::= { psCPerfEntry 4 }


        -- The elements in the fadmCond subgroup of the specialConditions

        fadmCNumEvents   OBJECT-TYPE
                SYNTAX  Counter
                ACCESS  read-only
                STATUS  mandatory
                DESCRIPTION
                        "Total number of all traps (events) generated by all
                         FADM's since this mode is started."
                ::= { fadmCond 1 }

        fadmCCounterFlag  OBJECT-TYPE
                SYNTAX  FlagType
                ACCESS  read-write
                STATUS  mandatory
                DESCRIPTION
                        "Turns software counters On or Off for this FADM."
                ::= { fadmCond 2 }

        fadmCPerfTable   OBJECT-TYPE
                SYNTAX  SEQUENCE OF FadmCPerfEntry
                ACCESS  not-accessible
                STATUS  mandatory
                DESCRIPTION
                        "This table represents the information for performance
                         data collected for each fadm card"
                ::= { fadmCond 3 }

        fadmCPerfEntry   OBJECT-TYPE
                SYNTAX  FadmCPerfEntry
                ACCESS  not-accessible
                STATUS  mandatory
                DESCRIPTION
                        "Specifies the index for each row in the table below"
                INDEX { fadmCPerfLocation, fadmCPerfShelf, fadmCPerfSlot }
                ::= { fadmCPerfTable 1 }

        FadmCPerfEntry   ::=
                SEQUENCE {
                        fadmCPerfLocation  CardLocation,
                        fadmCPerfShelf     CardShelf,
                        fadmCPerfSlot      INTEGER,
                        fadmCPerfState     CardState,
                        fadmCPerfStatus    CardStatus,
                        fadmCAvailTime     Counter,
                        fadmCErrFreeSecs   Counter
                }

        fadmCPerfLocation  OBJECT-TYPE
                SYNTAX  CardLocation
                ACCESS  read-only
                STATUS  mandatory
                DESCRIPTION
                        "The location of the card.  Choices are local or
                         remote."
                ::= { fadmCPerfEntry 1 }

        fadmCPerfShelf   OBJECT-TYPE
                SYNTAX  CardShelf
                ACCESS  read-only
                STATUS  mandatory
                DESCRIPTION
                        "The shelf the card is in.  Valid values are: 1 to 10"
                ::= { fadmCPerfEntry 2 }

        fadmCPerfSlot    OBJECT-TYPE
                SYNTAX  CardSlot
                ACCESS  read-only
                STATUS  mandatory
                DESCRIPTION
                        "The slot within the shelf the card is in."
                ::= { fadmCPerfEntry 3 }

        fadmCPerfState   OBJECT-TYPE
                SYNTAX  CardState
                ACCESS  read-only
                STATUS  mandatory
                DESCRIPTION
                        "The status of the mux card.  The states are:
                         online, offline, empty, loopback or diag."
                ::= { fadmCPerfEntry 5 }

        fadmCPerfStatus  OBJECT-TYPE
                SYNTAX  CardStatus
                ACCESS  read-only
                STATUS  mandatory
                DESCRIPTION
                        "The status of the mux card.  This status represents
                         the status of the mux card and in general is
                         different from the status of the system."
                ::= { fadmCPerfEntry 6 }

        fadmCAvailTime   OBJECT-TYPE
                SYNTAX  Counter
                ACCESS  read-only
                STATUS  mandatory
                DESCRIPTION
                        "The number of seconds in this time slot (15 minutes)
                         that this Mux has been up and running.  This will
                         generally be the same as 15 minutes in seconds (900)."
                ::= { fadmCPerfEntry 7 }

        fadmCErrFreeSecs OBJECT-TYPE
                SYNTAX  Counter
                ACCESS  read-only
                STATUS  mandatory
                DESCRIPTION
                        "The number of seconds in this time slot (15 minutes)
                         that this mux has not experienced any alarms."
                ::= { fadmCPerfEntry 8 }

-- The elements in the oppmCond subgroup of the specialConditions


        oppmCNumEvents   OBJECT-TYPE
                SYNTAX  Counter
                ACCESS  read-only
                STATUS  mandatory
                DESCRIPTION
                        "Total number of all traps (events) generated by all
                         OPPMs' since this mode is started."
                ::= { oppmCond 1 }


        oppmCPerfTable   OBJECT-TYPE
                SYNTAX  SEQUENCE OF OppmCPerfEntry
                ACCESS  not-accessible
                STATUS  mandatory
                DESCRIPTION
                        "This table represents the information for performance
                         data collected for each oppm card"
                ::= { oppmCond 2 }

        oppmCPerfEntry   OBJECT-TYPE
                SYNTAX  OppmCPerfEntry
                ACCESS  not-accessible
                STATUS  mandatory
                DESCRIPTION
                        "Specifies the index for each row in the table below"
                INDEX { oppmCPerfLocation, oppmCPerfShelf, oppmCPerfSlot }
                ::= { oppmCPerfTable 1 }

        OppmCPerfEntry   ::=
                SEQUENCE {
                        oppmCPerfLocation  CardLocation,
                        oppmCPerfShelf     CardShelf,
                        oppmCPerfSlot      INTEGER,
                        oppmCPerfState     CardState,
                        oppmCPerfStatus    CardStatus,
                        oppmCAvailTime     Counter,
                        oppmCErrFreeSecs   Counter
                }

        oppmCPerfLocation  OBJECT-TYPE
                SYNTAX  CardLocation
                ACCESS  read-only
                STATUS  mandatory
                DESCRIPTION
                        "The location of the card.  Choices are local or
                         remote."
                ::= { oppmCPerfEntry 1 }

        oppmCPerfShelf   OBJECT-TYPE
                SYNTAX  CardShelf
                ACCESS  read-only
                STATUS  mandatory
                DESCRIPTION
                        "The shelf the card is in.  Valid values are: 1 to 10"
                ::= { oppmCPerfEntry 2 }

        oppmCPerfSlot    OBJECT-TYPE
                SYNTAX  CardSlot
                ACCESS  read-only
                STATUS  mandatory
                DESCRIPTION
                        "The slot within the shelf the card is in."
                ::= { oppmCPerfEntry 3 }

        oppmCPerfState   OBJECT-TYPE
                SYNTAX  CardState
                ACCESS  read-only
                STATUS  mandatory
                DESCRIPTION
                        "The status of the oppm card.  The states are:
                         online, offline, empty, loopback or diag."
                ::= { oppmCPerfEntry 4 }

        oppmCPerfStatus  OBJECT-TYPE
                SYNTAX  CardStatus
                ACCESS  read-only
                STATUS  mandatory
                DESCRIPTION
                        "The status of the oppm card.  This status represents
                         the status of the oppm card and in general is
                         different from the status of the system."
                ::= { oppmCPerfEntry 5 }

        oppmCAvailTime   OBJECT-TYPE
                SYNTAX  Counter
                ACCESS  read-only
                STATUS  mandatory
                DESCRIPTION
                        "The number of seconds in this time slot (15 minutes)
                         that this oppm has been up and running.  This will
                         generally be the same as 15 minutes in seconds (900)."
                ::= { oppmCPerfEntry 6 }

        oppmCErrFreeSecs OBJECT-TYPE
                SYNTAX  Counter
                ACCESS  read-only
                STATUS  mandatory
                DESCRIPTION
                        "The number of seconds in this time slot (15 minutes)
                         that this oppm has not experienced any alarms."
                ::= { oppmCPerfEntry 7 }

        oppmCCounterFlag   OBJECT-TYPE
                SYNTAX  FlagType
                ACCESS  read-write
                STATUS  mandatory
                DESCRIPTION
"Turns special condition software counters On or Off for this card. Default is off."
                ::= { oppmCond 3}


        -- The elements in the mcmCond subgroup of the specialConditions

        mcmCNumEvents    OBJECT-TYPE
                SYNTAX  Counter
                ACCESS  read-only
                STATUS  mandatory
                DESCRIPTION
                        "Total number of events received for all MCM's since
                         this mode was started."
                ::= { mcmCond 1 }

        mcmCCntrTable    OBJECT-TYPE
                SYNTAX  SEQUENCE OF McmCCntrEntry
                ACCESS  not-accessible
                STATUS  mandatory
                DESCRIPTION
                        "This table represents the information for each
                         entry for the software counters."
                ::= { mcmCond 2 }

        mcmCCntrEntry    OBJECT-TYPE
                SYNTAX  McmCCntrEntry
                ACCESS  not-accessible
                STATUS  mandatory
                DESCRIPTION
                        "Specifies the index for each row in the table below"
                INDEX { mcmCCntrLocation, mcmCCntrShelf, mcmCCntrSlot,
                        mcmCCntrType }
                ::= { mcmCCntrTable 1 }

        McmCCntrEntry    ::=
                SEQUENCE {
                        mcmCCntrLocation CardLocation,
                        mcmCCntrShelf    CardShelf,
                        mcmCCntrSlot     INTEGER,
                        mcmCCntrType     INTEGER,
                        mcmCCounterFlag  FlagType,
                        mcmCTotPktSent   Counter,
                        mcmCTotPktRcvd   Counter,
                        mcmCBadPktRcvd   Counter,
                        mcmCTotBadTrans  Counter,
                        mcmCBytesSent    Counter,
                        mcmCBytesRcvd    Counter,
                        mcmCMsgsDlvrd    Counter,
                        mcmCBufAllocFail Counter,
                        mcmCEcbAllocFail Counter,
				mcmCClearCntrs   ResetType 
                }

        mcmCCntrLocation OBJECT-TYPE
                SYNTAX  CardLocation
                ACCESS  read-only
                STATUS  mandatory
                DESCRIPTION
                        "The location of the MCM card.  The values are: Local
                         or Remote.  The system automatically determines the
                         right value for this entry based on the known
                         MCM cards."
                ::= { mcmCCntrEntry 1 }

        mcmCCntrShelf    OBJECT-TYPE
                SYNTAX  CardShelf
                ACCESS  read-only
                STATUS  mandatory
                DESCRIPTION
                        "The shelf the card is in.  Valid values are: 1 to 10.
                         The system automatically determines the right value
                         for this entry based on the known (available) MCM
                         cards."
                ::= { mcmCCntrEntry 2 }

        mcmCCntrSlot     OBJECT-TYPE
                SYNTAX  CardSlot
                ACCESS  read-only
                STATUS  mandatory
                DESCRIPTION
                        "The slot within the shelf the card is in.  The
                         system automatically determines the right value
                         for this entry based on the known (available)
                         MCM cards."
                ::= { mcmCCntrEntry 3 }

        mcmCCntrType     OBJECT-TYPE
                SYNTAX  INTEGER { spi(1), iwm(2) }
                ACCESS  read-only
                STATUS  mandatory
                DESCRIPTION
                        "The type of the software counter data in this row.
                         The data is collected for the SPI data channels."
                ::= { mcmCCntrEntry 4 }

        mcmCCounterFlag  OBJECT-TYPE
                SYNTAX  FlagType
                ACCESS  read-write
                STATUS  mandatory
                DESCRIPTION
                        "Turns software counters On or Off for this MCM."
                ::= { mcmCCntrEntry 5 }

        mcmCTotPktSent   OBJECT-TYPE
                SYNTAX  Counter
                ACCESS  read-only
                STATUS  mandatory
                DESCRIPTION
                        "The number of data packets sent over the given data
                         channel."
                ::= { mcmCCntrEntry 6 }

        mcmCTotPktRcvd   OBJECT-TYPE
                SYNTAX  Counter
                ACCESS  read-only
                STATUS  mandatory
                DESCRIPTION
                        "The number of data packets received over the given
                         data channel."
                ::= { mcmCCntrEntry 7 }

        mcmCBadPktRcvd   OBJECT-TYPE
                SYNTAX  Counter
                ACCESS  read-only
                STATUS  mandatory
                DESCRIPTION
                        "The number of bad data packets received over the given
                         data channel."
                ::= { mcmCCntrEntry 8 }

        mcmCTotBadTrans  OBJECT-TYPE
                SYNTAX  Counter
                ACCESS  read-only
                STATUS  mandatory
                DESCRIPTION
                        "The number of bad data transmissions over the given
                         data channel."
                ::= { mcmCCntrEntry 9 }

        mcmCBytesSent    OBJECT-TYPE
                SYNTAX  Counter
                ACCESS  read-only
                STATUS  mandatory
                DESCRIPTION
                        "Total number of bytes sent over the given
                         data channel."
                ::= { mcmCCntrEntry 10 }

        mcmCBytesRcvd    OBJECT-TYPE
                SYNTAX  Counter
                ACCESS  read-only
                STATUS  mandatory
                DESCRIPTION
                        "Total number of data bytes received over the given
                         data channel."
                ::= { mcmCCntrEntry 11 }

        mcmCMsgsDlvrd    OBJECT-TYPE
                SYNTAX  Counter
                ACCESS  read-only
                STATUS  mandatory
                DESCRIPTION
                        "The number of complete messages delivered over the
                         given data channel."
                ::= { mcmCCntrEntry 12 }

        mcmCBufAllocFail OBJECT-TYPE
                SYNTAX  Counter
                ACCESS  read-only
                STATUS  mandatory
                DESCRIPTION
                        "Number of buffer allocation failures for the given
                         data channel."
                ::= { mcmCCntrEntry 13 }

        mcmCEcbAllocFail OBJECT-TYPE
                SYNTAX  Counter
                ACCESS  read-only
                STATUS  mandatory
                DESCRIPTION
                        "Number of Event Control Block allocation failures
                         for the given data channel."
                ::= { mcmCCntrEntry 14 }
        mcmCClearCntrs    OBJECT-TYPE
                SYNTAX  ResetType
                ACCESS  read-write
                STATUS  mandatory
                DESCRIPTION
                        "If the value is reset, all software counters for this
                         15 minute interval are reset to zero.  A get on this
			 will always return other."
                ::= { mcmCCntrEntry 15 }

        mcmCPerfTable    OBJECT-TYPE
                SYNTAX  SEQUENCE OF McmCPerfEntry
                ACCESS  not-accessible
                STATUS  mandatory
                DESCRIPTION
                        "This table represents the information for performance
                         data collected for each channel card"
                ::= { mcmCond 3 }

        mcmCPerfEntry    OBJECT-TYPE
                SYNTAX  McmCPerfEntry
                ACCESS  not-accessible
                STATUS  mandatory
                DESCRIPTION
                        "Specifies the index for each row in the table below"
                INDEX { mcmCPerfLocation, mcmCPerfShelf, mcmCPerfSlot }
                ::= { mcmCPerfTable 1 }

        McmCPerfEntry    ::=
                SEQUENCE {
                        mcmCPerfLocation   CardLocation,
                        mcmCPerfShelf      CardShelf,
                        mcmCPerfSlot       INTEGER,
                        mcmCPerfState      CardState,
                        mcmCPerfStatus     CardStatus,
                        mcmCAvailTime      Counter,
                        mcmCErrFreeSecs    Counter,
                        mcmCBiasCurrent    INTEGER,
                        mcmCModulation     INTEGER,
                        mcmCApc            INTEGER,
                        mcmCIwmModulation  INTEGER,
                        mcmCLaserOnOff     FlagType,
                        mcmCTemperature    Gauge,
                        mcmCIntensity      Gauge,
                        mcmCSignalStrength Gauge,
                        mcmCLossOfLight    Boolean,
                        mcmCSignalDetect   Boolean,
                        mcmCRefClock       INTEGER,
                        mcmCClockDiv       INTEGER
                }

        mcmCPerfLocation OBJECT-TYPE
                SYNTAX  CardLocation
                ACCESS  read-only
                STATUS  mandatory
                DESCRIPTION
                        "The location of the card.  Valid choices are Local
                         or Remote.  The system automatically selects this
                         value based on the known (available) CC cards."
                ::= { mcmCPerfEntry 1 }

        mcmCPerfShelf    OBJECT-TYPE
                SYNTAX  CardShelf
                ACCESS  read-only
                STATUS  mandatory
                DESCRIPTION
                        "The shelf the card is in.  Valid values are: 1 to 10"
                ::= { mcmCPerfEntry 2 }

        mcmCPerfSlot     OBJECT-TYPE
                SYNTAX  CardSlot
                ACCESS  read-only
                STATUS  mandatory
                DESCRIPTION
                        "The slot within the shelf the card is in."
                ::= { mcmCPerfEntry 3 }

        mcmCPerfState    OBJECT-TYPE
                SYNTAX  CardState
                ACCESS  read-only
                STATUS  mandatory
                DESCRIPTION
                        "The state of the channel card.  The states'
                         are: online, offline, empty, loopback or diagnostics."
                ::= { mcmCPerfEntry 4 }

        mcmCPerfStatus   OBJECT-TYPE
                SYNTAX  CardStatus
                ACCESS  read-only
                STATUS  mandatory
                DESCRIPTION
                        "The status of the channel card.  This
                         status represents the status of the communication
                         processor and in general is different from the
                         status of the system."
                ::= { mcmCPerfEntry 5 }

        mcmCAvailTime    OBJECT-TYPE
                SYNTAX  Counter
                ACCESS  read-only
                STATUS  mandatory
                DESCRIPTION
                        "The number of seconds in this time slot (15 minutes)
                         that this CC has been up and running.  This will
                         generally be the same as 15 minutes in seconds (900)."
                ::= { mcmCPerfEntry 6 }

        mcmCErrFreeSecs  OBJECT-TYPE
                SYNTAX  Counter
                ACCESS  read-only
                STATUS  mandatory
                DESCRIPTION
                        "The number of seconds in this time slot (15 minutes)
                         that this MCM has not experienced any alarms."
                ::= { mcmCPerfEntry 7 }

        mcmCBiasCurrent  OBJECT-TYPE
                SYNTAX  INTEGER
                ACCESS  read-only
                STATUS  mandatory
                DESCRIPTION
                        "Bias current for the optical laser."
                ::= { mcmCPerfEntry 8 }

        mcmCModulation   OBJECT-TYPE
                SYNTAX  INTEGER
                ACCESS  read-only
                STATUS  mandatory
                DESCRIPTION
                        "The frequency modulation for the optical laser."
                ::= { mcmCPerfEntry 9 }

        mcmCApc          OBJECT-TYPE
                SYNTAX  INTEGER
                ACCESS  read-only
                STATUS  mandatory
                DESCRIPTION
                        "The APC value."
                ::= { mcmCPerfEntry 10 }

        mcmCIwmModulation  OBJECT-TYPE
                SYNTAX  INTEGER
                ACCESS  read-only
                STATUS  mandatory
                DESCRIPTION
                        "The frequency modulation for the IWM channel."
                ::= { mcmCPerfEntry 11 }

        mcmCLaserOnOff   OBJECT-TYPE
                SYNTAX  FlagType
                ACCESS  read-only
                STATUS  mandatory
                DESCRIPTION
                        "The laser On/Off flag."
                ::= { mcmCPerfEntry 12 }

        mcmCTemperature  OBJECT-TYPE
                SYNTAX  Gauge
                ACCESS  read-only
                STATUS  mandatory
                DESCRIPTION
                        "The current temperature, or the operating temperature
                         of the optical device."
                ::= { mcmCPerfEntry 13 }

        mcmCIntensity    OBJECT-TYPE
                SYNTAX  Gauge
                ACCESS  read-only
                STATUS  mandatory
                DESCRIPTION
                        "The intensity of the optical light."
                ::= { mcmCPerfEntry 14 }

        mcmCSignalStrength OBJECT-TYPE
                SYNTAX  Gauge
                ACCESS  read-only
                STATUS  mandatory
                DESCRIPTION
                        "The current signal strength for the optical path."
                ::= { mcmCPerfEntry 15 }

        mcmCLossOfLight  OBJECT-TYPE
                SYNTAX  Boolean
                ACCESS  read-only
                STATUS  mandatory
                DESCRIPTION
                        "If set to true, no laser light is present.  If set to
                         false, no loss of light has occurred."
                ::= { mcmCPerfEntry 16 }

        mcmCSignalDetect OBJECT-TYPE
                SYNTAX  Boolean
                ACCESS  read-only
                STATUS  mandatory
                DESCRIPTION
                        "If set to true, signal is detected.  If set to false,
                         no signal is present."
                ::= { mcmCPerfEntry 17 }

        mcmCRefClock     OBJECT-TYPE
                SYNTAX  INTEGER { 	en1660 (1),
    						en1944(2),
    						en1953(3)
				} 
                ACCESS  not-accessible
                STATUS  mandatory
                DESCRIPTION
                        "The value of the reference clock in decimal notation.
                         For a given value, like 1660, the actual value is
                         16.60-EN.  In otherwords, assume a two digit decimal
                         point, plus any appropriate scaling factor."
                ::= { mcmCPerfEntry 18 }

        mcmCClockDiv     OBJECT-TYPE
                SYNTAX  INTEGER { dout-1250(1), dout-622(2), dout-155(3) }
                ACCESS  not-accessible
                STATUS  mandatory
                DESCRIPTION
                        "The clock divisor.  Values are 1250, 622 or 155 in the
                         appropriate clock frequency scale."
                ::= { mcmCPerfEntry 19 }

        mcmPortCCntrTable        OBJECT-TYPE
                SYNTAX  SEQUENCE OF McmPortCCntrEntry
                ACCESS  not-accessible
                STATUS  mandatory
                DESCRIPTION
                        "This table represents the information for each
                         MCM port's current counters."
                ::= { mcmCond 4 }

        mcmPortCCntrEntry        OBJECT-TYPE
                SYNTAX  McmPortCCntrEntry
                ACCESS  not-accessible
                STATUS  mandatory
                DESCRIPTION
                        "Specifies the index for each row in the table below"
                INDEX { mcmPortCCntrCardLocation, mcmPortCCntrCardShelf,
                        mcmPortCCntrCardSlot,  mcmPortCCntrIndex }
                ::= { mcmPortCCntrTable 1 }

        McmPortCCntrEntry        ::=
                SEQUENCE {
                        mcmPortCCntrCardLocation 		CardLocation,
                        mcmPortCCntrCardShelf    		CardShelf,
                        mcmPortCCntrCardSlot     		INTEGER,
			mcmPortCCntrIndex  			INTEGER,
                        mcmPortCCntrASs		        	Counter,
		--	mcmPortCCntrFrameASs			Counter,
                        mcmPortCCntrFEs				Counter,
                        mcmPortCCntrCRCErrs			Counter,
			mcmPortCCntrSESs			Counter,
                        mcmPortCCntrSEFSs			Counter,
                        mcmPortCCntrUASs			Counter,
			mcmPortCCntrLESs			Counter,
                        mcmPortCCntrBESs			Counter,
                        mcmPortCCntrDMs				Counter,
			mcmPortCCntrLCVs			Counter
                }

        mcmPortCCntrCardLocation OBJECT-TYPE
                SYNTAX  CardLocation
                ACCESS  read-only
                STATUS  mandatory
                DESCRIPTION
                        "Location of the MCM port.  Valid values are:
			 Local in the same chassis, or remote to this
			 chassis"
                ::= { mcmPortCCntrEntry 1 }

        mcmPortCCntrCardShelf    OBJECT-TYPE
                SYNTAX  CardShelf
                ACCESS  read-only
                STATUS  mandatory
                DESCRIPTION
                        "The shelf the card is in.  Valid values
			 are: 2..3."
                ::= { mcmPortCCntrEntry 2 }

        mcmPortCCntrCardSlot     OBJECT-TYPE
                SYNTAX  CardSlot
                ACCESS  read-only
                STATUS  mandatory
                DESCRIPTION
                        "The slot within the shelf the Module is in."
                ::= { mcmPortCCntrEntry 3 }

        mcmPortCCntrIndex      OBJECT-TYPE
                SYNTAX  INTEGER 
                ACCESS  read-only
                STATUS  mandatory
                DESCRIPTION
                        "Port's index."
                ::= { mcmPortCCntrEntry 4 }

        mcmPortCCntrASs      OBJECT-TYPE
                SYNTAX  Counter 
                ACCESS  read-only
                STATUS  mandatory
                DESCRIPTION
                        "mcm port's ASs counter less than 15 mins."
                ::= { mcmPortCCntrEntry 5 }

        --mcmPortCCntrFrameASs      OBJECT-TYPE
        --        SYNTAX  Counter
        --        ACCESS  read-only
        --        STATUS  mandatory
        --        DESCRIPTION
        --                "MCM port's FrameASs counter less than 15 mins."
        --        ::= { mcmPortCCntrEntry 6 }

        mcmPortCCntrFEs      OBJECT-TYPE
                SYNTAX  Counter
                ACCESS  read-only
                STATUS  mandatory
                DESCRIPTION
                        "MCM port's FEs counter less than 15 mins." 
                ::= { mcmPortCCntrEntry 7 }

        mcmPortCCntrCRCErrs    OBJECT-TYPE
                SYNTAX  Counter
                ACCESS  read-only
                STATUS  mandatory
                DESCRIPTION
                        "MCM port's CRC errs counter less than 15 mins."
                ::= { mcmPortCCntrEntry 8 }

        mcmPortCCntrSESs      OBJECT-TYPE
                SYNTAX  Counter 
                ACCESS  read-only
                STATUS  mandatory
                DESCRIPTION
                        "mcm port's SESs counter less than 15 mins."
                ::= { mcmPortCCntrEntry 9 }

        mcmPortCCntrSEFSs      OBJECT-TYPE
                SYNTAX  Counter
                ACCESS  read-only
                STATUS  mandatory
                DESCRIPTION
                        "MCM port's SEFSs counter less than 15 mins."
                ::= { mcmPortCCntrEntry 10 }

        mcmPortCCntrUASs      OBJECT-TYPE
                SYNTAX  Counter
                ACCESS  read-only
                STATUS  mandatory
                DESCRIPTION
                        "MCM port's UASs counter less than 15 mins." 
                ::= { mcmPortCCntrEntry 11 }

        mcmPortCCntrLESs    OBJECT-TYPE
                SYNTAX  Counter
                ACCESS  read-only
                STATUS  mandatory
                DESCRIPTION
                        "MCM port's LESs counter less than 15 mins."
                ::= { mcmPortCCntrEntry 12 }

        mcmPortCCntrBESs    OBJECT-TYPE
                SYNTAX  Counter
                ACCESS  read-only
                STATUS  mandatory
                DESCRIPTION
                        "MCM port's BESs counter less than 15 mins."
                ::= { mcmPortCCntrEntry 13 }

        mcmPortCCntrDMs    OBJECT-TYPE
                SYNTAX  Counter
                ACCESS  read-only
                STATUS  mandatory
                DESCRIPTION
                        "MCM port's DMSs counter less than 15 mins."
                ::= { mcmPortCCntrEntry 14 }

        mcmPortCCntrLCVs    OBJECT-TYPE
                SYNTAX  Counter
                ACCESS  read-only
                STATUS  mandatory
                DESCRIPTION
                        "MCM port's LCVs counter less than 15 mins."
                ::= { mcmPortCCntrEntry 15 }

---------------

        -- The elements in the fnCond subgroup of the specialConditions subgroup

        fnCNumEvents     OBJECT-TYPE
                SYNTAX  Counter
                ACCESS  not-accessible 
                STATUS  mandatory
                DESCRIPTION
                        "Total number of all traps (events) generated by all
                         Fans since this mode is started."
                ::= { fnCond 1 }

        fnCPerfTable     OBJECT-TYPE
                SYNTAX  SEQUENCE OF FnCPerfEntry
                ACCESS  not-accessible
                STATUS  mandatory
                DESCRIPTION
                        "This table represents the information for performance
                         data collected for each fan module."
                ::= { fnCond 2 }

        fnCPerfEntry     OBJECT-TYPE
                SYNTAX  FnCPerfEntry
                ACCESS  not-accessible
                STATUS  mandatory
                DESCRIPTION
                        "Specifies the index for each row in the table below"
                INDEX { fnCPerfID }
                ::= { fnCPerfTable 1 }

        FnCPerfEntry     ::=
                SEQUENCE {
                        fnCPerfID	 INTEGER,
                        fnCPerfState     INTEGER,
                        fnCPerfStatus    CardStatus
                }

        fnCPerfID     OBJECT-TYPE
                SYNTAX  INTEGER
                ACCESS  not-accessible 
                STATUS  mandatory
                DESCRIPTION
                        "The module ID where the fan module is plugged in."
                ::= { fnCPerfEntry 1 }

        fnCPerfState     OBJECT-TYPE
                SYNTAX  INTEGER  { fnOK(1),
				   fnDegrade(2),
				   fnFailed(3),
				   fnEmpty(4)
				 }
                ACCESS  not-accessible 
                STATUS  mandatory
                DESCRIPTION
                        "The state of the fan module."
                ::= { fnCPerfEntry 2 }

        fnCPerfStatus    OBJECT-TYPE
                SYNTAX  CardStatus
                ACCESS  not-accessible 
                STATUS  mandatory
                DESCRIPTION
                        "The status of the fan module.  This status
                         represents the status of the fan module and in general is
                         different from the status of the system."
                ::= { fnCPerfEntry 3 }



-- The elements in the rpsmCond subgroup of the specialConditions


        rpsmCNumEvents   OBJECT-TYPE
                SYNTAX  Counter
                ACCESS  read-only
                STATUS  mandatory
                DESCRIPTION
                        "Total number of all traps (events) generated by all
                         RPSMs' since this mode is started."
                ::= { rpsmCond 1 }


        rpsmCPerfTable   OBJECT-TYPE
                SYNTAX  SEQUENCE OF RpsmCPerfEntry
                ACCESS  not-accessible
                STATUS  mandatory
                DESCRIPTION
                        "This table represents the information for performance
                         data collected for each rpsm card"
                ::= { rpsmCond 2 }

        rpsmCPerfEntry   OBJECT-TYPE
                SYNTAX  RpsmCPerfEntry
                ACCESS  not-accessible
                STATUS  mandatory
                DESCRIPTION
                        "Specifies the index for each row in the table below"
                INDEX { rpsmCPerfLocation, rpsmCPerfShelf, rpsmCPerfSlot }
                ::= { rpsmCPerfTable 1 }

        RpsmCPerfEntry   ::=
                SEQUENCE {
                        rpsmCPerfLocation  CardLocation,
                        rpsmCPerfShelf     CardShelf,
                        rpsmCPerfSlot      INTEGER,
                        rpsmCPerfState     CardState,
                        rpsmCPerfStatus    CardStatus,
                        rpsmCAvailTime     Counter,
                        rpsmCErrFreeSecs   Counter
                }

        rpsmCPerfLocation  OBJECT-TYPE
                SYNTAX  CardLocation
                ACCESS  read-only
                STATUS  mandatory
                DESCRIPTION
                        "The location of the card.  Choices are local or
                         remote."
                ::= { rpsmCPerfEntry 1 }

        rpsmCPerfShelf   OBJECT-TYPE
                SYNTAX  CardShelf
                ACCESS  read-only
                STATUS  mandatory
                DESCRIPTION
                        "The shelf the card is in.  Valid values are: 1 to 10"
                ::= { rpsmCPerfEntry 2 }

        rpsmCPerfSlot    OBJECT-TYPE
                SYNTAX  CardSlot
                ACCESS  read-only
                STATUS  mandatory
                DESCRIPTION
                        "The slot within the shelf the card is in."
                ::= { rpsmCPerfEntry 3 }

        rpsmCPerfState   OBJECT-TYPE
                SYNTAX  CardState
                ACCESS  read-only
                STATUS  mandatory
                DESCRIPTION
                        "The state of the rpsm card.  The states are:
                         online, offline, empty, loopback or diag."
                ::= { rpsmCPerfEntry 4 }

        rpsmCPerfStatus  OBJECT-TYPE
                SYNTAX  CardStatus
                ACCESS  read-only
                STATUS  mandatory
                DESCRIPTION
                        "The status of the rpsm card.  This status represents
                         the status of the rpsm card and in general is
                         different from the status of the system."
                ::= { rpsmCPerfEntry 5 }

        rpsmCAvailTime   OBJECT-TYPE
                SYNTAX  Counter
                ACCESS  read-only
                STATUS  mandatory
                DESCRIPTION
                        "The number of seconds in this time slot (15 minutes)
                         that this rpsm has been up and running.  This will
                         generally be the same as 15 minutes in seconds (900)."
                ::= { rpsmCPerfEntry 6 }

        rpsmCErrFreeSecs OBJECT-TYPE
                SYNTAX  Counter
                ACCESS  read-only
                STATUS  mandatory
                DESCRIPTION
                        "The number of seconds in this time slot (15 minutes)
                         that this rpsm has not experienced any alarms."
                ::= { rpsmCPerfEntry 7 }

        rpsmCCounterFlag   OBJECT-TYPE
                SYNTAX  FlagType
                ACCESS  read-write
                STATUS  mandatory
                DESCRIPTION
			"Turns special condition software counters On or
			 Off for this card. Default is off."
                ::= { rpsmCond 3}

-- The elements in the rsdmCond subgroup of the specialConditions

        rsdmCNumEvents   OBJECT-TYPE
                SYNTAX  Counter
                ACCESS  read-only
                STATUS  mandatory
                DESCRIPTION
                        "Total number of all traps (events) generated by all
                         RSDMs' since this mode is started."
                ::= { rsdmCond 1 }


        rsdmCPerfTable   OBJECT-TYPE
                SYNTAX  SEQUENCE OF RsdmCPerfEntry
                ACCESS  not-accessible
                STATUS  mandatory
                DESCRIPTION
                        "This table represents the information for performance
                         data collected for each oppm card"
                ::= { rsdmCond 2 }

        rsdmCPerfEntry   OBJECT-TYPE
                SYNTAX  RsdmCPerfEntry
                ACCESS  not-accessible
                STATUS  mandatory
                DESCRIPTION
                        "Specifies the index for each row in the table below"
                INDEX { rsdmCPerfLocation, rsdmCPerfShelf, rsdmCPerfSlot }
                ::= { rsdmCPerfTable 1 }

        RsdmCPerfEntry   ::=
                SEQUENCE {
                        rsdmCPerfLocation  CardLocation,
                        rsdmCPerfShelf     CardShelf,
                        rsdmCPerfSlot      INTEGER,
                        rsdmCPerfState     CardState,
                        rsdmCPerfStatus    CardStatus,
                        rsdmCAvailTime     Counter,
                        rsdmCErrFreeSecs   Counter
                }

        rsdmCPerfLocation  OBJECT-TYPE
                SYNTAX  CardLocation
                ACCESS  read-only
                STATUS  mandatory
                DESCRIPTION
                        "The location of the card.  Choices are local or
                         remote."
                ::= { rsdmCPerfEntry 1 }

        rsdmCPerfShelf   OBJECT-TYPE
                SYNTAX  CardShelf
                ACCESS  read-only
                STATUS  mandatory
                DESCRIPTION
                        "The shelf the card is in.  Valid values are: 1 to 10"
                ::= { rsdmCPerfEntry 2 }

        rsdmCPerfSlot    OBJECT-TYPE
                SYNTAX  CardSlot
                ACCESS  read-only
                STATUS  mandatory
                DESCRIPTION
                        "The slot within the shelf the card is in."
                ::= { rsdmCPerfEntry 3 }

        rsdmCPerfState   OBJECT-TYPE
                SYNTAX  CardState
                ACCESS  read-only
                STATUS  mandatory
                DESCRIPTION
                        "The state of the rsdm card.  The states are:
                         online, offline, empty, loopback or diag."
                ::= { rsdmCPerfEntry 4 }

        rsdmCPerfStatus  OBJECT-TYPE
                SYNTAX  CardStatus
                ACCESS  read-only
                STATUS  mandatory
                DESCRIPTION
                        "The status of the rsdm card.  This status represents
                         the status of the rsdm card and in general is
                         different from the status of the system."
                ::= { rsdmCPerfEntry 5 }

        rsdmCAvailTime   OBJECT-TYPE
                SYNTAX  Counter
                ACCESS  read-only
                STATUS  mandatory
                DESCRIPTION
                        "The number of seconds in this time slot (15 minutes)
                         that this rsdm has been up and running.  This will
                         generally be the same as 15 minutes in seconds (900)."
                ::= { rsdmCPerfEntry 6 }

        rsdmCErrFreeSecs OBJECT-TYPE
                SYNTAX  Counter
                ACCESS  read-only
                STATUS  mandatory
                DESCRIPTION
                        "The number of seconds in this time slot (15 minutes)
                         that this rsdm has not experienced any alarms."
                ::= { rsdmCPerfEntry 7 }

        rsdmCCounterFlag   OBJECT-TYPE
                SYNTAX  FlagType
                ACCESS  read-write
                STATUS  mandatory
                DESCRIPTION
			"Turns special condition software counters On
			 or Off for this card. Default is off."
                ::= { rsdmCond 3}

        -- The elements in the rtdmCond subgroup of the specialConditions

        rtdmCNumEvents   OBJECT-TYPE
                SYNTAX  Counter
                ACCESS  read-only
                STATUS  mandatory
                DESCRIPTION
                        "Total number of all traps (events) generated by all
                         RTDM's since this mode is started."
                ::= { rtdmCond 1 }


        rtdmCPerfTable   OBJECT-TYPE
                SYNTAX  SEQUENCE OF RtdmCPerfEntry
                ACCESS  not-accessible
                STATUS  mandatory
                DESCRIPTION
                        "This table represents the information for performance
                         data collected for each mux/demux card"
                ::= { rtdmCond 2 }

        rtdmCPerfEntry   OBJECT-TYPE
                SYNTAX  RtdmCPerfEntry
                ACCESS  not-accessible
                STATUS  mandatory
                DESCRIPTION
                        "Specifies the index for each row in the table below"
                INDEX { rtdmCPerfLocation, rtdmCPerfShelf, rtdmCPerfSlot }
                ::= { rtdmCPerfTable 1 }

        RtdmCPerfEntry   ::=
                SEQUENCE {
                        rtdmCPerfLocation  CardLocation,
                        rtdmCPerfShelf     CardShelf,
                        rtdmCPerfSlot      INTEGER,
                        rtdmCPerfState     CardState,
                        rtdmCPerfStatus    CardStatus,
                        rtdmCAvailTime     Counter,
                        rtdmCErrFreeSecs   Counter
                }

        rtdmCPerfLocation  OBJECT-TYPE
                SYNTAX  CardLocation
                ACCESS  read-only
                STATUS  mandatory
                DESCRIPTION
                        "The location of the card.  Choices are local or
                         remote."
                ::= { rtdmCPerfEntry 1 }

        rtdmCPerfShelf   OBJECT-TYPE
                SYNTAX  CardShelf
                ACCESS  read-only
                STATUS  mandatory
                DESCRIPTION
                        "The shelf the card is in.  Valid values are: 1 to 10"
                ::= { rtdmCPerfEntry 2 }

        rtdmCPerfSlot    OBJECT-TYPE
                SYNTAX  CardSlot
                ACCESS  read-only
                STATUS  mandatory
                DESCRIPTION
                        "The slot within the shelf the card is in."
                ::= { rtdmCPerfEntry 3 }

        rtdmCPerfState   OBJECT-TYPE
                SYNTAX  CardState
                ACCESS  read-only
                STATUS  mandatory
                DESCRIPTION
                        "The status of the mux card.  The states are:
                         online, offline, empty, loopback or diag."
                ::= { rtdmCPerfEntry 4 }

        rtdmCPerfStatus  OBJECT-TYPE
                SYNTAX  CardStatus
                ACCESS  read-only
                STATUS  mandatory
                DESCRIPTION
                        "The status of the mux card.  This status represents
                         the status of the mux card and in general is
                         different from the status of the system."
                ::= { rtdmCPerfEntry 5 }

        rtdmCAvailTime   OBJECT-TYPE
                SYNTAX  Counter
                ACCESS  read-only
                STATUS  mandatory
                DESCRIPTION
                        "The number of seconds in this time slot (15 minutes)
                         that this Mux has been up and running.  This will
                         generally be the same as 15 minutes in seconds (900)."
                ::= { rtdmCPerfEntry 6 }

        rtdmCErrFreeSecs OBJECT-TYPE
                SYNTAX  Counter
                ACCESS  read-only
                STATUS  mandatory
                DESCRIPTION
                        "The number of seconds in this time slot (15 minutes)
                         that this mux has not experienced any alarms."
                ::= { rtdmCPerfEntry 7 }

        rtdmCCounterFlag   OBJECT-TYPE
                SYNTAX  FlagType
                ACCESS  read-write
                STATUS  mandatory
                DESCRIPTION
                        "Turns special condition software counters On or Off
			 for this card. Default is off."
                ::= { rtdmCond 3}


        -- The elements in the osamCond subgroup of the specialConditions

        osamCNumEvents   OBJECT-TYPE
                SYNTAX  Counter
                ACCESS  read-only
                STATUS  mandatory
                DESCRIPTION
                        "Total number of events received for all osam's since
                         this mode was started."
                ::= { osamCond 1 }

        osamCPerfTable   OBJECT-TYPE
                SYNTAX  SEQUENCE OF OsamCPerfEntry
                ACCESS  not-accessible
                STATUS  mandatory
                DESCRIPTION
                        "This table represents the information for 
                         special conditions performance data collected for 
                         each osam module."
                ::= { osamCond 2 }

        osamCPerfEntry   OBJECT-TYPE
                SYNTAX  OsamCPerfEntry
                ACCESS  not-accessible
                STATUS  mandatory
                DESCRIPTION
                        "Specifies the index for each row in the table below"
                INDEX { osamCPerfLocation, osamCPerfShelf, osamCPerfSlot }
                ::= { osamCPerfTable 1 }

        OsamCPerfEntry   ::=
                SEQUENCE {
                        osamCPerfLocation           CardLocation,
                        osamCPerfShelf              CardShelf,
                        osamCPerfSlot               INTEGER,
                        osamCPerfState              CardState,
                        osamCPerfStatus             CardStatus,
                        osamCPerfAvailTime          Counter,
                        osamCPerfErrFreeSecs        Counter
                }

        osamCPerfLocation  OBJECT-TYPE
                SYNTAX  CardLocation
                ACCESS  read-only
                STATUS  mandatory
                DESCRIPTION
                        "Location of the module."
                ::= { osamCPerfEntry 1 }

        osamCPerfShelf   OBJECT-TYPE
                SYNTAX  CardShelf
                ACCESS  read-only
                STATUS  mandatory
                DESCRIPTION
                        "The shelf number in which the module is plugged in."
                ::= { osamCPerfEntry 2 }

        osamCPerfSlot    OBJECT-TYPE
                SYNTAX  INTEGER (1..16)
                ACCESS  read-only
                STATUS  mandatory
                DESCRIPTION
                        "The slot number in which the module is plugged in."
                ::= { osamCPerfEntry 3 }

        osamCPerfState   OBJECT-TYPE
                SYNTAX  CardState
                ACCESS  read-only
                STATUS  mandatory
                DESCRIPTION
                        "The current state of the module."
                ::= { osamCPerfEntry 4 }

        osamCPerfStatus  OBJECT-TYPE
                SYNTAX  CardStatus
                ACCESS  read-only
                STATUS  mandatory
                DESCRIPTION
                        "The current alarm status of the channel."
                ::= { osamCPerfEntry 5 }

        osamCPerfAvailTime   OBJECT-TYPE
                SYNTAX  Counter
                ACCESS  read-only
                STATUS  mandatory
                DESCRIPTION
                        "The number of seconds since the start of this mode
                         that this module has been up and running."
                ::= { osamCPerfEntry 6 }

        osamCPerfErrFreeSecs OBJECT-TYPE
                SYNTAX  Counter
                ACCESS  read-only
                STATUS  mandatory
                DESCRIPTION
                        "The number of seconds since the start of this mode
                         that this module has been experienced any alarms."
                ::= { osamCPerfEntry 7 }

        osamCPerfCounterFlag   OBJECT-TYPE
                SYNTAX  FlagType
                ACCESS  read-write
                STATUS  mandatory
                DESCRIPTION
                        "Turns osam special condition software counters on
			 and off. Default is off."
                ::= { osamCond 3}

-- The elements in the rsmCond subgroup of the specialConditions

        rsmCNumEvents   OBJECT-TYPE
                SYNTAX  Counter
                ACCESS  read-only
                STATUS  mandatory
                DESCRIPTION
                        "Total number of all traps (events) generated by all
                         RSMs' since this mode is started."
                ::= { rsmCond 1 }


        rsmCPerfTable   OBJECT-TYPE
                SYNTAX  SEQUENCE OF RsmCPerfEntry
                ACCESS  not-accessible
                STATUS  mandatory
                DESCRIPTION
                        "This table represents the information for performance
                         data collected for each rsm card"
                ::= { rsmCond 2 }

        rsmCPerfEntry   OBJECT-TYPE
                SYNTAX  RsmCPerfEntry
                ACCESS  not-accessible
                STATUS  mandatory
                DESCRIPTION
                        "Specifies the index for each row in the table below"
                INDEX { rsmCPerfLocation, rsmCPerfShelf, rsmCPerfSlot }
                ::= { rsmCPerfTable 1 }

        RsmCPerfEntry   ::=
                SEQUENCE {
                        rsmCPerfLocation  CardLocation,
                        rsmCPerfShelf     CardShelf,
                        rsmCPerfSlot      CardSlot,
                        rsmCPerfState     CardState,
                        rsmCPerfStatus    CardStatus,
                        rsmCAvailTime     Counter,
                        rsmCErrFreeSecs   Counter
                }

        rsmCPerfLocation  OBJECT-TYPE
                SYNTAX  CardLocation
                ACCESS  read-only
                STATUS  mandatory
                DESCRIPTION
                        "The location of the card."
                ::= { rsmCPerfEntry 1 }

        rsmCPerfShelf   OBJECT-TYPE
                SYNTAX  CardShelf
                ACCESS  read-only
                STATUS  mandatory
                DESCRIPTION
                        "The shelf the card is in."
                ::= { rsmCPerfEntry 2 }

        rsmCPerfSlot    OBJECT-TYPE
                SYNTAX  CardSlot
                ACCESS  read-only
                STATUS  mandatory
                DESCRIPTION
                        "The slot within the shelf the card is in."
                ::= { rsmCPerfEntry 3 }

        rsmCPerfState   OBJECT-TYPE
                SYNTAX  CardState
                ACCESS  read-only
                STATUS  mandatory
                DESCRIPTION
                        "The state of the rsm card.  The states are:
                         online, offline, empty, loopback or diag."
                ::= { rsmCPerfEntry 4 }

        rsmCPerfStatus  OBJECT-TYPE
                SYNTAX  CardStatus
                ACCESS  read-only
                STATUS  mandatory
                DESCRIPTION
                        "The status of the rsm card.  This status represents
                         the status of the rsm card and in general is
                         different from the status of the system."
                ::= { rsmCPerfEntry 5 }

        rsmCAvailTime   OBJECT-TYPE
                SYNTAX  Counter
                ACCESS  read-only
                STATUS  mandatory
                DESCRIPTION
                        "The number of seconds in this time slot (15 minutes)
                         that this rsm has been up and running.  This will
                         generally be the same as 15 minutes in seconds (900)."
                ::= { rsmCPerfEntry 6 }

        rsmCErrFreeSecs OBJECT-TYPE
                SYNTAX  Counter
                ACCESS  read-only
                STATUS  mandatory
                DESCRIPTION
                        "The number of seconds in this time slot (15 minutes)
                         that this rsm has not experienced any alarms."
                ::= { rsmCPerfEntry 7 }

        rsmCCounterFlag	OBJECT-TYPE
                SYNTAX  FlagType
                ACCESS  read-write
                STATUS  mandatory
                DESCRIPTION
			"Turns special condition software counters On
			 or Off for this card. Default is off."
                ::= { rsmCond 3}

-- The elements in the upsmCond subgroup of the specialConditions

        upsmCNumEvents   OBJECT-TYPE
                SYNTAX  Counter
                ACCESS  read-only
                STATUS  mandatory
                DESCRIPTION
                        "Total number of all traps (events) generated by all
                         UPSMs' since this mode is started."
                ::= { upsmCond 1 }


        upsmCPerfTable   OBJECT-TYPE
                SYNTAX  SEQUENCE OF UpsmCPerfEntry
                ACCESS  not-accessible
                STATUS  mandatory
                DESCRIPTION
                        "This table represents the information for performance
                         data collected for each upsm card"
                ::= { upsmCond 2 }

        upsmCPerfEntry   OBJECT-TYPE
                SYNTAX  UpsmCPerfEntry
                ACCESS  not-accessible
                STATUS  mandatory
                DESCRIPTION
                        "Specifies the index for each row in the table below"
                INDEX { upsmCPerfLocation, upsmCPerfShelf, upsmCPerfSlot }
                ::= { upsmCPerfTable 1 }

        UpsmCPerfEntry   ::=
                SEQUENCE {
                        upsmCPerfLocation	CardLocation,
                        upsmCPerfShelf		CardShelf,
                        upsmCPerfSlot		CardSlot,
                        upsmCPerfState		CardState,
                        upsmCPerfStatus		CardStatus,
                        upsmCAvailTime		Counter,
                        upsmCErrFreeSecs	Counter
                }

        upsmCPerfLocation  OBJECT-TYPE
                SYNTAX  CardLocation
                ACCESS  read-only
                STATUS  mandatory
                DESCRIPTION
                        "The location of the card."
                ::= { upsmCPerfEntry 1 }

        upsmCPerfShelf	OBJECT-TYPE
                SYNTAX  CardShelf
                ACCESS  read-only
                STATUS  mandatory
                DESCRIPTION
                        "The shelf the card is in."
                ::= { upsmCPerfEntry 2 }

        upsmCPerfSlot    OBJECT-TYPE
                SYNTAX  CardSlot
                ACCESS  read-only
                STATUS  mandatory
                DESCRIPTION
                        "The slot within the shelf the card is in."
                ::= { upsmCPerfEntry 3 }

        upsmCPerfState   OBJECT-TYPE
                SYNTAX  CardState
                ACCESS  read-only
                STATUS  mandatory
                DESCRIPTION
                        "The state of the upsm card.  The states are:
                         online, offline, empty, loopback or diag."
                ::= { upsmCPerfEntry 4 }

        upsmCPerfStatus	OBJECT-TYPE
                SYNTAX  CardStatus
                ACCESS  read-only
                STATUS  mandatory
                DESCRIPTION
                        "The status of the upsm card.  This status represents
                         the status of the upsm card and in general is
                         different from the status of the system."
                ::= { upsmCPerfEntry 5 }

        upsmCAvailTime	OBJECT-TYPE
                SYNTAX  Counter
                ACCESS  read-only
                STATUS  mandatory
                DESCRIPTION
                        "The number of seconds in this time slot (15 minutes)
                         that this upsm has been up and running.  This will
                         generally be the same as 15 minutes in seconds (900)."
                ::= { upsmCPerfEntry 6 }

        upsmCErrFreeSecs OBJECT-TYPE
                SYNTAX  Counter
                ACCESS  read-only
                STATUS  mandatory
                DESCRIPTION
                        "The number of seconds in this time slot (15 minutes)
                         that this upsm has not experienced any alarms."
                ::= { upsmCPerfEntry 7 }

        upsmCCounterFlag   OBJECT-TYPE
                SYNTAX  FlagType
                ACCESS  read-write
                STATUS  mandatory
                DESCRIPTION
			"Turns special condition software counters On
			 or Off for this card. Default is off."
                ::= { upsmCond 3}


        -- The elements in the eventLog subgroup of the traps

        eveTrapThreshold OBJECT-TYPE
                SYNTAX  INTEGER
                ACCESS  not-accessible
                STATUS  mandatory
                DESCRIPTION
                        "Threshold before events of the same type are no longer
                         sent. Default can be a number as small as 1."
                ::= { eventLog 1 }

        eveNumEvents    OBJECT-TYPE
                SYNTAX  EventBuffer
                ACCESS  read-only
                STATUS  mandatory
                DESCRIPTION
                        "Number of events logged in the table below.  This
                         counter is automatically set by the software."
                ::= { eventLog 2 }

        eveLogTable     OBJECT-TYPE
                SYNTAX  SEQUENCE OF EveLogEntry
                ACCESS  not-accessible
                STATUS  mandatory
                DESCRIPTION
                        "This table represents the information for the
			 event log buffer.  There are a maximum of 1000
			 entries in the event log.  The events are kept
			 in a circular buffer fashion with eveSeqNum
			 going from 1 to 9999."
                ::= { eventLog 3 }

        eveLogEntry     OBJECT-TYPE
                SYNTAX  EveLogEntry
                ACCESS  not-accessible
                STATUS  mandatory
                DESCRIPTION
                        "Specifies the index for each row in the table below"
                INDEX { eveDateTime, eveSeqNum }
                ::= { eveLogTable 1 }

        EveLogEntry     ::=
                SEQUENCE {
                        eveDateTime     DateAndTime,
                        eveEventId      INTEGER,
                        eveSeverity     TrapStatus,
                        eveSysStatus    CardStatus,
                        eveSource       DisplayString,
                        eveDescr        DisplayString,
                        eveTrap         Boolean,
                        eveSeqNum       INTEGER

                }

        eveDateTime     OBJECT-TYPE
                SYNTAX  DateAndTime
                ACCESS  read-only
                STATUS  mandatory
                DESCRIPTION
                        "The date and time of the event logged in the buffer"
                ::= { eveLogEntry 1 }

        eveEventId      OBJECT-TYPE
                SYNTAX  INTEGER (0..9999)
                ACCESS  read-only
                STATUS  mandatory
                DESCRIPTION
                        "The event ID assigned to this event."
                ::= { eveLogEntry 2 }

        eveSeverity     OBJECT-TYPE
                SYNTAX  TrapStatus
                ACCESS  read-only
                STATUS  mandatory
                DESCRIPTION
                        "The severity of this event.  Could be critical, major,
                         minor, or normal (informational)."
                ::= { eveLogEntry 3 }

        eveSysStatus    OBJECT-TYPE
                SYNTAX  CardStatus
                ACCESS  read-only
                STATUS  mandatory
                DESCRIPTION
                        "The current status of the system.  Could be critical,
                         major, minor, or normal (informational)."
                ::= { eveLogEntry 4 }

        eveSource       OBJECT-TYPE
                SYNTAX  DisplayString (SIZE (0..152))
                ACCESS  read-only
                STATUS  mandatory
                DESCRIPTION
                        "A five to seven tuple string composed of the
			 following items: System Name:card type (MPM,
			 OCMITU, OFCM, etc.). location (L for local,
			 R[number] for remote with optional station number).
			 shelf #. slot id[. port #][:link name(optional
			 depending on card type)] [:ring name(optional)] [:path name(optional)].
			 When an event applies to all slots of the whole
			 chassis, 0 will be displayed for both shelf and slot.
			 Example: SystemInSunnyvale:OCMITU.L.1.6:ITU23"
                ::= { eveLogEntry 5 }

        eveDescr        OBJECT-TYPE
                SYNTAX  DisplayString (SIZE (0..100))
                ACCESS  read-only
                STATUS  mandatory
                DESCRIPTION
                        "A string signifying the cause of the error in natural
                         language (preferrably English) format."
                ::= { eveLogEntry 6 }

        eveTrap         OBJECT-TYPE
                SYNTAX  Boolean
                ACCESS  read-only
                STATUS  mandatory
                DESCRIPTION
                        "If set to True, this event was sent as a trap.  If
                         set to False, this event was merely logged and not
                         sent as a trap."
                ::= { eveLogEntry 7 }

        eveSeqNum      OBJECT-TYPE
                SYNTAX  INTEGER (0..9999)
                ACCESS  read-only
                STATUS  mandatory
                DESCRIPTION
                        "The unique sequence number for this event entry in
                         the event log."
                ::= { eveLogEntry 8 }

        eveDeleteLog    OBJECT-TYPE
                SYNTAX  ResetType
                ACCESS  read-write
                STATUS  mandatory
                DESCRIPTION
                        "If the value is reset, the event log table of the
                         active cp is deleted - meaning all the log entries
                         are flushed!!"
                ::= { eventLog 4 }

        eveLastEntryDateTime    OBJECT-TYPE
                SYNTAX  DateAndTime
                ACCESS  read-only
                STATUS  mandatory
                DESCRIPTION
                        "Date and time stamp of the last event log entry.  This
                         provides quick access into the last event log entry."
                ::= { eventLog 5 }

        eveHundredthEntryDateTime    OBJECT-TYPE
                SYNTAX  DateAndTime
                ACCESS  read-only
                STATUS  mandatory
                DESCRIPTION
                        "Date and time stamp of the most recent 100th event
                         log entry.  This provides quick access into
                         retrieving the most recent 100 event log entries.
                         If less than 100 entries exist in the event log,
                         the return value contains all zeroes."
                ::= { eventLog 6 }

        eveTwoHundredthEntryDateTime    OBJECT-TYPE
                SYNTAX  DateAndTime
                ACCESS  read-only
                STATUS  mandatory
                DESCRIPTION
                        "Date and time stamp of the most recent 200th event
                         log entry.  This provides quick access into
                         retrieving the most recent 200 event log entries.
                         If less than 200 entries exist in the event log,
                         the return value contains all zeroes."
                ::= { eventLog 7 }


        eveThreeHundredthEntryDateTime    OBJECT-TYPE
                SYNTAX  DateAndTime
                ACCESS  read-only
                STATUS  mandatory
                DESCRIPTION
                        "Date and time stamp of the most recent 300th event
                         log entry.  This provides quick access into
                         retrieving the most recent 300 event log entries.
                         If less than 300 entries exist in the event log,
                         the return value contains all zeroes."
                ::= { eventLog 8 }


        eveFourHundredthEntryDateTime    OBJECT-TYPE
                SYNTAX  DateAndTime
                ACCESS  read-only
                STATUS  mandatory
                DESCRIPTION
                        "Date and time stamp of the most recent 400th event
                         log entry.  This provides quick access into
                         retrieving the most recent 400 event log entries.
                         If less than 400 entries exist in the event log,
                         the return value contains all zeroes."
                ::= { eventLog 9 }


        eveFiveHundredthEntryDateTime    OBJECT-TYPE
                SYNTAX  DateAndTime
                ACCESS  read-only
                STATUS  mandatory
                DESCRIPTION
                        "Date and time stamp of the most recent 500th event
                         log entry.  This provides quick access into
                         retrieving the most recent 500 event log entries.
                         If less than 500 entries exist in the event log,
                         the return value contains all zeroes."
                ::= { eventLog 10 }


        eveSixHundredthEntryDateTime    OBJECT-TYPE
                SYNTAX  DateAndTime
                ACCESS  read-only
                STATUS  mandatory
                DESCRIPTION
                        "Date and time stamp of the most recent 600th event
                         log entry.  This provides quick access into
                         retrieving the most recent 600 event log entries.
                         If less than 600 entries exist in the event log,
                         the return value contains all zeroes."
                ::= { eventLog 11 }

        eveSevenHundredthEntryDateTime    OBJECT-TYPE
                SYNTAX  DateAndTime
                ACCESS  read-only
                STATUS  mandatory
                DESCRIPTION
                        "Date and time stamp of the most recent 700th event
                         log entry.  This provides quick access into
                         retrieving the most recent 700 event log entries.
                         If less than 700 entries exist in the event log,
                         the return value contains all zeroes."
                ::= { eventLog 12 }

		eveEightHundredthEntryDateTime    OBJECT-TYPE
                SYNTAX  DateAndTime
                ACCESS  read-only
                STATUS  mandatory
                DESCRIPTION
                        "Date and time stamp of the most recent 800th event
                         log entry.  This provides quick access into
                         retrieving the most recent 800 event log entries.
                         If less than 800 entries exist in the event log,
                         the return value contains all zeroes."
                ::= { eventLog 13 }

		eveNineHundredthEntryDateTime    OBJECT-TYPE
                SYNTAX  DateAndTime
                ACCESS  read-only
                STATUS  mandatory
                DESCRIPTION
                        "Date and time stamp of the most recent 900th event
                         log entry.  This provides quick access into
                         retrieving the most recent 900 event log entries.
                         If less than 900 entries exist in the event log,
                         the return value contains all zeroes."
                ::= { eventLog 14 }


        -- The elements in the userLog subgroup of the traps

        usrNumLogs      OBJECT-TYPE
                SYNTAX  UserBuffer
                ACCESS  read-only
                STATUS  mandatory
                DESCRIPTION
                        "Number of user events logged in the table below.  This
                         counter is automatically set by the software."
                ::= { userLog 1 }

        usrLogTable     OBJECT-TYPE
                SYNTAX  SEQUENCE OF UsrLogEntry
                ACCESS  not-accessible
                STATUS  mandatory
                DESCRIPTION
                        "This table represents the information for user event
                         log buffer"
                ::= { userLog 2 }

        usrLogEntry     OBJECT-TYPE
                SYNTAX  UsrLogEntry
                ACCESS  not-accessible
                STATUS  mandatory
                DESCRIPTION
                        "Specifies the index for each row in the table below"
                INDEX { usrDateTime, usrLogonId }
                ::= { usrLogTable 1 }

        UsrLogEntry     ::=
                SEQUENCE {
                        usrDateTime     DateAndTime,
                        usrLogonId      LogonID,
                        usrTarget       DisplayString (SIZE (0..30)),
                        usrLogDescr     DisplayString (SIZE (0..100)),
                        usrTrap         Boolean
                }

        usrDateTime     OBJECT-TYPE
                SYNTAX  DateAndTime
                ACCESS  read-only
                STATUS  mandatory
                DESCRIPTION
                        "The date and time of the event logged in the buffer"
                ::= { usrLogEntry 1 }

        usrLogonId      OBJECT-TYPE
                SYNTAX  LogonID
                ACCESS  read-only
                STATUS  mandatory
                DESCRIPTION
                        "The Logon ID of the user causing this event to be
                         logged."
                ::= { usrLogEntry 2 }

        usrTarget       OBJECT-TYPE
                SYNTAX  DisplayString (SIZE (0..30))
                ACCESS  read-only
                STATUS  mandatory
                DESCRIPTION
                        "A four tuple string composed of the following items:
                         location (remote or local), type (cp, cc, mux or ps),
                         shelf, and slot id.  The tuples are separated by
                         comma.  Example: local,cp,b,1.  This column identifies
                         which subsystem was affected by the user action."
                ::= { usrLogEntry 3 }

        usrLogDescr     OBJECT-TYPE
                SYNTAX  DisplayString (SIZE (0..100))
                ACCESS  read-only
                STATUS  mandatory
                DESCRIPTION
                        "A string signifying the action logged in natural
                         language (preferrably English) format."
                ::= { usrLogEntry 4 }

        usrTrap         OBJECT-TYPE
                SYNTAX  Boolean
                ACCESS  read-only
                STATUS  mandatory
                DESCRIPTION
                        "If set to True, this user event was sent as a trap.
                         If set to False, this event was merely logged and not
                         sent as a trap."
                ::= { usrLogEntry 5 }

        -- The elements in the alarmLog subgroup of the faults group


        alarmNumEvents    OBJECT-TYPE
                SYNTAX  INTEGER(0..300)
                ACCESS  read-only
                STATUS  mandatory
                DESCRIPTION
                        "Number of alarms logged in the table below.  This
                         counter is automatically set by the software. The max
			 is 300 entries."
                ::= { alarmLog 1}

        alarmLogTable     OBJECT-TYPE
                SYNTAX  SEQUENCE OF AlarmLogEntry
                ACCESS  not-accessible
                STATUS  mandatory
                DESCRIPTION
                        "This table represents the information for the alarm
                         log buffer"
                ::= { alarmLog 2 }

	alarmLogEntry     OBJECT-TYPE
                SYNTAX  AlarmLogEntry
                ACCESS  not-accessible
                STATUS  mandatory
                DESCRIPTION
                        "Specifies the index for each row in the table below"
                INDEX { alarmFirstDateTime, alarmTag }
                ::= { alarmLogTable 1 }

        AlarmLogEntry     ::=
                SEQUENCE {
			alarmFirstDateTime	DateAndTime,
			alarmTag		INTEGER,
			alarmLastDateTime	DateAndTime,
			alarmEventId		INTEGER,
			alarmSeverity		INTEGER,
			alarmSource		DisplayString,
			alarmDescr		DisplayString,
			alarmCnt		INTEGER,
			alarmAck		INTEGER,
			alarmClear		INTEGER
		}

        alarmFirstDateTime     OBJECT-TYPE
                SYNTAX  DateAndTime
                ACCESS  read-only
                STATUS  mandatory
                DESCRIPTION
                        "The date and time for the first alarm occurrence."
                ::= { alarmLogEntry 1 }

        alarmTag     OBJECT-TYPE
                SYNTAX  INTEGER(1..999)
                ACCESS  read-only
                STATUS  mandatory
                DESCRIPTION
                        "A unique tag used to identify the alarm entry."
                ::= { alarmLogEntry 2 }

        alarmLastDateTime     OBJECT-TYPE
                SYNTAX  DateAndTime
                ACCESS  read-only
                STATUS  mandatory
                DESCRIPTION
                        "The date and time for the most recent alarm occurrence.
			 If this is the first time occurrence, it would be same
			 as alarmFirstDateTime."
                ::= { alarmLogEntry 3 }

        alarmEventId      OBJECT-TYPE
                SYNTAX  INTEGER (0..9999)
                ACCESS  read-only
                STATUS  mandatory
                DESCRIPTION
                        "The event ID assigned to this alarm."
                ::= { alarmLogEntry 4 }

        alarmSeverity     OBJECT-TYPE
                SYNTAX  INTEGER{
				 critical(1),
				 major(2),
				 minor(3)
				}
                ACCESS  read-only
                STATUS  mandatory
                DESCRIPTION
                        "The severity of this alarm.  Could be critical, major,
                         or minor."
                ::= { alarmLogEntry 5 }


        alarmSource       OBJECT-TYPE
                SYNTAX  DisplayString (SIZE (0..152))
                ACCESS  read-only
                STATUS  mandatory
                DESCRIPTION
                        "A five to seven tuple string composed of the
			 following items: System Name:card type (MPM,
			 OCMITU, OFCM, etc.). location (L for local,
			 R[number] for remote with optional station number).
			 shelf #. slot id[. port #][:link name(optional
			 depending on card type)][:ring name (optional)]
			 [:pathname(optional)].
			 When an event applies to all slots of the whole
			 chassis, 0 will be displayed for both shelf and slot.
			 Example: SystemInSunnyvale:OCMITU.L.1.6:ITU23"
                ::= { alarmLogEntry 6 }

        alarmDescr        OBJECT-TYPE
                SYNTAX  DisplayString (SIZE (0..100))
                ACCESS  read-only
                STATUS  mandatory
                DESCRIPTION
                        "A string signifying the cause of the error in natural
                         language (preferrably English) format."
                ::= { alarmLogEntry 7 }

	alarmCnt        OBJECT-TYPE
                SYNTAX  INTEGER
                ACCESS  read-only
                STATUS  mandatory
                DESCRIPTION
                        "Number of times alarm has occurred(from the same source)."
                ::= { alarmLogEntry 8 }

	alarmAck      OBJECT-TYPE
                SYNTAX  INTEGER {
				  acknowledged(1),
				  unacknowledged(2)
				}
                ACCESS  read-write
                STATUS  mandatory
                DESCRIPTION
                        "Acknowledge or unacknowledge the active alarm. Ack will
			 remove its contribution to the external dry contact alarm
			 closure. Default is unacknowledged."
                ::= { alarmLogEntry  9 }

	alarmClear      OBJECT-TYPE
                SYNTAX  INTEGER {
				  other(1),
				  clear(2)
				}
                ACCESS  read-write
                STATUS  mandatory
                DESCRIPTION
                        "An action to clear the alarm from the alarm log. If
			 alarm persists, another alarm will be sent. A GET
			 operation would always return other(1)."
                ::= { alarmLogEntry  10 }

        alarmLastChange    OBJECT-TYPE
                SYNTAX  INTEGER
                ACCESS  read-only
                STATUS  mandatory
                DESCRIPTION
                        "Time ticks in microseconds of when the last change
			 was made to the alarm log.  This includes ack/unack,
			 clear, and alarm addition/deletion."
                ::= { alarmLog 3}



        -- The elements in the diagnostics subgroup of the traps

        diagModeNum     OBJECT-TYPE
                SYNTAX  INTEGER (0..128)
                ACCESS  read-only
                STATUS  mandatory
                DESCRIPTION
                        "Number of cards in diagnostics mode in the table
                         below.  This counter is automatically set by the
                         software."
                ::= { diagnostics 1 }

        diagModeTable   OBJECT-TYPE
                SYNTAX  SEQUENCE OF DiagModeEntry
                ACCESS  not-accessible
                STATUS  mandatory
                DESCRIPTION
                        "This table represents the information for each card
                         in diagnostics mode."
                ::= { diagnostics 2 }

        diagModeEntry   OBJECT-TYPE
                SYNTAX  DiagModeEntry
                ACCESS  not-accessible
                STATUS  mandatory
                DESCRIPTION
                        "Specifies the index for each row in the table below"
                INDEX { diagLocation, diagShelf, diagSlot }
                ::= { diagModeTable 1 }

        DiagModeEntry   ::=
                SEQUENCE {
                        diagLocation    CardLocation,
                        diagShelf       CardShelf,
                        diagSlot        INTEGER,
                        diagSetMode     INTEGER
                }

        diagLocation    OBJECT-TYPE
                SYNTAX  CardLocation
                ACCESS  read-only 
                STATUS  mandatory
                DESCRIPTION
                        "The location of the card: local or remote"
                ::= { diagModeEntry 1 }

        diagShelf       OBJECT-TYPE
                SYNTAX  CardShelf
                ACCESS  read-only 
                STATUS  mandatory
                DESCRIPTION
                        "The shelf in which the card is located."
                ::= { diagModeEntry 2 }

        diagSlot        OBJECT-TYPE
                SYNTAX  CardSlot
                ACCESS  read-only 
                STATUS  mandatory
                DESCRIPTION
                        "The card slot in which the card is located."
                ::= { diagModeEntry 3 }

        diagSetMode     OBJECT-TYPE
                SYNTAX  INTEGER { other(1),
				warmboot(2),
				loopbackDisabled(3),
				loopbackEnabled(4)
				}                
                ACCESS  read-only 
                STATUS  mandatory
                DESCRIPTION
                        "If on, the card will be in diagnostics mode.  If
                         off, the card comes out of diagnostics mode."
                ::= { diagModeEntry 4 }

        diagTestNum     OBJECT-TYPE
                SYNTAX  INTEGER (0..20)
                ACCESS  read-only
                STATUS  mandatory
                DESCRIPTION
                        "Number of built-in diagnostics tests in the table
                         below."
                ::= { diagnostics 3 }

        diagTestTable   OBJECT-TYPE
                SYNTAX  SEQUENCE OF DiagTestEntry
                ACCESS  not-accessible
                STATUS  mandatory
                DESCRIPTION
                        "This table represents the information for each
                         built-in diagnostics test."
                ::= { diagnostics 4 }

        diagTestEntry   OBJECT-TYPE
                SYNTAX  DiagTestEntry
                ACCESS  not-accessible
                STATUS  mandatory
                DESCRIPTION
                        "Specifies the index for each row in the table below"
                INDEX { diagTestId, diagTLocation, diagTShelf, diagTSlot }
                ::= { diagTestTable 1 }

        DiagTestEntry   ::=
                SEQUENCE {
                        diagTestId      INTEGER,
                        diagTLocation   CardLocation,
                        diagTShelf      CardShelf,
                        diagTSlot       INTEGER,
                        diagParam1      DisplayString (SIZE (0..30)),
                        diagParam2      DisplayString (SIZE (0..30)),
                        diagParam3      DisplayString (SIZE (0..30)),
                        diagTSetMode    FlagType
                }

        diagTestId      OBJECT-TYPE
                SYNTAX  INTEGER {
		    		lLoopBack(1),
				rLoopBack(2),
				lNormal(3),
				rNormal(4)
		    }
                ACCESS  read-write
                STATUS  mandatory
                DESCRIPTION
                        "The name of the built-in diagnostics test."
                ::= { diagTestEntry 1 }

        diagTLocation   OBJECT-TYPE
                SYNTAX  CardLocation
                ACCESS  read-write
                STATUS  mandatory
                DESCRIPTION
                        "The location of the card to run the test on"
                ::= { diagTestEntry 2 }

        diagTShelf      OBJECT-TYPE
                SYNTAX  CardShelf
                ACCESS  read-write
                STATUS  mandatory
                DESCRIPTION
                        "The shelf in which the card is located."
                ::= { diagTestEntry 3 }

        diagTSlot       OBJECT-TYPE
                SYNTAX  CardSlot
                ACCESS  read-write
                STATUS  mandatory
                DESCRIPTION
                        "The card slot in which the card is located."
                ::= { diagTestEntry 4 }

        diagParam1      OBJECT-TYPE
                SYNTAX  DisplayString (SIZE (0..30))
                ACCESS  read-write
                STATUS  mandatory
                DESCRIPTION
                        "The first parameter, if any to pass to the built-in
                         test module.  This parameter may be NULL to signify
                         no run-time parameters.  If there is a parameter in,
                         any data type, it should be passed as a String
                         equivalent."
                ::= { diagTestEntry 5 }

        diagParam2      OBJECT-TYPE
                SYNTAX  DisplayString (SIZE (0..30))
                ACCESS  read-write
                STATUS  mandatory
                DESCRIPTION
                        "The second parameter, if any to pass to the built-in
                         test module.  This parameter may be NULL to signify
                         no more run-time parameters.  If there is a parameter
                         in any data type, it should be passed as a String
                         equivalent."
                ::= { diagTestEntry 6 }

        diagParam3      OBJECT-TYPE
                SYNTAX  DisplayString (SIZE (0..30))
                ACCESS  read-write
                STATUS  mandatory
                DESCRIPTION
                        "The third parameter, if any to pass to the built-in
                         test module.  This parameter may be NULL to signify
                         no more run-time parameters.  If there is a parameter
                         in any data type, it should be passed as a String
                         equivalent."
                ::= { diagTestEntry 7 }

        diagTSetMode    OBJECT-TYPE
                SYNTAX  FlagType
                ACCESS  read-write
                STATUS  mandatory
                DESCRIPTION
                        "If on, the given test will be run on the given card.
                         The value off has no effect in this case and is
                         ignored."
                ::= { diagTestEntry 8 }


        -- The elements in the userSecMgmt subgroup of the Security group

        usrNumUsers     OBJECT-TYPE
                SYNTAX  INTEGER (0..999)
                ACCESS  read-only
                STATUS  mandatory
                DESCRIPTION
                        "Number of user Logons in the table below.  This
                         counter is automatically set by the software."
                ::= { userSecMgmt 1 }

        usrSecTable     OBJECT-TYPE
                SYNTAX  SEQUENCE OF UsrSecEntry
                ACCESS  not-accessible
                STATUS  mandatory
                DESCRIPTION
                        "This table represents the information for each user
                         logon entry."
                ::= { userSecMgmt 2 }

        usrSecEntry     OBJECT-TYPE
                SYNTAX  UsrSecEntry
                ACCESS  not-accessible
                STATUS  mandatory
                DESCRIPTION
                        "Specifies the index for each row in the table below"
                INDEX { usrSecLogonId }
                ::= { usrSecTable 1 }

        UsrSecEntry     ::=
                SEQUENCE {
                        usrSecLogonId       LogonID,
                        usrSecPasswd        HashedPasswd,
                        usrSecRole          INTEGER,
                        usrSecFullName      DisplayString (SIZE (0..45)),
                        usrSecActDateTime   DateAndTime,
                        usrSecLastDateTime  DateAndTime,
			usrSecSetLastDateTime ResetType
                }

        usrSecLogonId   OBJECT-TYPE
                SYNTAX  LogonID
                ACCESS  read-write
                STATUS  mandatory
                DESCRIPTION
                        "The unique logon ID assigned to each user.  This field
                         should only be written by users that are in the right
                         security role."
                ::= { usrSecEntry 1 }

        usrSecPasswd    OBJECT-TYPE
                SYNTAX  HashedPasswd
                ACCESS  read-write
                STATUS  mandatory
                DESCRIPTION
                        "The hashed password for each unique logon ID.  To
                         turn the user account off, typically the password
                         is set to some fixed value.  Fixed passwords are
                         not accepted as valid passwords.  Since this field
                         is one-way hashed, it can be safely read without
                         compromising the security of the system."
                ::= { usrSecEntry 2 }

        usrSecRole      OBJECT-TYPE
                SYNTAX  INTEGER
                ACCESS  read-write
                STATUS  mandatory
                DESCRIPTION
                        "The role associated with each user logon ID.  This is
                         an index into the system role(s) table."
                ::= { usrSecEntry 3 }

        usrSecFullName  OBJECT-TYPE
                SYNTAX  DisplayString (SIZE (0..45))
                ACCESS  read-write
                STATUS  mandatory
                DESCRIPTION
                        "The full name of the user associated with each unique
                         logon ID."
                ::= { usrSecEntry 4 }

        usrSecActDateTime  OBJECT-TYPE
                SYNTAX  DateAndTime
                ACCESS  read-only
                STATUS  mandatory
                DESCRIPTION
                        "The Time & Date of the user account activation."
                ::= { usrSecEntry 5 }

        usrSecLastDateTime  OBJECT-TYPE
                SYNTAX  DateAndTime
                ACCESS  read-only
                STATUS  mandatory
                DESCRIPTION
                        "The Time & Date of the last user logon to the system"
                ::= { usrSecEntry 6 }

	usrSecSetLastDateTime   OBJECT-TYPE
                SYNTAX  ResetType
                ACCESS  read-write
                STATUS  mandatory
                DESCRIPTION
                        "An action to set the Time & Date of the last user
			 logon to the current systemtime."
                ::= { usrSecEntry 7 }
 


        -- The elements in the systemSecMgmt subgroup of the Security group

        secNumRoles     OBJECT-TYPE
                SYNTAX  INTEGER (0..9999)
                ACCESS  not-accessible
                STATUS  mandatory
                DESCRIPTION
                        "Number of system security roles in the table below.
                         This counter is automatically set by the software."
                ::= { systemSecMgmt 1 }

        secRoleTable    OBJECT-TYPE
                SYNTAX  SEQUENCE OF SecRoleEntry
                ACCESS  not-accessible
                STATUS  mandatory
                DESCRIPTION
                        "This table represents the information for each
                         system security role entry."
                ::= { systemSecMgmt 2 }

        secRoleEntry    OBJECT-TYPE
                SYNTAX  SecRoleEntry
                ACCESS  not-accessible
                STATUS  mandatory
                DESCRIPTION
                        "Specifies the index for each row in the table below"
                INDEX { secRole }
                ::= { secRoleTable 1 }

        SecRoleEntry    ::=
                SEQUENCE {
                        secRole         EntityName,
                        secRoleDescr    DisplayString (SIZE (0..60))
                }

        secRole         OBJECT-TYPE
                SYNTAX  EntityName
                ACCESS  not-accessible
                STATUS  mandatory
                DESCRIPTION
                        "Each row in this table defines a unique security
                         role."
                ::= { secRoleEntry 1 }

        secRoleDescr    OBJECT-TYPE
                SYNTAX  DisplayString (SIZE (0..60))
                ACCESS  not-accessible
                STATUS  mandatory
                DESCRIPTION
                        "The full narrated description of each security Role."
                ::= { secRoleEntry 2 }

        secNumGroups    OBJECT-TYPE
                SYNTAX  INTEGER (0..9999)
                ACCESS  not-accessible
                STATUS  mandatory
                DESCRIPTION
                        "Number of entity groups in the table below.
                         This counter is automatically set by the software."
                ::= { systemSecMgmt 3 }

        secGroupTable   OBJECT-TYPE
                SYNTAX  SEQUENCE OF SecGroupEntry
                ACCESS  not-accessible
                STATUS  mandatory
                DESCRIPTION
                        "This table represents the information for each
                         entity group entry."
                ::= { systemSecMgmt 4 }

        secGroupEntry   OBJECT-TYPE
                SYNTAX  SecGroupEntry
                ACCESS  not-accessible
                STATUS  mandatory
                DESCRIPTION
                        "Specifies the index for each row in the table below"
                INDEX { secGroup, secGroupRole }
                ::= { secGroupTable 1 }

        SecGroupEntry   ::=
                SEQUENCE {
                        secGroup        EntityName,
                        secGroupRole    EntityName
                }

        secGroup        OBJECT-TYPE
                SYNTAX  EntityName
                ACCESS  not-accessible
                STATUS  mandatory
                DESCRIPTION
                        "Each row in this table defines a grouping of entities
                         or elements from the MIB."
                ::= { secGroupEntry 1 }

        secGroupRole    OBJECT-TYPE
                SYNTAX  EntityName
                ACCESS  not-accessible
                STATUS  mandatory
                DESCRIPTION
                        "The containment of this group within a security role.
                         Under the given schema, each Role may have zero or
                         more entity groups.  Given an entity group, it may
                         have been contained within one or more roles."
                ::= { secGroupEntry 2 }

        secNumElements  OBJECT-TYPE
                SYNTAX  INTEGER (0..9999)
                ACCESS  not-accessible
                STATUS  mandatory
                DESCRIPTION
                        "Number of elements or entities in the table below.
                         This counter is automatically set by the software."
                ::= { systemSecMgmt 5 }

        secElementTable OBJECT-TYPE
                SYNTAX  SEQUENCE OF SecElementEntry
                ACCESS  not-accessible
                STATUS  mandatory
                DESCRIPTION
                        "This table represents the information for each
                         entity or element in the MIB."
                ::= { systemSecMgmt 6 }

        secElementEntry OBJECT-TYPE
                SYNTAX  SecElementEntry
                ACCESS  not-accessible
                STATUS  mandatory
                DESCRIPTION
                        "Specifies the index for each row in the table below"
                INDEX { secElement }
                ::= { secElementTable 1 }

        SecElementEntry ::=
                SEQUENCE {
                        secElement         EntityName,
                        secElementAccess   INTEGER,
                        secElementOID      DisplayString (SIZE (0..30)),
                        secElementType     INTEGER,
                        secElementParent   EntityName
                }

        secElement      OBJECT-TYPE
                SYNTAX  EntityName
                ACCESS  not-accessible
                STATUS  mandatory
                DESCRIPTION
                        "Each row in this table defines an element or entity
                         from the MIB."
                ::= { secElementEntry 1 }

        secElementAccess  OBJECT-TYPE
                SYNTAX  INTEGER { read(1), write(2), readWrite(3), none(4) }
                ACCESS  not-accessible
                STATUS  mandatory
                DESCRIPTION
                        "The original access mode for this element from the
                         MIB."
                ::= { secElementEntry 2 }

        secElementOID     OBJECT-TYPE
                SYNTAX  DisplayString (SIZE (0..30))
                ACCESS  not-accessible
                STATUS  mandatory
                DESCRIPTION
                        "The original SNMP OID for this element from the
                         MIB."
                ::= { secElementEntry 3 }

        secElementType    OBJECT-TYPE
                SYNTAX  INTEGER { element(1), group(2), table(3) }
                ACCESS  not-accessible
                STATUS  mandatory
                DESCRIPTION
                        "The original type for this element from the
                         MIB."
                ::= { secElementEntry 4 }

        secElementParent  OBJECT-TYPE
                SYNTAX  EntityName
                ACCESS  not-accessible
                STATUS  mandatory
                DESCRIPTION
                        "The original parent name for this element from the
                         MIB.  The parent is either a table or a subgroup."
                ::= { secElementEntry 5 }

        secNumElmntGrp  OBJECT-TYPE
                SYNTAX  INTEGER (0..9999)
                ACCESS  not-accessible
                STATUS  mandatory
                DESCRIPTION
                        "Number of element-to-group mappings in the table
                         below. This counter is automatically set by the
                         software."
                ::= { systemSecMgmt 7 }

        secElmntGrpTable   OBJECT-TYPE
                SYNTAX  SEQUENCE OF SecElmntGrpEntry
                ACCESS  not-accessible
                STATUS  mandatory
                DESCRIPTION
                        "This table represents the information for each
                         element-to-group mapping."
                ::= { systemSecMgmt 8 }

        secElmntGrpEntry  OBJECT-TYPE
                SYNTAX  SecElmntGrpEntry
                ACCESS  not-accessible
                STATUS  mandatory
                DESCRIPTION
                        "Specifies the index for each row in the table below"
                INDEX { elmntName, grpName }
                ::= { secElmntGrpTable 1 }

        SecElmntGrpEntry  ::=
                SEQUENCE {
                        elmntName       EntityName,
                        grpName         EntityName,
                        elmntGrpAccess  INTEGER
                }

        elmntName       OBJECT-TYPE
                SYNTAX  EntityName
                ACCESS  not-accessible
                STATUS  mandatory
                DESCRIPTION
                        "Each row in this table defines a mapping of elements
                         to groups.  This column is an index into the
                         secElementTable."
                ::= { secElmntGrpEntry 1 }

        grpName         OBJECT-TYPE
                SYNTAX  EntityName
                ACCESS  not-accessible
                STATUS  mandatory
                DESCRIPTION
                        "Each row in this table defines a mapping of elements
                         to groups.  This column is an index into the
                         secGroupTable."
                ::= { secElmntGrpEntry 2 }

        elmntGrpAccess  OBJECT-TYPE
                SYNTAX  INTEGER { read(1), write(2), readWrite(3), none(4) }
                ACCESS  not-accessible
                STATUS  mandatory
                DESCRIPTION
                        "The access mode assigned to each element/group entry.
                         Under the given schema, each group may have zero or
                         more MIB elements.  Given an element, it may
                         have been contained within one or more groups.  The
                         access mode specified here defines what is the granted
                         access mode to the named element contained in this
                         group.  Note, the granted access right can never
                         exceed that of the actual MIB access privilege."
                ::= { secElmntGrpEntry 3 }


        -- The elements in the cpAcct subgroup of the accounting group

        acctCPTable     OBJECT-TYPE
                SYNTAX  SEQUENCE OF AcctCPEntry
                ACCESS  not-accessible
                STATUS  mandatory
                DESCRIPTION
                        "This table represents the information for each
                         system accounting data maintained for each CP."
                ::= { cpAcct 1 }

        acctCPEntry     OBJECT-TYPE
                SYNTAX  AcctCPEntry
                ACCESS  not-accessible
                STATUS  mandatory
                DESCRIPTION
                        "Specifies the index for each row in the table below"
                INDEX { acctCPShelf, acctCPSlot }
                ::= { acctCPTable 1 }

        AcctCPEntry     ::=
                SEQUENCE {
                        acctCPShelf       CardShelf,
                        acctCPSlot        INTEGER,
                        acctCPDsgnAct     Counter,
                        acctCPDsgnStdby   Counter,
                        acctCPActive      Counter,
                        acctCPStandby     Counter,
                        acctCPUpTime      Counter,
                        acctCPUnAvail     Counter,
                        acctCPResetCntrs  ResetType
                }

        acctCPShelf     OBJECT-TYPE
                SYNTAX  CardShelf
                ACCESS  read-only
                STATUS  mandatory
                DESCRIPTION
                        "The shelf in which the given CP card is placed."
                ::= { acctCPEntry 1 }

        acctCPSlot      OBJECT-TYPE
                SYNTAX  CardSlot
                ACCESS  read-only
                STATUS  mandatory
                DESCRIPTION
                        "The slot in which the given CP card is placed."
                ::= { acctCPEntry 2 }

        acctCPDsgnAct   OBJECT-TYPE
                SYNTAX  Counter
                ACCESS  not-accessible
                STATUS  mandatory
                DESCRIPTION
                        "The total time this CP has been designated Active"
                ::= { acctCPEntry 3 }

        acctCPDsgnStdby OBJECT-TYPE
                SYNTAX  Counter
                ACCESS  not-accessible
                STATUS  mandatory
                DESCRIPTION
                        "The total time this CP has been designated Standby"
                ::= { acctCPEntry 4 }

        acctCPActive    OBJECT-TYPE
                SYNTAX  Counter
                ACCESS  read-only
                STATUS  mandatory
                DESCRIPTION
                        "The total time this CP has actually been the primary"
                ::= { acctCPEntry 5 }

        acctCPStandby   OBJECT-TYPE
                SYNTAX  Counter
                ACCESS  read-only
                STATUS  mandatory
                DESCRIPTION
                        "The total time this CP has actually been the standby"
                ::= { acctCPEntry 6 }

        acctCPUpTime    OBJECT-TYPE
                SYNTAX  Counter
                ACCESS  read-only
                STATUS  mandatory
                DESCRIPTION
                        "The total time since this CP has been commissioned"
                ::= { acctCPEntry 7 }

        acctCPUnAvail   OBJECT-TYPE
                SYNTAX  Counter
                ACCESS  read-only
                STATUS  mandatory
                DESCRIPTION
                        "The total time this CP has not been available due
                         to an alarm, diag testing or being put offline"
                ::= { acctCPEntry 8 }

        acctCPResetCntrs  OBJECT-TYPE
                SYNTAX  ResetType
                ACCESS  read-write
                STATUS  mandatory
                DESCRIPTION
                        "If reset, the CP accounting counters will be reset to 0.
                         A get on this will always return other."
                ::= { acctCPEntry 9 }


        -- The elements in the ccAcct subgroup of the accounting group

        acctCCTable     OBJECT-TYPE
                SYNTAX  SEQUENCE OF AcctCCEntry
                ACCESS  not-accessible
                STATUS  mandatory
                DESCRIPTION
                        "This table represents the information for each
                         system accounting data maintained for each CC."
                ::= { ccAcct 1 }

        acctCCEntry     OBJECT-TYPE
                SYNTAX  AcctCCEntry
                ACCESS  not-accessible
                STATUS  mandatory
                DESCRIPTION
                        "Specifies the index for each row in the table below"
                INDEX { acctCCLocation, acctCCShelf, acctCCSlot }
                ::= { acctCCTable 1 }

        AcctCCEntry     ::=
                SEQUENCE {
                        acctCCLocation    CardLocation,
                        acctCCShelf       CardShelf,
                        acctCCSlot        INTEGER,
                        acctCCUpTime      Counter,
                        acctCCUnAvail     Counter,
                        acctCCResetCntrs  ResetType
                }

        acctCCLocation  OBJECT-TYPE
                SYNTAX  CardLocation
                ACCESS  read-only
                STATUS  mandatory
                DESCRIPTION
                        "The location of the CC card: local or remote."
                ::= { acctCCEntry 1 }

        acctCCShelf     OBJECT-TYPE
                SYNTAX  CardShelf
                ACCESS  read-only
                STATUS  mandatory
                DESCRIPTION
                        "The shelf in which the given CC card is placed."
                ::= { acctCCEntry 2 }

        acctCCSlot      OBJECT-TYPE
                SYNTAX  CardSlot
                ACCESS  read-only
                STATUS  mandatory
                DESCRIPTION
                        "The slot in which the given CC card is placed."
                ::= { acctCCEntry 3 }

        acctCCUpTime    OBJECT-TYPE
                SYNTAX  Counter
                ACCESS  read-only
                STATUS  mandatory
                DESCRIPTION
                        "The total time since this CC has been commissioned"
                ::= { acctCCEntry 4 }

        acctCCUnAvail   OBJECT-TYPE
                SYNTAX  Counter
                ACCESS  read-only
                STATUS  mandatory
                DESCRIPTION
                        "The total time this CC has not been available due
                         to an alarm, diag testing or being put offline"
                ::= { acctCCEntry 5 }

        acctCCResetCntrs  OBJECT-TYPE
                SYNTAX  ResetType
                ACCESS  read-write
                STATUS  mandatory
                DESCRIPTION
                        "If reset, the CC accounting counters will be reset to 0.
                         A get on this will always return other."
                ::= { acctCCEntry 6 }


        -- The elements in the mcmAcct subgroup of the accounting group

        acctmcmTable     OBJECT-TYPE
                SYNTAX  SEQUENCE OF AcctmcmEntry
                ACCESS  not-accessible
                STATUS  mandatory
                DESCRIPTION
                        "This table represents the information for each
                         system accounting data maintained for each MCM."
                ::= { mcmAcct 1 }

        acctmcmEntry     OBJECT-TYPE
                SYNTAX  AcctmcmEntry 
                ACCESS  not-accessible
                STATUS  mandatory
                DESCRIPTION
                        "Specifies the index for each row in the table below"
                INDEX { acctmcmLocation, acctmcmShelf, acctmcmSlot }
                ::= { acctmcmTable 1 }

        AcctmcmEntry     ::=
                SEQUENCE {
                        acctmcmLocation    CardLocation,
                        acctmcmShelf       CardShelf,
                        acctmcmSlot        INTEGER,
                        acctmcmUpTime      Counter,
                        acctmcmUnAvail     Counter,
                        acctmcmResetCntrs  ResetType
                }

        acctmcmLocation  OBJECT-TYPE
                SYNTAX  CardLocation
                ACCESS  read-only
                STATUS  mandatory
                DESCRIPTION
                        "The location of the MCM card: local or remote."
                ::= { acctmcmEntry 1 }

        acctmcmShelf     OBJECT-TYPE
                SYNTAX  CardShelf
                ACCESS  read-only
                STATUS  mandatory
                DESCRIPTION
                        "The shelf in which the given MCM card is placed."
                ::= { acctmcmEntry 2 }

        acctmcmSlot      OBJECT-TYPE
                SYNTAX  CardSlot
                ACCESS  read-only
                STATUS  mandatory
                DESCRIPTION
                        "The slot in which the given MCM card is placed."
                ::= { acctmcmEntry 3 }

        acctmcmUpTime    OBJECT-TYPE
                SYNTAX  Counter
                ACCESS  read-only
                STATUS  mandatory
                DESCRIPTION
                        "The total time since this MCM has been commissioned"
                ::= { acctmcmEntry 4 }

        acctmcmUnAvail   OBJECT-TYPE
                SYNTAX  Counter
                ACCESS  read-only
                STATUS  mandatory
                DESCRIPTION
                        "The total time this MCM has not been available due
                         to an alarm, diag testing or being put offline"
                ::= { acctmcmEntry 5 }

        acctmcmResetCntrs  OBJECT-TYPE
                SYNTAX  ResetType
                ACCESS  read-write
                STATUS  mandatory
                DESCRIPTION
       			"If reset, the MCM accounting counters will be
			 reset to 0. A get on this will always
			 return other."
                ::= { acctmcmEntry 6 }



        -- The Generic Trap supported by the LuxN MIB.

        luxNGenericTrap   TRAP-TYPE
                ENTERPRISE  luxN
                VARIABLES { eveDateTime, eveEventId, eveDescr, eveSeverity,
                             eveSysStatus, eveSource,  cpIpAddress, eveSeqNum }
                DESCRIPTION
			"This is a generic trap identifying an event for
			 a given event source.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 1

        luxNsignalStrengthLowTrap   TRAP-TYPE
                ENTERPRISE  luxN
                VARIABLES { eveDateTime, eveEventId, eveDescr, eveSeverity,
                             eveSysStatus, eveSource,  cpIpAddress, eveSeqNum }
                DESCRIPTION
			"This trap is sent when the receieve signal
			 strength is low.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 1006

        luxNsignalStrengthNormalTrap   TRAP-TYPE
                ENTERPRISE  luxN
                VARIABLES { eveDateTime, eveEventId, eveDescr, eveSeverity,
                             eveSysStatus, eveSource,  cpIpAddress, eveSeqNum }
                DESCRIPTION
			"This trap is sent when the receieve signal
			 strength is normal.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 1007

        luxNlaserPowerOutOfRangeTrap   TRAP-TYPE
                ENTERPRISE  luxN
                VARIABLES { eveDateTime, eveEventId, eveDescr, eveSeverity,
                             eveSysStatus, eveSource,  cpIpAddress, eveSeqNum }
                DESCRIPTION
			"This trap is sent upon detection of out of range
			 laser power.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 1008

        luxNlaserPowerNormalTrap   TRAP-TYPE
                ENTERPRISE  luxN
                VARIABLES { eveDateTime, eveEventId, eveDescr, eveSeverity,
                             eveSysStatus, eveSource,  cpIpAddress, eveSeqNum }
                DESCRIPTION
			"This trap is sent upon detection of normal
			 laser power.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 1009

        luxNcardActivationFailureTrap   TRAP-TYPE
                ENTERPRISE  luxN
                VARIABLES { eveDateTime, eveEventId, eveDescr, eveSeverity,
                             eveSysStatus, eveSource,  cpIpAddress, eveSeqNum }
                DESCRIPTION
			"Obsolete.  This trap is sent whenever a card activation
			 failure is detected.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2003

        luxNsnmpAuthenticationFailureTrap   TRAP-TYPE
                ENTERPRISE  luxN
                VARIABLES { eveDateTime, eveEventId, eveDescr, eveSeverity,
                             eveSysStatus, eveSource,  cpIpAddress, eveSeqNum }
                DESCRIPTION
			"This trap is sent upon receipt of invalid
			 community strings.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2017

        luxNcoldStartTrap   TRAP-TYPE
                ENTERPRISE  luxN
                VARIABLES { eveDateTime, eveEventId, eveDescr, eveSeverity,
                             eveSysStatus, eveSource,  cpIpAddress, eveSeqNum }
                DESCRIPTION
			"This trap is sent when the device has reinitialized
			 itself.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2018

        luxNwarmStartTrap   TRAP-TYPE
                ENTERPRISE  luxN
                VARIABLES { eveDateTime, eveEventId, eveDescr, eveSeverity,
                             eveSysStatus, eveSource,  cpIpAddress, eveSeqNum }
                DESCRIPTION
			"This trap is sent when the device has undergone
			 a warm boot.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2019

        luxNlossOfLightResolvedTrap   TRAP-TYPE
                ENTERPRISE  luxN
                VARIABLES { eveDateTime, eveEventId, eveDescr, eveSeverity,
                             eveSysStatus, eveSource,  cpIpAddress, eveSeqNum }
                DESCRIPTION
			"This trap is sent when a loss of light condition
			 has been resolved for the link between two
			 optically connected channel cards.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2021

        luxNlossOfLightDetectedTrap   TRAP-TYPE
                ENTERPRISE  luxN
                VARIABLES { eveDateTime, eveEventId, eveDescr, eveSeverity,
                             eveSysStatus, eveSource,  cpIpAddress, eveSeqNum }
                DESCRIPTION
			"This trap is sent when a loss of light condition
			 has been detected for the link between two
			 optically connected channel cards.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2022

        luxNpingCompletionTrap   TRAP-TYPE
                ENTERPRISE  luxN
                VARIABLES { eveDateTime, eveEventId, eveDescr, eveSeverity,
                             eveSysStatus, eveSource,  cpIpAddress, eveSeqNum }
                DESCRIPTION
			"Obsolete.  This trap is sent when a sequence of pings
			 is completed.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2023

        luxNspiConnectionUpTrap   TRAP-TYPE
                ENTERPRISE  luxN
                VARIABLES { eveDateTime, eveEventId, eveDescr, eveSeverity,
                             eveSysStatus, eveSource,  cpIpAddress, eveSeqNum }
                DESCRIPTION
			"Obsolete.  This trap is sent when SPI communications
			 has been established with a card specified in the
			 source field.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2030

        luxNcardLostTrap   TRAP-TYPE
                ENTERPRISE  luxN
                VARIABLES { eveDateTime, eveEventId, eveDescr, eveSeverity,
                             eveSysStatus, eveSource,  cpIpAddress, eveSeqNum }
                DESCRIPTION
			"This trap is sent when SPI communications has been
			 lost with a card specified in the source field.
			 The reason is either that the card has been physically
			 removed or there exist a failure condition.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2031

        luxNConfigChangeTrap   TRAP-TYPE
                ENTERPRISE  luxN
                VARIABLES { eveDateTime, eveEventId, eveDescr, eveSeverity,
                             eveSysStatus, eveSource,  cpIpAddress, eveSeqNum }
                DESCRIPTION
			"This trap is sent when a configuration change
			 has ocurred for a card specified in the source
			 field.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2034

        luxNstatsPollFailedTrap   TRAP-TYPE
                ENTERPRISE  luxN
                VARIABLES { eveDateTime, eveEventId, eveDescr, eveSeverity,
                             eveSysStatus, eveSource,  cpIpAddress, eveSeqNum }
                DESCRIPTION
			"This trap is sent when statistics data can no longer
			 be gathered from a card in the specified source
			 field.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2035

        luxNCardFoundTrap   TRAP-TYPE
                ENTERPRISE  luxN
                VARIABLES { eveDateTime, eveEventId, eveDescr, eveSeverity,
                             eveSysStatus, eveSource,  cpIpAddress, eveSeqNum }
                DESCRIPTION
			"This trap is sent when a card has been 
			 discovered in the chassis.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2040

        luxNlocalLoopbackEnabledTrap   TRAP-TYPE
                ENTERPRISE  luxN
                VARIABLES { eveDateTime, eveEventId, eveDescr, eveSeverity,
                             eveSysStatus, eveSource,  cpIpAddress, eveSeqNum }
                DESCRIPTION
			"This trap is sent when the local loopback mode
			 has been enabled for a channel card in the
			 specified source field. The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2041

        luxNremoteLoopbackEnabledTrap   TRAP-TYPE
                ENTERPRISE  luxN
                VARIABLES { eveDateTime, eveEventId, eveDescr, eveSeverity,
                             eveSysStatus, eveSource,  cpIpAddress, eveSeqNum }
                DESCRIPTION
			"This trap is sent when the remote loopback mode
			 has been enabled for a channel card in the
			 specified source field. The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2042

        luxNlocalLoopbackDisabledTrap   TRAP-TYPE
                ENTERPRISE  luxN
                VARIABLES { eveDateTime, eveEventId, eveDescr, eveSeverity,
                             eveSysStatus, eveSource,  cpIpAddress, eveSeqNum }
                DESCRIPTION
			"This trap is sent when the local loopback mode
			 has been disabled for a channel card in the
			 specified source field. The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2043

        luxNremoteLoopbackDisabledTrap   TRAP-TYPE
                ENTERPRISE  luxN
                VARIABLES { eveDateTime, eveEventId, eveDescr, eveSeverity,
                             eveSysStatus, eveSource,  cpIpAddress, eveSeqNum }
                DESCRIPTION
			"This trap is sent when the remote loopback mode
			 has been disabled for a channel card in the
			 specified source field. The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2044

        luxNftpSessionInitiatedTrap   TRAP-TYPE
                ENTERPRISE  luxN
                VARIABLES { eveDateTime, eveEventId, eveDescr, eveSeverity,
                             eveSysStatus, eveSource,  cpIpAddress, eveSeqNum }
                DESCRIPTION
			"This trap is sent when a ftp session has been
			 initiated from the CLI. The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2047

        luxNuserResetStatusTrap   TRAP-TYPE
                ENTERPRISE  luxN
                VARIABLES { eveDateTime, eveEventId, eveDescr, eveSeverity,
                             eveSysStatus, eveSource,  cpIpAddress, eveSeqNum }
                DESCRIPTION
			"Obsolete.  This trap is sent when the status information
			 for a card specified in the source field has
			 been modified via the snmp agent.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2050

        luxNprotectionSwitchTrap   TRAP-TYPE
                ENTERPRISE  luxN
                VARIABLES { eveDateTime, eveEventId, eveDescr, eveSeverity,
                             eveSysStatus, eveSource,  cpIpAddress, eveSeqNum }
                DESCRIPTION
			"This trap is sent when a protection switch has
			 occurred either automatically or manually.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2051

        luxNipAddressErrorTrap   TRAP-TYPE
                ENTERPRISE  luxN
                VARIABLES { eveDateTime, eveEventId, eveDescr, eveSeverity,
                             eveSysStatus, eveSource,  cpIpAddress, eveSeqNum }
                DESCRIPTION
			"Obsolete.  This trap is sent when an error has
			 occurred while configuring the IP address.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2052

        luxNipNetmaskErrorTrap   TRAP-TYPE
                ENTERPRISE  luxN
                VARIABLES { eveDateTime, eveEventId, eveDescr, eveSeverity,
                             eveSysStatus, eveSource,  cpIpAddress, eveSeqNum }
                DESCRIPTION
			"Obsolete.  This trap is sent when an error has
			 occurred while configuring the Netmask.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2053

        luxNdefaultGatewayErrorTrap   TRAP-TYPE
                ENTERPRISE  luxN
                VARIABLES { eveDateTime, eveEventId, eveDescr, eveSeverity,
                             eveSysStatus, eveSource,  cpIpAddress, eveSeqNum }
                DESCRIPTION
			"Obsolete.  This trap is sent when an error has
			 occurred while configuring the default gateway.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2054

        luxNlossOfSignalTrap   TRAP-TYPE
                ENTERPRISE  luxN
                VARIABLES { eveDateTime, eveEventId, eveDescr, eveSeverity,
                             eveSysStatus, eveSource,  cpIpAddress, eveSeqNum }
                DESCRIPTION
			"This trap is sent when a loss of signal is
			 detected on one of the ports on a channel card
			 specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2055

        luxNlossOfSignalNormalTrap   TRAP-TYPE
                ENTERPRISE  luxN
                VARIABLES { eveDateTime, eveEventId, eveDescr, eveSeverity,
                             eveSysStatus, eveSource,  cpIpAddress, eveSeqNum }
                DESCRIPTION
			"This trap is sent when a loss of signal problem
			 on one of the ports on a channel card
			 specified in the source field has been corrected.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2056

        luxNlossOfFrameTrap   TRAP-TYPE
                ENTERPRISE  luxN
                VARIABLES { eveDateTime, eveEventId, eveDescr, eveSeverity,
                             eveSysStatus, eveSource,  cpIpAddress, eveSeqNum }
                DESCRIPTION
			"This trap is sent when a loss of frame error
			 condition is detected on one of the ports on a
			 channel card specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2057

        luxNlossOfFrameNormalTrap   TRAP-TYPE
                ENTERPRISE  luxN
                VARIABLES { eveDateTime, eveEventId, eveDescr, eveSeverity,
                             eveSysStatus, eveSource,  cpIpAddress, eveSeqNum }
                DESCRIPTION
			"This trap is sent when a loss of frame error
			 condition on one of the ports on a channel card
			 specified in the source field has been corrected.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2058

        luxNrecvAISTrap   TRAP-TYPE
                ENTERPRISE  luxN
                VARIABLES { eveDateTime, eveEventId, eveDescr, eveSeverity,
                             eveSysStatus, eveSource,  cpIpAddress, eveSeqNum }
                DESCRIPTION
			"This trap is sent when a receive AIS (Alarm
			 Indication Signal) is detected on one of the ports
			 on a channel card specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2059

        luxNrecvAISNormalTrap   TRAP-TYPE
                ENTERPRISE  luxN
                VARIABLES { eveDateTime, eveEventId, eveDescr, eveSeverity,
                             eveSysStatus, eveSource,  cpIpAddress, eveSeqNum }
                DESCRIPTION
			"This trap is sent when a receive AIS (Alarm
			 Indication Signal) problem on one of the ports
			 on a channel card specified in the source field
			 has been corrected.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2060

        luxNrecvYellowAlarmTrap   TRAP-TYPE
                ENTERPRISE  luxN
                VARIABLES { eveDateTime, eveEventId, eveDescr, eveSeverity,
                             eveSysStatus, eveSource,  cpIpAddress, eveSeqNum }
                DESCRIPTION
			"This trap is sent when a receive receive yellow
			 alarm is detected on one of the ports on a channel
			 card specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2061

        luxNrecvYellowAlarmNormalTrap   TRAP-TYPE
                ENTERPRISE  luxN
                VARIABLES { eveDateTime, eveEventId, eveDescr, eveSeverity,
                             eveSysStatus, eveSource,  cpIpAddress, eveSeqNum }
                DESCRIPTION
			"This trap is sent when a receive receive yellow
			 alarm problem on one of the ports on a channel
			 card specified in the source field has been
			 corrected.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2062

        luxNlineCodeViolationTrap   TRAP-TYPE
                ENTERPRISE  luxN
                VARIABLES { eveDateTime, eveEventId, eveDescr, eveSeverity,
                             eveSysStatus, eveSource,  cpIpAddress, eveSeqNum }
                DESCRIPTION
			"This trap is sent when a line code violation error
			 condition is detected on one of the ports on a
			 channel card specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2063

        luxNlineCodeViolationNormalTrap   TRAP-TYPE
                ENTERPRISE  luxN
                VARIABLES { eveDateTime, eveEventId, eveDescr, eveSeverity,
                             eveSysStatus, eveSource,  cpIpAddress, eveSeqNum }
                DESCRIPTION
			"This trap is sent when a line code violation error
			 condition on one of the ports on a channel card
			 specified in the source field has been corrected.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2064

        luxNframingAlarmTrap   TRAP-TYPE
                ENTERPRISE  luxN
                VARIABLES { eveDateTime, eveEventId, eveDescr, eveSeverity,
                             eveSysStatus, eveSource,  cpIpAddress, eveSeqNum }
                DESCRIPTION
			"This trap is sent when a framing alarm is
			 detected on one of the ports on a channel card
			 specified in the source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2065

        luxNframingAlarmNormalTrap   TRAP-TYPE
                ENTERPRISE  luxN
                VARIABLES { eveDateTime, eveEventId, eveDescr, eveSeverity,
                             eveSysStatus, eveSource,  cpIpAddress, eveSeqNum }
                DESCRIPTION
			"This trap is sent when a framing alarm problem
			 on one of the ports on a channel card specified
			 in the source field has been corrected.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2066

        luxNlossOfTimingTrap   TRAP-TYPE
                ENTERPRISE  luxN
                VARIABLES { eveDateTime, eveEventId, eveDescr, eveSeverity,
                             eveSysStatus, eveSource,  cpIpAddress, eveSeqNum }
                DESCRIPTION
			"This trap is sent when a loss of timing condition
			 is detected on a channel card specified in
			 the source field.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2067

        luxNlossOfTimingNormalTrap   TRAP-TYPE
                ENTERPRISE  luxN
                VARIABLES { eveDateTime, eveEventId, eveDescr, eveSeverity,
                             eveSysStatus, eveSource,  cpIpAddress, eveSeqNum }
                DESCRIPTION
			"This trap is sent when a loss of timing problem
			 on a channel card specified in the source field
			 has been corrected.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2068

        luxNmcmNearendCardLoopbackEnabledTrap   TRAP-TYPE
                ENTERPRISE  luxN
                VARIABLES { eveDateTime, eveEventId, eveDescr, eveSeverity,
                             eveSysStatus, eveSource,  cpIpAddress, eveSeqNum }
                DESCRIPTION
			"This trap is sent to indicate that a near-end card
			 loopback has been enabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2077

        luxNmcmNearendCardLoopbackDisabledTrap   TRAP-TYPE
                ENTERPRISE  luxN
                VARIABLES { eveDateTime, eveEventId, eveDescr, eveSeverity,
                             eveSysStatus, eveSource,  cpIpAddress, eveSeqNum }
                DESCRIPTION
			"This trap is sent to indicate that a near-end card
			 loopback has been disabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2078

        luxNmcmNetworkPortLoopbackEnabledTrap   TRAP-TYPE
                ENTERPRISE  luxN
                VARIABLES { eveDateTime, eveEventId, eveDescr, eveSeverity,
                             eveSysStatus, eveSource,  cpIpAddress, eveSeqNum }
                DESCRIPTION
			"This trap is sent to indicate that a network port
			 loopback has been enabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2079

        luxNmcmNetworkPortLoopbackDisabledTrap   TRAP-TYPE
                ENTERPRISE  luxN
                VARIABLES { eveDateTime, eveEventId, eveDescr, eveSeverity,
                             eveSysStatus, eveSource,  cpIpAddress, eveSeqNum }
                DESCRIPTION
			"This trap is sent to indicate that a network port
			 loopback has been disabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2080

        luxNmcmCardNetworkLoopbackEnabledTrap   TRAP-TYPE
                ENTERPRISE  luxN
                VARIABLES { eveDateTime, eveEventId, eveDescr, eveSeverity,
                             eveSysStatus, eveSource,  cpIpAddress, eveSeqNum }
                DESCRIPTION
			"This trap is sent to indicate that a card network
			 loopback has been enabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2081

        luxNmcmCardNetworkLoopbackDisabledTrap   TRAP-TYPE
                ENTERPRISE  luxN
                VARIABLES { eveDateTime, eveEventId, eveDescr, eveSeverity,
                             eveSysStatus, eveSource,  cpIpAddress, eveSeqNum }
                DESCRIPTION
			"This trap is sent to indicate that a card network
			 loopback has been disabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2082

        luxNmcmNearendPortLoopbackEnabledTrap   TRAP-TYPE
                ENTERPRISE  luxN
                VARIABLES { eveDateTime, eveEventId, eveDescr, eveSeverity,
                             eveSysStatus, eveSource,  cpIpAddress, eveSeqNum }
                DESCRIPTION
			"This trap is sent to indicate that a nearend port
			 loopback has been enabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2083

        luxNmcmNearendPortLoopbackDisabledTrap   TRAP-TYPE
                ENTERPRISE  luxN
                VARIABLES { eveDateTime, eveEventId, eveDescr, eveSeverity,
                             eveSysStatus, eveSource,  cpIpAddress, eveSeqNum }
                DESCRIPTION
			"This trap is sent to indicate that a nearend port
			 loopback has been disabled on a mcm card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2084

        luxNpowerSupplyNotPresentTrap   TRAP-TYPE
                ENTERPRISE  luxN
                VARIABLES { eveDateTime, eveEventId, eveDescr, eveSeverity,
                             eveSysStatus, eveSource,  cpIpAddress, eveSeqNum }
                DESCRIPTION
			"This trap is sent to indicate that the power supply
			 specified in the source field is not present.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2085

        luxNpowerSupplyOKTrap   TRAP-TYPE
                ENTERPRISE  luxN
                VARIABLES { eveDateTime, eveEventId, eveDescr, eveSeverity,
                             eveSysStatus, eveSource,  cpIpAddress, eveSeqNum }
                DESCRIPTION
			"This trap is sent to indicate that the power supply
			 specified in the source field is performing
			 properly.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2086

        luxNpowerSupplyDegradedTrap   TRAP-TYPE
                ENTERPRISE  luxN
                VARIABLES { eveDateTime, eveEventId, eveDescr, eveSeverity,
                             eveSysStatus, eveSource,  cpIpAddress, eveSeqNum }
                DESCRIPTION
			"This trap is sent to indicate that the performance
			 of the power supply specified in the source field
			 has degraded.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2087

        luxNpowerSupplyFailureTrap   TRAP-TYPE
                ENTERPRISE  luxN
                VARIABLES { eveDateTime, eveEventId, eveDescr, eveSeverity,
                             eveSysStatus, eveSource,  cpIpAddress, eveSeqNum }
                DESCRIPTION
			"This trap is sent to indicate that the power
			 supply specified in the source field has failed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2088

        luxNfanOKTrap   TRAP-TYPE
                ENTERPRISE  luxN
                VARIABLES { eveDateTime, eveEventId, eveDescr, eveSeverity,
                             eveSysStatus, eveSource,  cpIpAddress, eveSeqNum }
                DESCRIPTION
			"This trap is sent to indicate that the fan
			 specified in the source field is performing
			 properly.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2089

        luxNfanFailureTrap   TRAP-TYPE
                ENTERPRISE  luxN
                VARIABLES { eveDateTime, eveEventId, eveDescr, eveSeverity,
                             eveSysStatus, eveSource,  cpIpAddress, eveSeqNum }
                DESCRIPTION
			"This trap is sent to indicate that the fan
			 specified in the source field has failed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2090

        luxNcsimDataUnavailableTrap   TRAP-TYPE
                ENTERPRISE  luxN
                VARIABLES { eveDateTime, eveEventId, eveDescr, eveSeverity,
                             eveSysStatus, eveSource,  cpIpAddress, eveSeqNum }
                DESCRIPTION
			"This trap is sent to indicate that the ColorSIM
			 module as specified in the source field is in
			 a Data Unavailable state.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2091

        luxNcsimDataAvailableTrap   TRAP-TYPE
                ENTERPRISE  luxN
                VARIABLES { eveDateTime, eveEventId, eveDescr, eveSeverity,
                             eveSysStatus, eveSource,  cpIpAddress, eveSeqNum }
                DESCRIPTION
			"This trap is sent to indicate that the ColorSIM
			 module as specified in the source field is in
			 a Data Available state.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2092

        luxNcsimModuleFailureTrap   TRAP-TYPE
                ENTERPRISE  luxN
                VARIABLES { eveDateTime, eveEventId, eveDescr, eveSeverity,
                             eveSysStatus, eveSource,  cpIpAddress, eveSeqNum }
                DESCRIPTION
			"This trap is sent to indicate that the ColorSIM
			 module as specified in the source field has
			 failed to operate properly.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2093

        luxNethernetLossOfCarrierTrap   TRAP-TYPE
                ENTERPRISE  luxN
                VARIABLES { eveDateTime, eveEventId, eveDescr, eveSeverity,
                             eveSysStatus, eveSource,  cpIpAddress, eveSeqNum }
                DESCRIPTION
			"This trap is sent to indicate that loss of carrier
			 has been detected on the CPE's ethernet port.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2094

        luxNethernetCarrierDetectedTrap   TRAP-TYPE
                ENTERPRISE  luxN
                VARIABLES { eveDateTime, eveEventId, eveDescr, eveSeverity,
                             eveSysStatus, eveSource,  cpIpAddress, eveSeqNum }
                DESCRIPTION
			"This trap is sent to indicate that the carrier
			 has been detected on the CPE's ethernet port.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2095

        luxNtimingPriorityChangedTrap   TRAP-TYPE
                ENTERPRISE  luxN
                VARIABLES { eveDateTime, eveEventId, eveDescr, eveSeverity,
                             eveSysStatus, eveSource,  cpIpAddress, eveSeqNum }
                DESCRIPTION
			"This trap is sent to indicate that the timing
			 priority for a card has been changed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2096

        luxNopenFiberCPEAlarmTrap   TRAP-TYPE
                ENTERPRISE  luxN
                VARIABLES { eveDateTime, eveEventId, eveDescr, eveSeverity,
                             eveSysStatus, eveSource,  cpIpAddress, eveSeqNum }
                DESCRIPTION
			"This trap is sent when an open fiber condition
			 on the CPE has been detected from a
			 card specified in the source field.  The
			 source is a 4 or 5 tuple specifying the type,
			 location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2097

        luxNopenFiberCPEAlarmResolvedTrap   TRAP-TYPE
                ENTERPRISE  luxN
                VARIABLES { eveDateTime, eveEventId, eveDescr, eveSeverity,
                             eveSysStatus, eveSource,  cpIpAddress, eveSeqNum }
                DESCRIPTION
			"This trap is sent when an open fiber condition
			 on the CPE has been resolved from a
			 card specified in the source field.  The
			 source is a 4 or 5 tuple specifying the type,
			 location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2098

        luxNstandbyMPMDetectedTrap   TRAP-TYPE
                ENTERPRISE  luxN
                VARIABLES { eveDateTime, eveEventId, eveDescr, eveSeverity,
                             eveSysStatus, eveSource,  cpIpAddress, eveSeqNum }
                DESCRIPTION
			"This trap is sent when the standby MPM card
			 has been detected.  The
			 source is a 4 or 5 tuple specifying the type,
			 location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2099

        luxNstandbyMPMLostTrap   TRAP-TYPE
                ENTERPRISE  luxN
                VARIABLES { eveDateTime, eveEventId, eveDescr, eveSeverity,
                             eveSysStatus, eveSource,  cpIpAddress, eveSeqNum }
                DESCRIPTION
			"This trap is sent when the standby MPM card
			 has been lost.  The
			 source is a 4 or 5 tuple specifying the type,
			 location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2100

        luxNprotectionLinkFailureTrap   TRAP-TYPE
                ENTERPRISE  luxN
                VARIABLES { eveDateTime, eveEventId, eveDescr, eveSeverity,
                             eveSysStatus, eveSource,  cpIpAddress, eveSeqNum }
                DESCRIPTION
			"This trap is sent when the protection link has
			 become unaviable due to either low receive power
			 level or an open fiber condition.  The
			 source is a 4 or 5 tuple specifying the type,
			 location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2101

        luxNprotectionLinkFailureResolvedTrap   TRAP-TYPE
                ENTERPRISE  luxN
                VARIABLES { eveDateTime, eveEventId, eveDescr, eveSeverity,
                             eveSysStatus, eveSource,  cpIpAddress, eveSeqNum }
                DESCRIPTION
			"This trap is sent when the protection link
			 has become available as a result of a corrective
			 action to resolve a previous failure condition.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2102

        luxNtopologyDatabaseChangedTrap   TRAP-TYPE
                ENTERPRISE  luxN
                VARIABLES { eveDateTime, eveEventId, eveDescr, eveSeverity,
                             eveSysStatus, eveSource,  cpIpAddress, eveSeqNum }
                DESCRIPTION
			"This trap is sent whenever a link has either been
			 added or deleted from the topology database.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2103

        luxNosamBiasCurrentOverLimitTrap   TRAP-TYPE
                ENTERPRISE  luxN
                VARIABLES { eveDateTime, eveEventId, eveDescr, eveSeverity,
                             eveSysStatus, eveSource,  cpIpAddress, eveSeqNum }
                DESCRIPTION
			"This trap is sent when the osam's bias current
                         exceeds 90% of allowed maximum.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2110

        luxNosamBiasCurrentNormal   TRAP-TYPE
                ENTERPRISE  luxN
                VARIABLES { eveDateTime, eveEventId, eveDescr, eveSeverity,
                             eveSysStatus, eveSource,  cpIpAddress, eveSeqNum }
                DESCRIPTION
			"This trap is sent when the osam's bias current
                         is within normal range.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2111

        luxNosamTecCurrentOverLimit   TRAP-TYPE
                ENTERPRISE  luxN
                VARIABLES { eveDateTime, eveEventId, eveDescr, eveSeverity,
                             eveSysStatus, eveSource,  cpIpAddress, eveSeqNum }
                DESCRIPTION
			"This trap is sent when the osam's TEC current
                         is above the specified limit.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2112

        luxNosamTecCurrentNormal   TRAP-TYPE
                ENTERPRISE  luxN
                VARIABLES { eveDateTime, eveEventId, eveDescr, eveSeverity,
                             eveSysStatus, eveSource,  cpIpAddress, eveSeqNum }
                DESCRIPTION
			"This trap is sent when the osam's TEC current
                         is within normal range.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2113

        luxNosamLaserTemperatureDrift   TRAP-TYPE
                ENTERPRISE  luxN
                VARIABLES { eveDateTime, eveEventId, eveDescr, eveSeverity,
                             eveSysStatus, eveSource,  cpIpAddress, eveSeqNum }
                DESCRIPTION
			"This trap is sent when the osam's laser temperature
                         drifts by more than +/- 2 degree Celsius.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2114

        luxNosamLaserTemperatureStable   TRAP-TYPE
                ENTERPRISE  luxN
                VARIABLES { eveDateTime, eveEventId, eveDescr, eveSeverity,
                             eveSysStatus, eveSource,  cpIpAddress, eveSeqNum }
                DESCRIPTION
			"This trap is sent when the osam's laser temperature
                         no longer drifts.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2115

        luxNosamMaxInputPowerReached   TRAP-TYPE
                ENTERPRISE  luxN
                VARIABLES { eveDateTime, eveEventId, eveDescr, eveSeverity,
                             eveSysStatus, eveSource,  cpIpAddress, eveSeqNum }
                DESCRIPTION
			"This trap is sent when the osam's input power
                         is greater than or equal to 9 dBm.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2116

        luxNosamInputPowerBackDownNormal   TRAP-TYPE
                ENTERPRISE  luxN
                VARIABLES { eveDateTime, eveEventId, eveDescr, eveSeverity,
                             eveSysStatus, eveSource,  cpIpAddress, eveSeqNum }
                DESCRIPTION
			"This trap is sent when the osam's input power
                         has fallen within normal range.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2117

        luxNosamMaxOutputPowerReached   TRAP-TYPE
                ENTERPRISE  luxN
                VARIABLES { eveDateTime, eveEventId, eveDescr, eveSeverity,
                             eveSysStatus, eveSource,  cpIpAddress, eveSeqNum }
                DESCRIPTION
			"This trap is sent when the osam's output power
                         is greater than or equal to 13 dBm.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2118

        luxNosamOutputPowerNormal   TRAP-TYPE
                ENTERPRISE  luxN
                VARIABLES { eveDateTime, eveEventId, eveDescr, eveSeverity,
                             eveSysStatus, eveSource,  cpIpAddress, eveSeqNum }
                DESCRIPTION
			"This trap is sent when the osam's output power
                         is within normal range.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2119

        luxNosamOpticalGainDeltaExceeded   TRAP-TYPE
                ENTERPRISE  luxN
                VARIABLES { eveDateTime, eveEventId, eveDescr, eveSeverity,
                             eveSysStatus, eveSource,  cpIpAddress, eveSeqNum }
                DESCRIPTION
			"This trap is sent when the osam's gain delta
                         is greater than or equal to 4 dB.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2120

        luxNosamOpticalGainDeltaNormal   TRAP-TYPE
                ENTERPRISE  luxN
                VARIABLES { eveDateTime, eveEventId, eveDescr, eveSeverity,
                             eveSysStatus, eveSource,  cpIpAddress, eveSeqNum }
                DESCRIPTION
			"This trap is sent when the osam's gain delta
                         is less than 4 dB.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2121

        luxNosamMinInputPowerBelowLimit   TRAP-TYPE
                ENTERPRISE  luxN
                VARIABLES { eveDateTime, eveEventId, eveDescr, eveSeverity,
                             eveSysStatus, eveSource,  cpIpAddress, eveSeqNum }
                DESCRIPTION
			"This trap is sent when the osam's input power is
                         less than or equal to -30 dBm.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2122

        luxNosamInputPowerBackUpNormal   TRAP-TYPE
                ENTERPRISE  luxN
                VARIABLES { eveDateTime, eveEventId, eveDescr, eveSeverity,
                             eveSysStatus, eveSource,  cpIpAddress, eveSeqNum }
                DESCRIPTION
			"This trap is sent when the osam's input power
                         has risen within normal range.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2123

        luxNosamSingleAprSensorFailed   TRAP-TYPE
                ENTERPRISE  luxN
                VARIABLES { eveDateTime, eveEventId, eveDescr, eveSeverity,
                             eveSysStatus, eveSource,  cpIpAddress, eveSeqNum }
                DESCRIPTION
			"This trap is sent when the osam's APR sensor is
                         not functioning.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2124

        luxNosamSingleAprSensorNormal   TRAP-TYPE
                ENTERPRISE  luxN
                VARIABLES { eveDateTime, eveEventId, eveDescr, eveSeverity,
                             eveSysStatus, eveSource,  cpIpAddress, eveSeqNum }
                DESCRIPTION
			"This trap is sent when the osam's APR sensor has
                         become functional.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2125

        luxNosamDualAprSensorFailed   TRAP-TYPE
                ENTERPRISE  luxN
                VARIABLES { eveDateTime, eveEventId, eveDescr, eveSeverity,
                             eveSysStatus, eveSource,  cpIpAddress, eveSeqNum }
                DESCRIPTION
			"This trap is sent when both of the osam's APR sensors 
                         are not functioning.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2126

        luxNosamDualAprSensorNormal   TRAP-TYPE
                ENTERPRISE  luxN
                VARIABLES { eveDateTime, eveEventId, eveDescr, eveSeverity,
                             eveSysStatus, eveSource,  cpIpAddress, eveSeqNum }
                DESCRIPTION
			"This trap is sent when both of the osam's APR sensors 
                         has become functional.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2127

        luxNosamFiberDisconnected   TRAP-TYPE
                ENTERPRISE  luxN
                VARIABLES { eveDateTime, eveEventId, eveDescr, eveSeverity,
                             eveSysStatus, eveSource,  cpIpAddress, eveSeqNum }
                DESCRIPTION
			"This trap is sent when a fiber disconnect condition
                         has been detected on an osam module.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2128

        luxNosamFiberConnected   TRAP-TYPE
                ENTERPRISE  luxN
                VARIABLES { eveDateTime, eveEventId, eveDescr, eveSeverity,
                             eveSysStatus, eveSource,  cpIpAddress, eveSeqNum }
                DESCRIPTION
			"This trap is sent when a fiber connect condition
                         has been detected after a fiber disconnect on an osam 
                         module.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2129

        luxNosamControlChanged   TRAP-TYPE
                ENTERPRISE  luxN
                VARIABLES { eveDateTime, eveEventId, eveDescr, eveSeverity,
                             eveSysStatus, eveSource,  cpIpAddress, eveSeqNum }
                DESCRIPTION
			"This trap is sent when either the current control or
			 gain control has been changed.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2130

        luxNosamLaserModuleOn   TRAP-TYPE
                ENTERPRISE  luxN
                VARIABLES { eveDateTime, eveEventId, eveDescr, eveSeverity,
                             eveSysStatus, eveSource,  cpIpAddress, eveSeqNum }
                DESCRIPTION
			"This trap is sent when the laser module has
			 been turned on by the osam firmware.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2131

        luxNosamLaserModuleOff   TRAP-TYPE
                ENTERPRISE  luxN
                VARIABLES { eveDateTime, eveEventId, eveDescr, eveSeverity,
                             eveSysStatus, eveSource,  cpIpAddress, eveSeqNum }
                DESCRIPTION
			"This trap is sent when the laser module has
			 been turned off by the osam firmware.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2132

        luxNipAuthenticationFailure   TRAP-TYPE
                ENTERPRISE  luxN
                VARIABLES { eveDateTime, eveEventId, eveDescr, eveSeverity,
                             eveSysStatus, eveSource,  cpIpAddress, eveSeqNum }
                DESCRIPTION
			"Not yet supported.  This trap is sent when access
			 from an invalid IP address based on the ACL has
			 been detected.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2133

	luxNftpCompletedTrap   TRAP-TYPE
                ENTERPRISE  luxN
                VARIABLES { eveDateTime, eveEventId, eveDescr, eveSeverity,
                             eveSysStatus, eveSource,  cpIpAddress, eveSeqNum }
                DESCRIPTION
			"This trap is sent when the ftp session has
			 been disconnected.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2134

	luxNftpHostFailedTrap   TRAP-TYPE
                ENTERPRISE  luxN
                VARIABLES { eveDateTime, eveEventId, eveDescr, eveSeverity,
                             eveSysStatus, eveSource,  cpIpAddress, eveSeqNum }
                DESCRIPTION
			"This trap is sent when the MPM is unable to
			 connect to the ftp host. 
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2135

	luxNimageUpdateInProgressTrap   TRAP-TYPE
                ENTERPRISE  luxN
                VARIABLES { eveDateTime, eveEventId, eveDescr, eveSeverity,
                             eveSysStatus, eveSource,  cpIpAddress, eveSeqNum }
                DESCRIPTION
			"This trap is sent when an module image is being
			 downloaded to MPM through ftp. 
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2136

	luxNimageUpdateSuccessTrap   TRAP-TYPE
                ENTERPRISE  luxN
                VARIABLES { eveDateTime, eveEventId, eveDescr, eveSeverity,
                             eveSysStatus, eveSource,  cpIpAddress, eveSeqNum }
                DESCRIPTION
			"This trap is sent when a module image download to
			 MPM through ftp has been completed successfully.   
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2137

	luxNimageUpdateFailedTrap   TRAP-TYPE
                ENTERPRISE  luxN
                VARIABLES { eveDateTime, eveEventId, eveDescr, eveSeverity,
                             eveSysStatus, eveSource,  cpIpAddress, eveSeqNum }
                DESCRIPTION
			"This trap is sent when a module image download
			 to MPM through ftp has failed.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2138

	luxNmoduleUpdateInProgressTrap   TRAP-TYPE
                ENTERPRISE  luxN
                VARIABLES { eveDateTime, eveEventId, eveDescr, eveSeverity,
                             eveSysStatus, eveSource,  cpIpAddress, eveSeqNum }
                DESCRIPTION
			"This trap is sent when a module image is being
			 transferred from the MPM to the module.  
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2139
		
	luxNmoduleUpdateSuccessTrap   TRAP-TYPE
                ENTERPRISE  luxN
                VARIABLES { eveDateTime, eveEventId, eveDescr, eveSeverity,
                             eveSysStatus, eveSource,  cpIpAddress, eveSeqNum }
                DESCRIPTION
			"This trap is sent when a module image transfer
			 from the MPM to the module has been completed
			 successfully.  
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2140

	luxNmoduleUpdateFailedTrap   TRAP-TYPE
                ENTERPRISE  luxN
                VARIABLES { eveDateTime, eveEventId, eveDescr, eveSeverity,
                             eveSysStatus, eveSource,  cpIpAddress, eveSeqNum }
                DESCRIPTION
			"This trap is sent when a module image transfer
			 from the MPM to the module has failed.  
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2141

        luxNethernetLinkFailure   TRAP-TYPE
                ENTERPRISE  luxN
                VARIABLES { eveDateTime, eveEventId, eveDescr, eveSeverity,
                             eveSysStatus, eveSource,  cpIpAddress, eveSeqNum }
                DESCRIPTION
			"This trap is sent upon detection of the ethernet
			 link failure on the MPM.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2142

        luxNethernetLinkFailureResolved   TRAP-TYPE
                ENTERPRISE  luxN
                VARIABLES { eveDateTime, eveEventId, eveDescr, eveSeverity,
                             eveSysStatus, eveSource,  cpIpAddress, eveSeqNum }
                DESCRIPTION
			"This trap is sent upon resolution of the ethernet
			 link failure on the MPM.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2143

  luxNcardMismatchTrap   TRAP-TYPE
                ENTERPRISE  luxN
                VARIABLES { eveDateTime, eveEventId, eveDescr, eveSeverity,
                             eveSysStatus, eveSource,  cpIpAddress, eveSeqNum }
                DESCRIPTION
			"This trap is sent when a card mismatch is found in a given slot.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2145

  luxNpwrFeedLowVoltageTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 reaches very close to the shutdown voltage.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2146

  luxNpwrFeedLowVoltageRecoveryTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 recovers from the low voltage level condition .
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2147

  luxNpwrFeedOKTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 is within the operating window of the chassis .
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2148

  luxNpwrFeedFailureTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 is either too low or too high to operate the chassis
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2149

  luxNpwrFeedBrkOpenTrap   TRAP-TYPE
                ENTERPRISE  luxN
                VARIABLES { eveDateTime, eveEventId, eveDescr, eveSeverity,
                             eveSysStatus, eveSource,  cpIpAddress, eveSeqNum }
                DESCRIPTION
			"This trap is sent when a user manually flips open the breaker relay
			 switch attached to that feed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2150

  luxNextCritAlmInpTrap   TRAP-TYPE
                ENTERPRISE  luxN
                VARIABLES { eveDateTime, eveEventId, eveDescr, eveSeverity,
                             eveSysStatus, eveSource,  cpIpAddress, eveSeqNum }
                DESCRIPTION
			"This trap is sent when an alarm gets generated at an external
			 alarm input that is configured for critical severity.
			 The source is a 4 or 5 tuple
			 specifying the type, location, shelf, slot ID, and
			 optionally the port number of the source of the
			 event.  In the case of the power supply, fan and ext. alarm input,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2151

  luxNextMajAlmInpTrap   TRAP-TYPE
                ENTERPRISE  luxN
                VARIABLES { eveDateTime, eveEventId, eveDescr, eveSeverity,
                             eveSysStatus, eveSource,  cpIpAddress, eveSeqNum }
                DESCRIPTION
			"This trap is sent when an alarm gets generated at an external
			 alarm input that is configured for majority severity.
			 The source is a 4 or 5 tuple
			 specifying the type, location, shelf, slot ID, and
			 optionally the port number of the source of the
			 event.  In the case of the power supply, fan and ext. alarm input,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2152

  luxNextMinorAlmInpTrap   TRAP-TYPE
                ENTERPRISE  luxN
                VARIABLES { eveDateTime, eveEventId, eveDescr, eveSeverity,
                             eveSysStatus, eveSource,  cpIpAddress, eveSeqNum }
                DESCRIPTION
			"This trap is sent when an alarm gets generated at an external
			 alarm input that is configured for minor severity.
			 The source is a 4 or 5 tuple
			 specifying the type, location, shelf, slot ID, and
			 optionally the port number of the source of the
			 event.  In the case of the power supply, fan and ext. alarm input,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2153

  luxNextClearAlmInpTrap   TRAP-TYPE
                ENTERPRISE  luxN
                VARIABLES { eveDateTime, eveEventId, eveDescr, eveSeverity,
                             eveSysStatus, eveSource,  cpIpAddress, eveSeqNum }
                DESCRIPTION
			"This trap is sent when an alarm gets cleared at an external
			 alarm input.
			 The source is a 4 or 5 tuple
			 specifying the type, location, shelf, slot ID, and
			 optionally the port number of the source of the
			 event.  In the case of the power supply, fan and ext. alarm input,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2154

  luxNpwrFeedOverVoltageTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 reaches very close to the shutdown voltage on the higher side.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2155

  luxNpwrFeedOverVoltageRecoveryTrap   TRAP-TYPE
                ENTERPRISE  luxN
                VARIABLES { eveDateTime, eveEventId, eveDescr, eveSeverity,
                             eveSysStatus, eveSource,  cpIpAddress, eveSeqNum }
                DESCRIPTION
			"This trap is sent when the DC voltage level on the power feed
			 recovers from the over voltage level condition .
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2156

  luxNstandbySWMismatchTrap   TRAP-TYPE
                ENTERPRISE  luxN
                VARIABLES { eveDateTime, eveEventId, eveDescr, eveSeverity,
                             eveSysStatus, eveSource,  cpIpAddress, eveSeqNum }
                DESCRIPTION
			"This trap is sent when there is a mismatch between the software version of 
			 standby and active MPM.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2157

  luxNstandbyDBNotSupportedTrap   TRAP-TYPE
                ENTERPRISE  luxN
                VARIABLES { eveDateTime, eveEventId, eveDescr, eveSeverity,
                             eveSysStatus, eveSource,  cpIpAddress, eveSeqNum }
                DESCRIPTION
			"This trap is sent when the standby MPM do not 
			 support Active MPM's database.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2158

  luxNactiveStandbySWAlignedTrap   TRAP-TYPE
                ENTERPRISE  luxN
                VARIABLES { eveDateTime, eveEventId, eveDescr, eveSeverity,
                             eveSysStatus, eveSource,  cpIpAddress, eveSeqNum }
                DESCRIPTION
			"This trap is sent when the software version between 
			 standby and active MPM is aligned.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2159

  luxNactiveStandbyDBAlignedTrap   TRAP-TYPE
                ENTERPRISE  luxN
                VARIABLES { eveDateTime, eveEventId, eveDescr, eveSeverity,
                             eveSysStatus, eveSource,  cpIpAddress, eveSeqNum }
                DESCRIPTION
			"This trap is sent when the database version between 
			 standby and active MPM is aligned.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 2160

        luxNmpmBootImageChangedTrap   TRAP-TYPE
                ENTERPRISE  luxN
                VARIABLES { eveDateTime, eveEventId, eveDescr, eveSeverity,
                             eveSysStatus, eveSource,  cpIpAddress, eveSeqNum }
                DESCRIPTION
			"This trap is sent to indicate that the executable
			 image for the MPM has been changed. Upon reset of
			 the MPM card, this new bootfile will be used.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3002

        luxNdateTimeSetTrap   TRAP-TYPE
                ENTERPRISE  luxN
                VARIABLES { eveDateTime, eveEventId, eveDescr, eveSeverity,
                             eveSysStatus, eveSource,  cpIpAddress, eveSeqNum }
                DESCRIPTION
			"This trap is sent to indicate that the date and
			 time of the system has been changed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3003

        luxNuserAddedTrap   TRAP-TYPE
                ENTERPRISE  luxN
                VARIABLES { eveDateTime, eveEventId, eveDescr, eveSeverity,
                             eveSysStatus, eveSource,  cpIpAddress, eveSeqNum }
                DESCRIPTION
			"This trap is sent to indicate that a new user
			 has been added to the system.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3004

        luxNuserDeletedTrap   TRAP-TYPE
                ENTERPRISE  luxN
                VARIABLES { eveDateTime, eveEventId, eveDescr, eveSeverity,
                             eveSysStatus, eveSource,  cpIpAddress, eveSeqNum }
                DESCRIPTION
			"This trap is sent to indicate that a user
			 has been deleted from the system.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3005

        luxNuserPasswordChangeTrap   TRAP-TYPE
                ENTERPRISE  luxN
                VARIABLES { eveDateTime, eveEventId, eveDescr, eveSeverity,
                             eveSysStatus, eveSource,  cpIpAddress, eveSeqNum }
                DESCRIPTION
			"This trap is sent to indicate that the password
			 of one of the user's has been changed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3006

        luxNuserLevelModifiedTrap   TRAP-TYPE
                ENTERPRISE  luxN
                VARIABLES { eveDateTime, eveEventId, eveDescr, eveSeverity,
                             eveSysStatus, eveSource,  cpIpAddress, eveSeqNum }
                DESCRIPTION
			"This trap is sent to indicate that the privilege
			 level of one of the user's has been changed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3007

        luxNsystemNameChangeTrap   TRAP-TYPE
                ENTERPRISE  luxN
                VARIABLES { eveDateTime, eveEventId, eveDescr, eveSeverity,
                             eveSysStatus, eveSource,  cpIpAddress, eveSeqNum }
                DESCRIPTION
			"This trap is sent to indicate that the name of
			 the system has been changed.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3008

        luxNcardAddedTrap   TRAP-TYPE
                ENTERPRISE  luxN
                VARIABLES { eveDateTime, eveEventId, eveDescr, eveSeverity,
                             eveSysStatus, eveSource,  cpIpAddress, eveSeqNum }
                DESCRIPTION
			"This trap is sent to indicate that a new card has
			 been added to the system through either CLI/SNMP
			 in the specified source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3009

        luxNcardDeletedTrap   TRAP-TYPE
                ENTERPRISE  luxN
                VARIABLES { eveDateTime, eveEventId, eveDescr, eveSeverity,
                             eveSysStatus, eveSource,  cpIpAddress, eveSeqNum }
                DESCRIPTION
			"This trap is sent to indicate that a card has
			 been deleted from the system through either
			 CLI/SNMP in the specified source field.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3010

        luxNmpmRedundancySwitchOverTrap   TRAP-TYPE
                ENTERPRISE  luxN
                VARIABLES { eveDateTime, eveEventId, eveDescr, eveSeverity,
                             eveSysStatus, eveSource,  cpIpAddress, eveSeqNum }
                DESCRIPTION
			"This trap is sent to indicate that a mpm
			 switchover has occurred.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3011

        luxNconnectionAddedTrap   TRAP-TYPE
                ENTERPRISE  luxN
                VARIABLES { eveDateTime, eveEventId, eveDescr, eveSeverity,
                             eveSysStatus, eveSource,  cpIpAddress, eveSeqNum }
                DESCRIPTION
			"This trap is sent to indicate that a connectino
			 has been added to an ofcm/ofcd card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3012

        luxNconnectionDeletedTrap   TRAP-TYPE
                ENTERPRISE  luxN
                VARIABLES { eveDateTime, eveEventId, eveDescr, eveSeverity,
                             eveSysStatus, eveSource,  cpIpAddress, eveSeqNum }
                DESCRIPTION
			"This trap is sent to indicate that a connection
			 has been deleted from an ofcm/ofcd card.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3013

        luxNipAddressChangedTrap   TRAP-TYPE
                ENTERPRISE  luxN
                VARIABLES { eveDateTime, eveEventId, eveDescr, eveSeverity,
                             eveSysStatus, eveSource,  cpIpAddress, eveSeqNum }
                DESCRIPTION
			"This trap is sent to indicate that the IP address
			 has been changed successfully.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3014

        luxNipNetmaskChangedTrap   TRAP-TYPE
                ENTERPRISE  luxN
                VARIABLES { eveDateTime, eveEventId, eveDescr, eveSeverity,
                             eveSysStatus, eveSource,  cpIpAddress, eveSeqNum }
                DESCRIPTION
			"This trap is sent to indicate that the netmask
			 has been changed successfully.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3015

        luxNdefaultGatewayChangedTrap   TRAP-TYPE
                ENTERPRISE  luxN
                VARIABLES { eveDateTime, eveEventId, eveDescr, eveSeverity,
                             eveSysStatus, eveSource,  cpIpAddress, eveSeqNum }
                DESCRIPTION
			"This trap is sent to indicate that the default
			 gateway has been changed successfully.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3016

	luxNGetCommunityChangeTrap   TRAP-TYPE
                ENTERPRISE  luxN
                VARIABLES { eveDateTime, eveEventId, eveDescr, eveSeverity,
                             eveSysStatus, eveSource,  cpIpAddress, eveSeqNum }
                DESCRIPTION
			"This trap is sent to indicate that the getcommunity
			 has been changed.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3017

	luxNSetCommunityChangeTrap   TRAP-TYPE
                ENTERPRISE  luxN
                VARIABLES { eveDateTime, eveEventId, eveDescr, eveSeverity,
                             eveSysStatus, eveSource,  cpIpAddress, eveSeqNum }
                DESCRIPTION
			"This trap is sent to indicate that the setcommunity
			 has been changed.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3018

	luxNModuleResetTrap   TRAP-TYPE
                ENTERPRISE  luxN
                VARIABLES { eveDateTime, eveEventId, eveDescr, eveSeverity,
                             eveSysStatus, eveSource,  cpIpAddress, eveSeqNum }
                DESCRIPTION
			"This trap is sent to indicate that a module has
			 been reset.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3019

        luxNtopologyRediscoveredTrap   TRAP-TYPE
                ENTERPRISE  luxN
                VARIABLES { eveDateTime, eveEventId, eveDescr, eveSeverity,
                             eveSysStatus, eveSource,  cpIpAddress, eveSeqNum }
                DESCRIPTION
			"This trap is sent to indicate that the topology
			 database has been rediscovered which is triggered
			 through either CLI or snmp. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3020

        luxNcolorsimEnabledTrap   TRAP-TYPE
                ENTERPRISE  luxN
                VARIABLES { eveDateTime, eveEventId, eveDescr, eveSeverity,
                             eveSysStatus, eveSource,  cpIpAddress, eveSeqNum }
                DESCRIPTION
			"This trap is sent to indicate that the ColorSIM
			 feature has been enabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3021

        luxNcolorsimDisabledTrap   TRAP-TYPE
                ENTERPRISE  luxN
                VARIABLES { eveDateTime, eveEventId, eveDescr, eveSeverity,
                             eveSysStatus, eveSource,  cpIpAddress, eveSeqNum }
                DESCRIPTION
			"This trap is sent to indicate that the ColorSIM
			 feature has been disabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3022

        luxNautoCutoffEnabledTrap   TRAP-TYPE
                ENTERPRISE  luxN
                VARIABLES { eveDateTime, eveEventId, eveDescr, eveSeverity,
                             eveSysStatus, eveSource,  cpIpAddress, eveSeqNum }
                DESCRIPTION
			"This trap is sent to indicate that the auto cutoff
			 feature has been enabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3023

        luxNautoCutoffDisabledTrap   TRAP-TYPE
                ENTERPRISE  luxN
                VARIABLES { eveDateTime, eveEventId, eveDescr, eveSeverity,
                             eveSysStatus, eveSource,  cpIpAddress, eveSeqNum }
                DESCRIPTION
			"This trap is sent to indicate that the auto cutoff
			 feature has been disabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3024

        luxNextAlarmsEnabledTrap   TRAP-TYPE
                ENTERPRISE  luxN
                VARIABLES { eveDateTime, eveEventId, eveDescr, eveSeverity,
                             eveSysStatus, eveSource,  cpIpAddress, eveSeqNum }
                DESCRIPTION
			"This trap is sent to indicate that the external
			 alarm closures have been enabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3025

        luxNextAlarmsDisabledTrap   TRAP-TYPE
                ENTERPRISE  luxN
                VARIABLES { eveDateTime, eveEventId, eveDescr, eveSeverity,
                             eveSysStatus, eveSource,  cpIpAddress, eveSeqNum }
                DESCRIPTION
			"This trap is sent to indicate that the external
			 alarm closures have been disabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3026

	luxNdlModuleActivatedTrap   TRAP-TYPE
                ENTERPRISE  luxN
                VARIABLES { eveDateTime, eveEventId, eveDescr, eveSeverity,
                             eveSysStatus, eveSource,  cpIpAddress, eveSeqNum }
                DESCRIPTION
			"This trap is sent to indicate that a module
			 activation, switching to another module image
			 version, has occurred.
			 The source is a 4 or 5 tuple specifying the
			 type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3027

        luxNhttpEnabledTrap   TRAP-TYPE
                ENTERPRISE  luxN
                VARIABLES { eveDateTime, eveEventId, eveDescr, eveSeverity,
                             eveSysStatus, eveSource,  cpIpAddress, eveSeqNum }
                DESCRIPTION
			"This trap is sent to indicate that the http
			 server has been enabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3032

        luxNhttpDisabledTrap   TRAP-TYPE
                ENTERPRISE  luxN
                VARIABLES { eveDateTime, eveEventId, eveDescr, eveSeverity,
                             eveSysStatus, eveSource,  cpIpAddress, eveSeqNum }
                DESCRIPTION
			"This trap is sent to indicate that the http
			 server has been disabled. The source is a
			 4 or 5 tuple specifying the type, location,
			 shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3033

        luxNstaticRouteAddedTrap   TRAP-TYPE
                ENTERPRISE  luxN
                VARIABLES { eveDateTime, eveEventId, eveDescr, eveSeverity,
                             eveSysStatus, eveSource,  cpIpAddress, eveSeqNum }
                DESCRIPTION
			"This trap is sent to indicate that a new route has
			 been added to the system through either CLI/SNMP
			 in the specified source field.
			 The source is a 4 or 5 tuple
			 specifying the type, location, shelf, slot ID, and
			 optionally the port number of the source of the
			 event.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure. The eveDescr  field consists of
			 trap description and the route information - local CC shelf, slot 
			 and destination IP address"
                ::= 3034

        luxNstaticRouteDeletedTrap   TRAP-TYPE
                ENTERPRISE  luxN
                VARIABLES { eveDateTime, eveEventId, eveDescr, eveSeverity,
                             eveSysStatus, eveSource,  cpIpAddress, eveSeqNum }
                DESCRIPTION
			"This trap is sent to indicate that a route has
			 been deleted from the system through either CLI/SNMP
			 in the specified source field.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure. The eveDescr  field consists of
			 trap description and the route information - local CC shelf, slot 
			 and destination IP address"
                ::= 3035


        luxNupsrProtectionSwitchOverSrc TRAP-TYPE
                ENTERPRISE  luxN
                VARIABLES { eveDateTime, eveEventId, eveDescr, eveSeverity,
                             eveSysStatus, eveSource,  cpIpAddress, eveSeqNum }
                DESCRIPTION
			"This trap is sent to indicate that UPSR protection switch over occurred 
			 on the source either through SNMP or CLI. If the module type is OCM
			 for this trap, then after issuing this trap it goes into standby mode.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3036

        luxNupsrProtectionSwitchOverDest TRAP-TYPE
                ENTERPRISE  luxN
                VARIABLES { eveDateTime, eveEventId, eveDescr, eveSeverity,
                             eveSysStatus, eveSource,  cpIpAddress, eveSeqNum }
                DESCRIPTION
			"This trap is sent to indicate that UPSR protection switch over occurred 
			 on the destination either through SNMP or CLI. If the module type is OCM
			 for this trap, then after issuing this trap it goes into active mode
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3037

        luxNimnIpAddressChanged  TRAP-TYPE
                ENTERPRISE  luxN
                VARIABLES { eveDateTime, eveEventId, eveDescr, eveSeverity,
                             eveSysStatus, eveSource,  cpIpAddress, eveSeqNum }
                DESCRIPTION
			"This trap is sent to indicate that a IMN Ip address is successfully
			 changed either through SNMP or CLI.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3038


        luxNupsrNormal  TRAP-TYPE
                ENTERPRISE  luxN
                VARIABLES { eveDateTime, eveEventId, eveDescr, eveSeverity,
                             eveSysStatus, eveSource,  cpIpAddress, eveSeqNum }
                DESCRIPTION
			"This trap is sent to indicate that UPSR is successfully
			 enabled either through SNMP or CLI on the system.
			 This is done once UPSR functionality is normal on the 
			 system.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3039

        luxNupsrDegraded  TRAP-TYPE
                ENTERPRISE  luxN
                VARIABLES { eveDateTime, eveEventId, eveDescr, eveSeverity,
                             eveSysStatus, eveSource,  cpIpAddress, eveSeqNum }
                DESCRIPTION
			"This trap is sent to indicate that UPSR is successfully
			 disabled either through SNMP, CLI or SPI driver on the system.
			 This is done after the UPSR functionality on the system is degraded
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3040

        luxNusrOneAlarmAction  TRAP-TYPE
                ENTERPRISE  luxN
                VARIABLES { eveDateTime, eveEventId, eveDescr, eveSeverity,
                             eveSysStatus, eveSource,  cpIpAddress, eveSeqNum }
                DESCRIPTION
			"This trap is sent to indicate that user has performed acknowledgment/
			 unacknowledgment/Clearing of a single alarm in the alarm log either 
			 through SNMP or CLI .
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3041

        luxNusrAllAlarmAction  TRAP-TYPE
                ENTERPRISE  luxN
                VARIABLES { eveDateTime, eveEventId, eveDescr, eveSeverity,
                             eveSysStatus, eveSource,  cpIpAddress, eveSeqNum }
                DESCRIPTION
			"This trap is sent to indicate that user has performed acknowledgment/
			 unacknowledgment/Clearing of all alarms in the alarm log either through 
			 SNMP or CLI .
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3042

        luxNringConfigurationChanged   TRAP-TYPE
                ENTERPRISE  luxN
                VARIABLES { eveDateTime, eveEventId, eveDescr, eveSeverity,
                             eveSysStatus, eveSource,  cpIpAddress, eveSeqNum }
                DESCRIPTION
			"This trap is sent to indicate that the user has changed the 
			 ring configuration either through deletion or addition of
			 ringId or pathId.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure. The eveDescr  field consists of
			 trap description and the cross connect information "
                ::= 3047

        luxNeventLogCleared   TRAP-TYPE
                ENTERPRISE  luxN
                VARIABLES { eveDateTime, eveEventId, eveDescr, eveSeverity,
                             eveSysStatus, eveSource,  cpIpAddress, eveSeqNum }
                DESCRIPTION
			"This trap is sent to indicate that the user has cleared the
			 event log either through CLI or SNMP.
			 The source is a 4 or 5 tuple
			 specifying the type, location, shelf, slot ID, and
			 optionally the port number of the source of the
			 event. Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 3048

	  luxNextAlarmInpTrap   TRAP-TYPE
					ENTERPRISE  luxN
					VARIABLES { eveDateTime, eveEventId, eveDescr, eveSeverity,
								 eveSysStatus, eveSource,  cpIpAddress, eveSeqNum }
					DESCRIPTION
				"This trap is sent when an user sets up alarm severity 
				 (crit/maj/minor/disable) on external alarm input.
				 The source is a 4 or 5 tuple
				 specifying the type, location, shelf, slot ID, and
				 optionally the port number of the source of the
				 event.  In the case of the power supply, fan and ext. alarm input,
				 the shelf number is set to 0.  Each event has an
				 unique event ID.  It also has a preset event
				 severity.  The severity or trap type may be:
				 critical, major, minor, or normal.  For a given
				 event severity, there is a corresponding system
				 status, not necessarily the same as the event
				 severity.  For each reported trap, the IP address
				 of the CP responsible for sending this trap is
				 also included in the trap structure."
					::= 3049

	  luxNextAudioAlarmTrap   TRAP-TYPE
					ENTERPRISE  luxN
					VARIABLES { eveDateTime, eveEventId, eveDescr, eveSeverity,
								 eveSysStatus, eveSource,  cpIpAddress, eveSeqNum }
					DESCRIPTION
				"This trap is sent when an user enables or disables audio alarm.
				 The source is a 4 or 5 tuple
				 specifying the type, location, shelf, slot ID, and
				 optionally the port number of the source of the
				 event.  In the case of the power supply, fan and ext. alarm input,
				 the shelf number is set to 0.  Each event has an
				 unique event ID.  It also has a preset event
				 severity.  The severity or trap type may be:
				 critical, major, minor, or normal.  For a given
				 event severity, there is a corresponding system
				 status, not necessarily the same as the event
				 severity.  For each reported trap, the IP address
				 of the CP responsible for sending this trap is
				 also included in the trap structure."
					::= 3050



        luxNlogonIntruderTrap   TRAP-TYPE
                ENTERPRISE  luxN
                VARIABLES { eveDateTime, eveEventId, eveDescr, eveSeverity,
                             eveSysStatus, eveSource,  cpIpAddress, eveSeqNum }
                DESCRIPTION
			"This trap is sent to indicate that someone is
			 repeatly trying to logon using an invalid
			 password.  The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 4000

        luxNcpAuthenticationErrorTrap   TRAP-TYPE
                ENTERPRISE  luxN
                VARIABLES { eveDateTime, eveEventId, eveDescr, eveSeverity,
                             eveSysStatus, eveSource,  cpIpAddress, eveSeqNum }
                DESCRIPTION
			"This trap is sent to indicate that an invalid
			 login attempt has been detected.
			 The source is a 4 or 5 tuple
			 specifying the type, location, shelf, slot ID, and
			 optionally the port number of the source of the
			 event.  In the case of the power supply and fan,
			 the shelf number is set to 0.  Each event has an
			 unique event ID.  It also has a preset event
			 severity.  The severity or trap type may be:
			 critical, major, minor, or normal.  For a given
			 event severity, there is a corresponding system
			 status, not necessarily the same as the event
			 severity.  For each reported trap, the IP address
			 of the CP responsible for sending this trap is
			 also included in the trap structure."
                ::= 4003


END
