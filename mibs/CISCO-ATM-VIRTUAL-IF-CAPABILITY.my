-- *****************************************************************
-- ciscoAtmVirtualIfCapabilities MIB
--
-- AGENT-CAPABILITIES for CISCO-ATM-VIRTUAL-IF-MIB 
--
-- May 2002, Subra Hegde
--
-- Copyright(c) 2002 by Cisco Systems,Inc.
--
-- *****************************************************************

CISCO-ATM-VIRTUAL-IF-CAPABILITY DEFINITIONS ::= BEGIN
IMPORTS
        MODULE-IDENTITY
                FROM SNMPv2-SMI
        AGENT-CAPABILITIES
                FROM SNMPv2-CONF
        Unsigned32
                FROM CISCO-TC
        ciscoAgentCapability
                FROM CISCO-SMI;   

ciscoAtmVirtualIfCapability MODULE-IDENTITY
        LAST-UPDATED    "200205140000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for 
                CISCO-ATM-VIRTUAL-IF-MIB.
  
                - cavIfCapmVirtualIfCapabilityV2R00 is
                  for AXSM module in Release 2.0.

                - cavIfCapabilityAxsmV2R0010 is
                  for AXSM Service Module in Release 2.0.10.       

                - cavIfCapabilityAxsmeV2R0160 is
                  for AXSM-E Service Module in Release 2.1.60."

        REVISION       "200205140000Z"
        DESCRIPTION
                "Initial version of the MIB"
        ::= { ciscoAgentCapability 9999 }

cavIfCapabilityAxsmV2R00 AGENT-CAPABILITIES

PRODUCT-RELEASE  "MGX8850 Release 2.00"
STATUS           current
DESCRIPTION      "CISCO-ATM-VIRTUAL-IF-MIB Capabilities for
                 AXSM Service Module."

SUPPORTS CISCO-ATM-VIRTUAL-IF-MIB
INCLUDES { caviMIBGroup,
           caviEgressStatMIBGroup,
           caviIngressStatMIBGroup 
}

VARIATION    caviIfType
SYNTAX       INTEGER { uni(1),nni(2) }
DESCRIPTION  "Does not support vnni(3), vuni(4)."

VARIATION    caviMinRate
SYNTAX       Unsigned32 (50..5651320)
DESCRIPTION  "The upper limit is the maximum rate for 
             oc48 which is 5651320 cells/sec."

VARIATION    caviMaxRate
SYNTAX       Unsigned32 (50..5651320)
DESCRIPTION  "The upper limit is the maximum rate for 
             oc48 which is 5651320 cells/sec."

VARIATION    caviEgrRMCells
DESCRIPTION  "value is always 0."
        
VARIATION    caviEgrXmtEFCICells
DESCRIPTION  "value is always 0."

VARIATION    caviEgrRcvEFCICells
DESCRIPTION  "value is always 0."

VARIATION    caviEgrXmtOAMCells
DESCRIPTION  "value is always 0."

VARIATION    caviIngRMCells
DESCRIPTION  "value is always 0."
        
VARIATION    caviIngXmtEFCICells
DESCRIPTION  "value is always 0."

VARIATION    caviIngRcvEFCICells
DESCRIPTION  "value is always 0."

VARIATION    caviIngXmtOAMCells
DESCRIPTION  "value is always 0."

    ::= { ciscoAtmVirtualIfCapability 1 }

cavIfCapabilityAxsmV2R0010 AGENT-CAPABILITIES

PRODUCT-RELEASE "MGX8850 Release 2.0.10"
STATUS          current
DESCRIPTION     "CISCO-ATM-VIRTUAL-IF-MIB Capabilities for
                AXSM Service Module."

SUPPORTS CISCO-ATM-VIRTUAL-IF-MIB
INCLUDES { caviMIBGroup,
           caviEgressStatMIBGroup,
           caviIngressStatMIBGroup 
}

VARIATION    caviIfType
SYNTAX       INTEGER { uni(1),nni(2), vnni(3) }
DESCRIPTION  "Does not support vuni(4)."

VARIATION    caviMinRate
SYNTAX       Unsigned32 (50..5651320)
DESCRIPTION  "The upper limit is the maximum rate for 
             oc48 which is 5651320 cells per sec"

VARIATION    caviMaxRate
SYNTAX       Unsigned32 (50..5651320)
DESCRIPTION  "The upper limit is the maximum rate for 
             oc48 which is 5651320 cells per sec."

VARIATION    caviEgrRMCells
ACCESS       not-implemented
DESCRIPTION  "Object not supported"
        
VARIATION    caviEgrXmtEFCICells
ACCESS       not-implemented
DESCRIPTION  "Object not supported"

VARIATION    caviEgrRcvEFCICells
ACCESS       not-implemented
DESCRIPTION  "Object not supported"

VARIATION    caviEgrXmtOAMCells
ACCESS       not-implemented
DESCRIPTION  "Object not supported"

VARIATION    caviHEgrXmtClp0Cells
ACCESS       not-implemented
DESCRIPTION  "Object not supported"

VARIATION    caviHEgrXmtClp1Cells
ACCESS       not-implemented
DESCRIPTION  "Object not supported"

VARIATION    caviIngRMCells
ACCESS       not-implemented
DESCRIPTION  "Object not supported"
        
VARIATION    caviIngXmtEFCICells
ACCESS       not-implemented
DESCRIPTION  "Object not supported"

VARIATION    caviIngRcvEFCICells
ACCESS       not-implemented
DESCRIPTION  "Object not supported"

VARIATION    caviIngRcvOAMCells
ACCESS       not-implemented
DESCRIPTION  "Object not supported"

VARIATION    caviHIngRcvClp0Cells
ACCESS       not-implemented
DESCRIPTION  "Object not supported"

VARIATION    caviHIngRcvClp1Cells
ACCESS       not-implemented
DESCRIPTION  "Object not supported"

    ::= { ciscoAtmVirtualIfCapability 2 }

cavIfCapabilityAxsmeV2R0160 AGENT-CAPABILITIES

PRODUCT-RELEASE  "MGX8850 Release 2.1.60"
STATUS           current
DESCRIPTION      "CISCO-ATM-VIRTUAL-IF-MIB Capabilities for
                 Enhanced AXSM (AXSM-E)module."

SUPPORTS CISCO-ATM-VIRTUAL-IF-MIB
INCLUDES { caviMIBGroup,
           caviEgressStatMIBGroup,
           caviIngressStatMIBGroup, 
           caviEgressIntervalMIBGroup 
}

VARIATION    caviIfType
SYNTAX       INTEGER { uni(1),nni(2), vnni(3) }
DESCRIPTION  "Does not support vuni(4)."

VARIATION    caviMinRate
SYNTAX       Unsigned32 (50..1412830)
DESCRIPTION  "The upper limit is the maximum rate for 
             oc12 which is 1412830 cells per sec"

VARIATION    caviMaxRate
SYNTAX       Unsigned32 (50..1412830)
DESCRIPTION  "The upper limit is the maximum rate for 
             oc12 which is 1412830 cells per sec."

VARIATION    caviEgrRMCells
ACCESS       not-implemented
DESCRIPTION  "Object not supported"
        
VARIATION    caviEgrXmtEFCICells
ACCESS       not-implemented
DESCRIPTION  "Object not supported"

VARIATION    caviEgrRcvEFCICells
ACCESS       not-implemented
DESCRIPTION  "Object not supported"

VARIATION    caviEgrXmtOAMCells
ACCESS       not-implemented
DESCRIPTION  "Object not supported"

VARIATION    caviHEgrXmtClp0Cells
ACCESS       not-implemented
DESCRIPTION  "Object not supported"

VARIATION    caviHEgrXmtClp1Cells
ACCESS       not-implemented
DESCRIPTION  "Object not supported"

VARIATION    caviIngRMCells
ACCESS       not-implemented
DESCRIPTION  "Object not supported"
        
VARIATION    caviIngXmtEFCICells
ACCESS       not-implemented
DESCRIPTION  "Object not supported"

VARIATION    caviIngRcvEFCICells
ACCESS       not-implemented
DESCRIPTION  "Object not supported"

VARIATION    caviIngRcvOAMCells
ACCESS       not-implemented
DESCRIPTION  "Object not supported"

VARIATION    caviHIngRcvClp0Cells
ACCESS       not-implemented
DESCRIPTION  "Object not supported"

VARIATION    caviHIngRcvClp1Cells
ACCESS       not-implemented
DESCRIPTION  "Object not supported"

    ::= { ciscoAtmVirtualIfCapability 3 }

END
