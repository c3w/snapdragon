-- *****************************************************************
-- CISCO-AAA-SERVER-CAPABILITY.my:  Cisco AAA Server MIB AGENT-CAPABILITIES
--
-- January 20, 2000 - Mark W. Eklund
--
-- Copyright (c) 1999, 2000 by cisco Systems, Inc.
-- All rights reserved.
--
-- *****************************************************************

CISCO-AAA-SERVER-CAPABILITY DEFINITIONS ::= BEGIN


IMPORTS
        MODULE-IDENTITY
                FROM SNMPv2-SMI
        AGENT-CAPABILITIES
                FROM SNMPv2-CONF
        ciscoAgentCapability
                FROM CISCO-SMI;

ciscoAAAServerCapability MODULE-IDENTITY
        LAST-UPDATED    "200001200000Z"
        ORGANIZATION    "Cisco Systems, Inc."
        CONTACT-INFO
                "       Cisco Systems
                        Customer Service

                Postal: 170 W Tasman Drive
                        San Jose, CA  95134
                        USA

                   Tel: +1 800 553-NETS

                E-mail: cs-aaa@cisco.com"
        DESCRIPTION
                "Agent capabilities for CISCO-AAA-SERVER-MIB"
        ::= { ciscoAgentCapability 129 }

ciscoAAAServerCapabilityV10R00 AGENT-CAPABILITIES

PRODUCT-RELEASE "Cisco IOS 12.0(4)XJ"
        STATUS          current
        DESCRIPTION     "Cisco AAA Server MIB capabilities"

        SUPPORTS        CISCO-AAA-SERVER-MIB
        INCLUDES        {casStatisticsGroup, casConfigGroup, 
                         casServerNotificationGroup }

        VARIATION       casConfigEntry
                        CREATION-REQUIRES       casAddress

        VARIATION       casAddress
                        ACCESS read-only
                        DESCRIPTION
                                "create is not yet supported"

        VARIATION       casAuthenPort
                        ACCESS read-only
                        DESCRIPTION
                                "create is not yet supported"

        VARIATION       casAcctPort
                        ACCESS read-only
                        DESCRIPTION
                                "create is not yet supported"

        VARIATION       casKey
                        ACCESS read-only
                        DESCRIPTION
                                "create is not yet supported"

        VARIATION       casConfigRowStatus
                        ACCESS read-only
                        DESCRIPTION
                                "create is not yet supported"

::= { ciscoAAAServerCapability 1 }

END
