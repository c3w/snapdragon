CISCO-HSRP-EXT-CAPABILITY DEFINITIONS ::= BEGIN

IMPORTS
        MODULE-IDENTITY
                FROM SNMPv2-SMI
        AGENT-CAPABILITIES
                FROM SNMPv2-CONF
        ciscoAgentCapability
                FROM CISCO-SMI;

ciscoHsrpExtCapability MODULE-IDENTITY
                LAST-UPDATED    "9808250000Z"
                ORGANIZATION    "Cisco Systems, Inc."
                CONTACT-INFO
                        "       Cisco Systems
                                Customer Service

                        Postal: 170 West Tasman Drive
                                San Jose, CA  95134
                                USA

                           Tel: +1 800 553-NETS

                        E-mail: cs-hsrp@cisco.com"
                DESCRIPTION
                        "Agent capabilities for CISCO-HSRP-EXT-MIB"
                REVISION        "9808250000Z"
                DESCRIPTION
                        "Initial version of this MIB module."
        ::= { ciscoAgentCapability 10001 }
ciscoHsrpExtCapabilityV12R0 AGENT-CAPABILITIES

PRODUCT-RELEASE "Cisco IOS 12.0(3)T"
STATUS          current
DESCRIPTION     "Cisco Hsrp Ext MIB capabilities"

SUPPORTS        CISCO-HSRP-EXT-MIB
INCLUDES        { cHsrpExtGroup, cHsrpExtIfBIA }

VARIATION	cHsrpExtIfTrackedPriority
ACCESS		read-only
DESCRIPTION	"Unable to create or modify"

VARIATION	cHsrpExtIfTrackedRowStatus
ACCESS		read-only
DESCRIPTION	"Unable to create or modify"

VARIATION	cHsrpExtSecAddrRowStatus
ACCESS		read-only
DESCRIPTION	"Unable to create or modify"

VARIATION	cHsrpExtIfUseBIA
ACCESS		read-only
DESCRIPTION	"Unable to create or modify"

VARIATION	cHsrpExtIfRowStatus
ACCESS		read-only
DESCRIPTION	"Unable to create or modify"

        ::= { ciscoHsrpExtCapability 1 }

END
