-- *****************************************************************
-- CISCO-VOICE-ATM-DIAL-CONTROL-MIB.my: Voice ATM Dial Control MIB 
--                                      file
--
-- April 1998, Steve Yang
-- Updated May 1999 Chris White
--
-- Copyright (c) 1998, 1999 by cisco Systems, Inc.
-- All rights reserved.
-- *****************************************************************

CISCO-VOICE-ATM-DIAL-CONTROL-MIB DEFINITIONS ::= BEGIN

IMPORTS
        MODULE-IDENTITY,
        OBJECT-TYPE
                FROM SNMPv2-SMI
        TEXTUAL-CONVENTION,
        DisplayString,
        TruthValue
                FROM SNMPv2-TC
        MODULE-COMPLIANCE,
        OBJECT-GROUP
                FROM SNMPv2-CONF
        CvcSpeechCoderRate,
        CvcFaxTransmitRate,
        CvcGUid,
        CvcInBandSignaling
                FROM CISCO-VOICE-COMMON-DIAL-CONTROL-MIB
        callActiveSetupTime,
        callActiveIndex
                FROM DIAL-CONTROL-MIB
        cCallHistoryIndex
                FROM CISCO-DIAL-CONTROL-MIB
        ifIndex
                FROM IF-MIB
        ciscoExperiment
                FROM CISCO-SMI;
 
ciscoVoiceAtmDialControlMIB MODULE-IDENTITY
        LAST-UPDATED    "9905070000Z"
        ORGANIZATION    "Cisco Systems, Inc."
        CONTACT-INFO
            "       Cisco Systems
                    Customer Service

            Postal: 170 W. Tasman Drive
                    San Jose, CA  95134
                    USA
 
            Tel: +1 800 553-NETS

            E-mail: cs-voice@cisco.com"
        DESCRIPTION
            "This MIB module enhances the IETF Dial Control MIB
             (RFC2128) by providing ATM management information over a
             data network."
        REVISION        "9903200000Z"
        DESCRIPTION
            "Add new objects for handling the following:
             [1] Call History object ids 6-17 to bring MIB inline with
                 stored Call History record.
             [2] Added Call Active Entry objects
             [3] Added Dialpeer Objects for VoATM "
        ::= { ciscoExperiment 35 }

-- Voice ATM Dial Control MIB objects definitions

ciscoVoiceAtmDialControlMIBObjects OBJECT IDENTIFIER ::=
       { ciscoVoiceAtmDialControlMIB 1 }

-- The Voice Dial Control MIB consists of the following groups
-- [1] Voice ATM Dial Control Call History Group (cvAtmCallHistory)
-- [2] Voice ATM Dial Control Call Active Group (cvAtmCallActive)
-- [3] Voice ATM Dial Control Dialpeer Group (cvAtmDialPeer)

cvAtmCallHistory        OBJECT IDENTIFIER ::=
        { ciscoVoiceAtmDialControlMIBObjects 1 }
cvAtmCallActive         OBJECT IDENTIFIER ::=
        { ciscoVoiceAtmDialControlMIBObjects 2 }
cvAtmDialPeer           OBJECT IDENTIFIER ::=
        { ciscoVoiceAtmDialControlMIBObjects 3 }

-- 
-- Textual Conventions
--

--
-- Session Protocol textual convention
--
CvAtmSessionProtocol ::= TEXTUAL-CONVENTION
        STATUS      current
        DESCRIPTION
        "Represents a Session Protocol used by Voice calls between a
         local and remote router via the ATM backbone.

         other          - none of the following.
         ciscoSwitched  - cisco proprietary ATM session protocol.
        "
        SYNTAX      INTEGER {
            other             (1),
            ciscoSwitched     (2)
        }     


--**********************************************************************
-- Voice over ATM Dial Control Call History Group
--**********************************************************************

--
-- Voice over ATM Call History Table
-- 

cvAtmCallHistoryTable OBJECT-TYPE
        SYNTAX      SEQUENCE OF CvAtmCallHistoryEntry
        MAX-ACCESS  not-accessible
        STATUS      current
        DESCRIPTION
            "This table is the ATM extension to the call history table of
             IETF Dial Control MIB. It contains ATM call leg information
             about specific voice over ATM call."
        ::= { cvAtmCallHistory 1 }

cvAtmCallHistoryEntry OBJECT-TYPE
        SYNTAX      CvAtmCallHistoryEntry
        MAX-ACCESS  not-accessible
        STATUS      current
        DESCRIPTION
            "The information regarding a single ATM call leg.
             An entry of this table is created when its associated call
             history entry in the IETF Dial Control MIB is created and
             the call history entry contains information for the call
             establishment to the peer on the data network backbone via
             a voice over ATM peer.
             Th the IETF Dial Control MIB is deleted."
        INDEX       { cCallHistoryIndex }
        ::= { cvAtmCallHistoryTable 1 }


CvAtmCallHistoryEntry ::=
        SEQUENCE {
            cvAtmCallHistoryConnectionId           CvcGUid,
            cvAtmCallHistoryVpi                    INTEGER,
            cvAtmCallHistoryVci                    INTEGER,
            cvAtmCallHistoryLowerIfName            DisplayString,
            cvAtmCallHistorySessionTarget          DisplayString,
            cvAtmCallHistorySubchannelID           INTEGER,
            cvAtmCallHistorySessionProtocol        CvAtmSessionProtocol,
            cvAtmCallHistoryCalledNumber           DisplayString,
            cvAtmCallHistoryDtmfRelay              TruthValue,
            cvAtmCallHistoryUseSeqNumbers          TruthValue
        }

cvAtmCallHistoryConnectionId OBJECT-TYPE
        SYNTAX      CvcGUid 
        MAX-ACCESS  read-only
        STATUS      current
        DESCRIPTION
            "The global call identifier for the ATM call."
        ::= { cvAtmCallHistoryEntry 1 }

cvAtmCallHistoryVpi OBJECT-TYPE
        SYNTAX      INTEGER (0..4095)
        MAX-ACCESS  read-only
        STATUS      current
        DESCRIPTION
            "The VPI used for this ATM connection."
        ::= { cvAtmCallHistoryEntry 2 }
 
cvAtmCallHistoryVci OBJECT-TYPE
        SYNTAX      INTEGER (0..65535)
        MAX-ACCESS  read-only
        STATUS      current
        DESCRIPTION
            "The VCI used for this ATM connection."
        ::= { cvAtmCallHistoryEntry 3 }

cvAtmCallHistoryLowerIfName OBJECT-TYPE
        SYNTAX      DisplayString
        MAX-ACCESS  read-only 
        STATUS      current
        DESCRIPTION
            "The ifName of the ATM interface associated with this
             call."
        ::= { cvAtmCallHistoryEntry 4 }

cvAtmCallHistorySessionTarget OBJECT-TYPE
        SYNTAX      DisplayString 
        MAX-ACCESS  read-only
        STATUS      current
        DESCRIPTION
            "The object specifies the session target of the peer that
             was used for the voice over ATM call. A zero length string
             indicates that the value is unavailable."
        ::= { cvAtmCallHistoryEntry 5 }

cvAtmCallHistorySubchannelID OBJECT-TYPE
        SYNTAX      INTEGER (0..255)
        MAX-ACCESS  read-only
        STATUS      current
        DESCRIPTION
            "The subchannel used for this ATM connection."
        ::= { cvAtmCallHistoryEntry 6 }

cvAtmCallHistorySessionProtocol OBJECT-TYPE
        SYNTAX      CvAtmSessionProtocol 
        MAX-ACCESS  read-only
        STATUS      current
        DESCRIPTION
            "Specifies the session protocol used on this call."
        ::= { cvAtmCallHistoryEntry 7 }

cvAtmCallHistoryCalledNumber OBJECT-TYPE
        SYNTAX      DisplayString
        MAX-ACCESS  read-only
        STATUS      current
        DESCRIPTION
            "Specifes the number called for trunk connection calls. A
             zero length string indicates that this data is unavailable."
        ::= { cvAtmCallHistoryEntry 8 }

cvAtmCallHistoryDtmfRelay OBJECT-TYPE
        SYNTAX      TruthValue
        MAX-ACCESS  read-only
        STATUS      current
        DESCRIPTION
            "Specifies if Dtmf Relay was enabled for the call."
        ::= { cvAtmCallHistoryEntry 9 }

cvAtmCallHistoryUseSeqNumbers OBJECT-TYPE
        SYNTAX      TruthValue
        MAX-ACCESS  read-only
        STATUS      current
        DESCRIPTION
            "Specifies if Sequence Numbers were used on the voice data
             packets."
        ::= { cvAtmCallHistoryEntry 10 }

--**********************************************************************
-- Voice over ATM Dial Control Call Active Group
--**********************************************************************

--
-- Voice over ATM Call Active Table
-- 

cvAtmCallActiveTable OBJECT-TYPE
        SYNTAX      SEQUENCE OF CvAtmCallActiveEntry
        MAX-ACCESS  not-accessible
        STATUS      current
        DESCRIPTION
            "This table is the ATM extension to the active call table of
             IETF Dial Control MIB. It contains ATM call leg information
             about specific voice over ATM call."
        ::= { cvAtmCallActive 1 }

cvAtmCallActiveEntry OBJECT-TYPE
        SYNTAX      CvAtmCallActiveEntry
        MAX-ACCESS  not-accessible
        STATUS      current
        DESCRIPTION
            "The information regarding a single ATM call leg.
             An entry of this table is created when its associated call
             active entry in the IETF Dial Control MIB is created. The
             call active entry contains information for the call
             establishment to the peer on the data network backbone via
             a voice over ATM peer.
             The entry is deleted when its associated call active entry
             in the IETF Dial Control MIB is deleted."
        INDEX       { callActiveSetupTime, callActiveIndex }
        ::= { cvAtmCallActiveTable 1 }


CvAtmCallActiveEntry ::=
        SEQUENCE {
            cvAtmCallActiveConnectionId             CvcGUid,
            cvAtmCallActiveVpi                      INTEGER,
            cvAtmCallActiveVci                      INTEGER,
            cvAtmCallActiveLowerIfName              DisplayString,
            cvAtmCallActiveSessionTarget            DisplayString,
            cvAtmCallActiveSubchannelID             INTEGER,
            cvAtmCallActiveSessionProtocol          CvAtmSessionProtocol,
            cvAtmCallActiveCalledNumber             DisplayString,
            cvAtmCallActiveDtmfRelay                TruthValue,
            cvAtmCallActiveUseSeqNumbers            TruthValue
        }

cvAtmCallActiveConnectionId OBJECT-TYPE
        SYNTAX      CvcGUid 
        MAX-ACCESS  read-only
        STATUS      current
        DESCRIPTION
            "The global call identifier for the ATM call."
        ::= { cvAtmCallActiveEntry 1 }

cvAtmCallActiveVpi OBJECT-TYPE
        SYNTAX      INTEGER (0..4095)
        MAX-ACCESS  read-only
        STATUS      current
        DESCRIPTION
            "The VPI used for this ATM connection."
        ::= { cvAtmCallActiveEntry 2 }
 
cvAtmCallActiveVci OBJECT-TYPE
        SYNTAX      INTEGER (0..65535)
        MAX-ACCESS  read-only
        STATUS      current
        DESCRIPTION
            "The VCI used for this ATM connection."
        ::= { cvAtmCallActiveEntry 3 }

cvAtmCallActiveLowerIfName OBJECT-TYPE
        SYNTAX      DisplayString
        MAX-ACCESS  read-only 
        STATUS      current
        DESCRIPTION
            "The ifName of the ATM interface associated  with this
             call."
        ::= { cvAtmCallActiveEntry 4 }

cvAtmCallActiveSessionTarget OBJECT-TYPE
        SYNTAX      DisplayString 
        MAX-ACCESS  read-only
        STATUS      current
        DESCRIPTION
            "The object specifies the session target of the peer that
             is used for the voice over ATM call. A null string indicates 
             that the value is unavailable."
        ::= { cvAtmCallActiveEntry 5 }

cvAtmCallActiveSubchannelID OBJECT-TYPE
        SYNTAX      INTEGER (0..255)
        MAX-ACCESS  read-only
        STATUS      current
        DESCRIPTION
            "The subchannel used for this ATM connection."
        ::= { cvAtmCallActiveEntry 6 }

cvAtmCallActiveSessionProtocol OBJECT-TYPE
        SYNTAX      CvAtmSessionProtocol 
        MAX-ACCESS  read-only
        STATUS      current
        DESCRIPTION
            "Specifies the session protocol being used on this call."
        ::= { cvAtmCallActiveEntry 7 }

cvAtmCallActiveCalledNumber OBJECT-TYPE
        SYNTAX      DisplayString
        MAX-ACCESS  read-only
        STATUS      current
        DESCRIPTION
            "Specifes the number called for trunk connection calls. A
             null string indicates that this data is unavailable."
        ::= { cvAtmCallActiveEntry 8 }

cvAtmCallActiveDtmfRelay OBJECT-TYPE
        SYNTAX      TruthValue
        MAX-ACCESS  read-only
        STATUS      current
        DESCRIPTION
            "Specifies if Dtmf Relay is enabled for the call."
        ::= { cvAtmCallActiveEntry 9 }

cvAtmCallActiveUseSeqNumbers OBJECT-TYPE
        SYNTAX      TruthValue
        MAX-ACCESS  read-only
        STATUS      current
        DESCRIPTION
            "Specifies if Sequence Numbers are used on the voice data
             packets."
        ::= { cvAtmCallActiveEntry 10 }

--*********************************************************************
-- Voice over ATM specific Peer Configuration Table
--*********************************************************************

cvAtmPeerCfgTable OBJECT-TYPE
        SYNTAX      SEQUENCE OF CvATMPeerCfgEntry
        MAX-ACCESS  not-accessible
        STATUS      current
        DESCRIPTION
            "The table contains the Voice over ATM (ATM) peer specific
             information that is required to accept or place voice calls
             via the ATM backbone with the session protocol specified
             in cvAtmPeerCfgSessionProtocol."
       ::= { cvAtmDialPeer 1 }

cvAtmPeerCfgEntry OBJECT-TYPE
        SYNTAX      CvATMPeerCfgEntry
        MAX-ACCESS  not-accessible
        STATUS      current
        DESCRIPTION
            "A single ATM specific Peer. One entry per ATM encapsulation.
             The entry is created when its associated 'voiceOverATM(152)'
             encapsulation ifEntry is created.
             This entry is deleted when its associated ifEntry is deleted."
        INDEX       { ifIndex }
      ::= { cvAtmPeerCfgTable 1 }

CvATMPeerCfgEntry ::= SEQUENCE {
            cvAtmPeerCfgSessionProtocol            CvAtmSessionProtocol,
            cvAtmPeerCfgInterfaceName              DisplayString,
            cvAtmPeerCfgVpi                        INTEGER,
            cvAtmPeerCfgVci                        INTEGER,
            cvAtmPeerCfgVcName                     DisplayString,
            cvAtmPeerCfgCoderRate                  CvcSpeechCoderRate,
            cvAtmPeerCfgCodecBytes                 INTEGER,
            cvAtmPeerCfgFaxRate                    CvcFaxTransmitRate,
            cvAtmPeerCfgFaxBytes                   INTEGER,
            cvAtmPeerCfgInBandSignaling            CvcInBandSignaling,
            cvAtmPeerCfgVADEnable                  TruthValue,
            cvAtmPeerCfgUseSeqNumbers              TruthValue,
            cvAtmPeerCfgDtmfRelay                  TruthValue
        }

cvAtmPeerCfgSessionProtocol OBJECT-TYPE
        SYNTAX      CvAtmSessionProtocol
        MAX-ACCESS  read-write
        STATUS      current
        DESCRIPTION
            "The object specifies the session protocol to be used
             for Internet call between local and remote router via
             ATM backbone."
        DEFVAL      { ciscoSwitched }
        ::= { cvAtmPeerCfgEntry 1 }

cvAtmPeerCfgInterfaceName OBJECT-TYPE
        SYNTAX      DisplayString
        MAX-ACCESS  read-write 
        STATUS      current
        DESCRIPTION
            "The object specifies the ifName on which the call will go
             out.
             A zero length string indicates that no interface has been
             assigned."

        DEFVAL      { "" }
        ::= { cvAtmPeerCfgEntry 2 }

cvAtmPeerCfgVpi OBJECT-TYPE
        SYNTAX      INTEGER (0..4095)
        MAX-ACCESS  read-write
        STATUS      current
        DESCRIPTION
            "The VPI used for this ATM connection."
        DEFVAL      { 0 }
        ::= { cvAtmPeerCfgEntry 3 }
 
cvAtmPeerCfgVci OBJECT-TYPE
        SYNTAX      INTEGER (0..65535)
        MAX-ACCESS  read-write
        STATUS      current
        DESCRIPTION
            "The VCI used for this ATM connection."
        DEFVAL      { 0 }
        ::= { cvAtmPeerCfgEntry 4 }

cvAtmPeerCfgVcName OBJECT-TYPE
        SYNTAX      DisplayString
        MAX-ACCESS  read-write
        STATUS      current
        DESCRIPTION
            "The VC Name used for this ATM connection."
        DEFVAL      { "" }
        ::= { cvAtmPeerCfgEntry 5 }

cvAtmPeerCfgCoderRate OBJECT-TYPE
        SYNTAX      CvcSpeechCoderRate
        MAX-ACCESS  read-write
        STATUS      current
        DESCRIPTION
            "This object specifies the default voice coder rate of speech for
             the ATM peer."
        DEFVAL      { g729Ar8000 }
        ::= { cvAtmPeerCfgEntry 6 }

cvAtmPeerCfgCodecBytes OBJECT-TYPE
        SYNTAX      INTEGER (0..240)
        MAX-ACCESS  read-write
        STATUS      current
        DESCRIPTION
            "This object specifies the payload size for the voice packets
             to be transmitted during the call."
        DEFVAL       { 30 }
        ::= { cvAtmPeerCfgEntry 7 }

cvAtmPeerCfgFaxRate OBJECT-TYPE
        SYNTAX      CvcFaxTransmitRate
        MAX-ACCESS  read-write
        STATUS      current
        DESCRIPTION
            "This object specifies the default transmit rate of FAX for the
             ATM peer. If the value of this object is 'none', then
             the Fax relay feature is disabled; otherwise the Fax relay
             feature is enabled."
        DEFVAL      { voiceRate }
        ::= { cvAtmPeerCfgEntry 8 }

cvAtmPeerCfgFaxBytes OBJECT-TYPE
        SYNTAX      INTEGER (0..240)
        MAX-ACCESS  read-write
        STATUS      current
        DESCRIPTION
            "This object specifies the payload size for the fax packets
             to be transmitted during the call."
        DEFVAL       { 30 }
        ::= { cvAtmPeerCfgEntry 9 }

cvAtmPeerCfgInBandSignaling OBJECT-TYPE
        SYNTAX      CvcInBandSignaling
        MAX-ACCESS  read-write
        STATUS      current
        DESCRIPTION
            "This object specifies the type of in-band signaling used
             between the two end points of the call and is used by the
             router to determine how to interpret the ABCD signaling bits
             sent as part of the voice payload data."
        DEFVAL       { none }
        ::= { cvAtmPeerCfgEntry 10 }

cvAtmPeerCfgVADEnable OBJECT-TYPE
        SYNTAX      TruthValue 
        MAX-ACCESS  read-write
        STATUS      current
        DESCRIPTION
            "This object specifies whether or not VAD (Voice Activity
             Detection) is enabled. If the object value is 'false', then
             the voice data is continuously transmitted to ATM backbone."
        DEFVAL      { true }
        ::= { cvAtmPeerCfgEntry 11 }

cvAtmPeerCfgUseSeqNumbers OBJECT-TYPE
        SYNTAX      TruthValue 
        MAX-ACCESS  read-write
        STATUS      current
        DESCRIPTION
            "This object specifies whether or not Sequence Numbers are
             generated on voice packets."
        DEFVAL      { false }
        ::= { cvAtmPeerCfgEntry 12 }

cvAtmPeerCfgDtmfRelay OBJECT-TYPE
        SYNTAX      TruthValue 
        MAX-ACCESS  read-write
        STATUS      current
        DESCRIPTION
            "This object specifies whether or not Dtmf Relay is enabled.
             If it is then dtmf digits are transported as FRF11 Annex
             C packets, instead of being encoded as speech."
        DEFVAL      { false }
        ::= { cvAtmPeerCfgEntry 13 }

--
-- Notifications
--

ciscoVoiceAtmDialControlMIBNotificationPrefix OBJECT IDENTIFIER ::= 
        { ciscoVoiceAtmDialControlMIB 2 }
ciscoVoiceAtmDialControlMIBNotifications OBJECT IDENTIFIER ::= 
        { ciscoVoiceAtmDialControlMIBNotificationPrefix 0 }

--
-- Conformancy, Compliance and Group Objects
--

ciscoVoiceAtmDialControlMIBConformance OBJECT IDENTIFIER ::=
        { ciscoVoiceAtmDialControlMIB 3 }
ciscoVoiceAtmDialControlMIBCompliances OBJECT IDENTIFIER ::=
        { ciscoVoiceAtmDialControlMIBConformance 1 }
ciscoVoiceAtmDialControlMIBGroups      OBJECT IDENTIFIER ::=
        { ciscoVoiceAtmDialControlMIBConformance 2 }
 
-- compliance statements

ciscoVoiceAtmDialControlMIBCompliance MODULE-COMPLIANCE
        STATUS      current
        DESCRIPTION
            "The compliance statement for entities which
             implement the CISCO VOICE ATM DIAL CONTROL MIB"
        MODULE      -- this module
        MANDATORY-GROUPS
            { cvAtmCallHistoryGroup,
              cvAtmCallActiveGroup,
              cvAtmPeerCfgGroup }
        OBJECT cvAtmPeerCfgSessionProtocol
        MIN-ACCESS read-only
        DESCRIPTION
            "Agent implements read-only access at present time"
        OBJECT cvAtmPeerCfgInterfaceName
        MIN-ACCESS read-only
        DESCRIPTION
            "Agent implements read-only access at present time"
        OBJECT cvAtmPeerCfgVpi
        MIN-ACCESS read-only
        DESCRIPTION
            "Agent implements read-only access at present time"
        OBJECT cvAtmPeerCfgVci
        MIN-ACCESS read-only
        DESCRIPTION
            "Agent implements read-only access at present time"
        OBJECT cvAtmPeerCfgVcName
        MIN-ACCESS read-only
        DESCRIPTION
            "Agent implements read-only access at present time"
        OBJECT cvAtmPeerCfgCoderRate
        MIN-ACCESS read-only
        DESCRIPTION
            "Agent implements read-only access at present time"
        OBJECT cvAtmPeerCfgCodecBytes
        MIN-ACCESS read-only
        DESCRIPTION
            "Agent implements read-only access at present time"
        OBJECT cvAtmPeerCfgFaxRate
        MIN-ACCESS read-only
        DESCRIPTION
            "Agent implements read-only access at present time"
        OBJECT cvAtmPeerCfgFaxBytes
        MIN-ACCESS read-only
        DESCRIPTION
            "Agent implements read-only access at present time"
        OBJECT cvAtmPeerCfgInBandSignaling
        MIN-ACCESS read-only
        DESCRIPTION
            "Agent implements read-only access at present time"
        OBJECT cvAtmPeerCfgVADEnable
        MIN-ACCESS read-only
        DESCRIPTION
            "Agent implements read-only access at present time"
        OBJECT cvAtmPeerCfgUseSeqNumbers
        MIN-ACCESS read-only
        DESCRIPTION
            "Agent implements read-only access at present time"
        OBJECT cvAtmPeerCfgDtmfRelay
        MIN-ACCESS read-only
        DESCRIPTION
            "Agent implements read-only access at present time"
        ::= { ciscoVoiceAtmDialControlMIBCompliances 1 }

-- units of conformance

cvAtmCallHistoryGroup OBJECT-GROUP
        OBJECTS {
            cvAtmCallHistoryConnectionId,
            cvAtmCallHistoryVpi,                      
            cvAtmCallHistoryVci,                      
            cvAtmCallHistoryLowerIfName,
            cvAtmCallHistorySessionTarget,            
            cvAtmCallHistorySubchannelID,
            cvAtmCallHistorySessionProtocol,
            cvAtmCallHistoryCalledNumber,
            cvAtmCallHistoryDtmfRelay,
            cvAtmCallHistoryUseSeqNumbers
        }
        STATUS      current
        DESCRIPTION
            "A collection of objects providing the ATM Call History
             entry capability."
        ::= { ciscoVoiceAtmDialControlMIBGroups 1 }

cvAtmCallActiveGroup OBJECT-GROUP
        OBJECTS {
            cvAtmCallActiveConnectionId,
            cvAtmCallActiveVpi,                      
            cvAtmCallActiveVci,                      
            cvAtmCallActiveLowerIfName,
            cvAtmCallActiveSessionTarget,            
            cvAtmCallActiveSubchannelID,
            cvAtmCallActiveSessionProtocol,
            cvAtmCallActiveCalledNumber,
            cvAtmCallActiveDtmfRelay,
            cvAtmCallActiveUseSeqNumbers
        }
        STATUS      current
        DESCRIPTION
            "A collection of objects providing the ATM Call Active
             entry capability."
        ::= { ciscoVoiceAtmDialControlMIBGroups 2 }

cvAtmPeerCfgGroup OBJECT-GROUP
        OBJECTS {
            cvAtmPeerCfgSessionProtocol,
            cvAtmPeerCfgInterfaceName,
            cvAtmPeerCfgVpi,
            cvAtmPeerCfgVci,
            cvAtmPeerCfgVcName,
            cvAtmPeerCfgCoderRate,
            cvAtmPeerCfgCodecBytes,
            cvAtmPeerCfgFaxRate,
            cvAtmPeerCfgFaxBytes,
            cvAtmPeerCfgInBandSignaling,
            cvAtmPeerCfgVADEnable,
            cvAtmPeerCfgUseSeqNumbers,
            cvAtmPeerCfgDtmfRelay
        }
        STATUS      current
        DESCRIPTION
            "A collection of objects providing the ATM Dialpeer
             capability. These objects have been implemented as
             read-only."
        ::= { ciscoVoiceAtmDialControlMIBGroups 3 }
END
