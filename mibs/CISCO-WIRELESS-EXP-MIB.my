-- *****************************************************************
-- CISCO-WIRELESS-EXP-MIB.my:  Cisco Wireless Radio Point to Point
--			       Experimental MIB.
--
-- May 1999, Joseph L Raja
--
-- Copyright (c) 1998-1999 by Cisco Systems, Inc.
-- All rights reserved.
-- 
-- *****************************************************************
--
--
-- 1.0 Glossary
-- 
-- The following terms are used in the MIB definitions below. 
--
-- Radio Card: The line card that provides the wireless communication features.
-- Radio Link: The bi-directional wireless link that exists between two
--	       communicating radio cards.
-- Radio PHY: Represents the transmission characteristics of the Radio Link. 
-- RF Unit: The Radio Frequency components and the associated antennas.
-- Radio System: Radio card and RF unit(s).
--
-- 
-- 2.0 Cisco Wireless Radio Experimental MIB Organization
-- 
-- The Cisco Wireless Radio Experimental MIB provides the following
-- management groups :
--
-- When the draft-ietf-entmib-v2-03.txt gets finalized the Radio Frequency
-- Group will be moved into that MIB.
--
-- When the CISCO-IMAGE-MIB.my gets updated to include the image capabilities
-- we need the Image Group will be migrated into that MIB.
--
-- When the CISCO-LED-MIB.my becomes available and supports the functionality
-- the LED group needs, the LED group will be migrated into that.
-- 
-- o.  Radio Frequency Resource Group
-- 			This contains information about the Radio frequency
-- 			transmission and reception resources available on the
-- 			system. This group determines the portions of the
-- 			radio spectrum at which the radio subsystem can
-- 			operate.
-- 			This group in conjunction with the radio PHY group
-- 			determine the acutal spectrum that gets used for
-- 			communications.
--
-- o.  Image Group      This provides facilities to manage radio line card's 
--                      firmware image file URL's in router's image repository.
--                      It also provides access to the image details.
--
-- o.  LED Group        This group provides information about LEDs available
--                      on the line card.
--
-- o.  Duplexor Group   This group provides information about the Duplexors
--			installed in the RF resources.

--  
-- 3.0   MIB Definitions
-- 
-- 

CISCO-WIRELESS-EXP-MIB DEFINITIONS ::= BEGIN

	IMPORTS
	MODULE-IDENTITY, OBJECT-TYPE, Integer32
		FROM SNMPv2-SMI
	DateAndTime, DisplayString
		FROM SNMPv2-TC
	MODULE-COMPLIANCE, OBJECT-GROUP
		FROM SNMPv2-CONF
        ifIndex
		FROM IF-MIB
	entPhysicalIndex
		FROM ENTITY-MIB
	ciscoExperiment
		FROM CISCO-SMI
	Unsigned32
		FROM CISCO-TC;

	ciscoWirelessExpMIB MODULE-IDENTITY
           LAST-UPDATED "9905132010Z"
           ORGANIZATION "Cisco Systems Inc."
           CONTACT-INFO
	   "	Cisco Systems
		Customer Service

	   Postal: 170 W Tasman Drive
		   San Jose, CA  95134
		   USA

		   Tel: +1 800 553-NETS
	           E-mail: firestar-sw@cisco.com"
            DESCRIPTION
	        "This is the MIB Module for the Cisco Wireless Radio 
                 Point to Point experimental components."
       ::= { ciscoExperiment 52}

--
-- The Cisco Wireless Radio MIB Tree
-- 

cwrRadioExpMibObjects	OBJECT IDENTIFIER ::= { ciscoWirelessExpMIB 1 }
cwrRadioFreqEntityGroup	OBJECT IDENTIFIER ::= { cwrRadioExpMibObjects 1 }
cwrRadioImageGroup     	OBJECT IDENTIFIER ::= { cwrRadioExpMibObjects 2 }
cwrRadioLedGroup     	OBJECT IDENTIFIER ::= { cwrRadioExpMibObjects 3 }
cwrRadioDuplexorGroup 	OBJECT IDENTIFIER ::= { cwrRadioExpMibObjects 4 }

--
--	The Radio Frequency Entity Group.
--
--      The RF Table. This table contains information about the Radio frequency
--	Entities available for use on the system.
--

cwrRfEntityTable OBJECT-TYPE
        SYNTAX SEQUENCE OF CwrRfEntityEntry
        MAX-ACCESS not-accessible
        STATUS current
        DESCRIPTION
        "This table contains information about the radio frequency resources
	available for use on the system."
        ::= { cwrRadioFreqEntityGroup 1 }

cwrRfEntityEntry OBJECT-TYPE
        SYNTAX CwrRfEntityEntry
        MAX-ACCESS not-accessible
        STATUS current
        DESCRIPTION
        "This represents one entry in the cwrRfEntityTable. This table is
	largely	a read only table which provides details on the radio frequency
        resources available on the system. Physically each RF resource may be
        realized by one antenna and its associated control hardware.
        But a single antenna and its associated hardware may act as more than
        1 RF resource.

        A Duplexor is a mechanical device, that acts as a band pass filter
	when installed in an RF resource. 

	Normally a RF resource is capable of operating over a wide frequency
	range. To operate at restricted frequencies, the user has to own that 
	part of the frequency spectrum.  Since the user may not own parts of
	the frequency spectrum over which the RF resource may operate, a
	Duplexor is installed in the RF resource.  This restricts the
	RF resource to operate in the passband defined by the Duplexor.
	In this table the Duplexor's are identified by an index into the
	cwrDuplexorTable. 

	It is indexed by the ifIndex and cwrRfEntityIndex."
        INDEX { ifIndex, cwrRfEntityIndex }
        ::= { cwrRfEntityTable 1 }

CwrRfEntityEntry ::= SEQUENCE {
	cwrRfEntityIndex	        Integer32,
        cwrRfSwRevision                 Unsigned32,
        cwrRfAssemblyPartNumberClass    Unsigned32,
        cwrRfAssemblyPartNumberBase     Unsigned32,
        cwrRfAssemblyPartNumberVersion  Unsigned32,
        cwrRfBoardPartNumberClass       Unsigned32,
        cwrRfBoardPartNumberBase        Unsigned32,
        cwrRfBoardPartNumberVersion     Unsigned32,
        cwrRfBoardRevision              DisplayString,
	cwrRfSerialNumber               DisplayString,
	cwrRfManfDate		        DateAndTime,
        cwrRfVendorId                   Integer32,
	cwrRfDuplexorIndex	        Integer32
        }

cwrRfEntityIndex OBJECT-TYPE
        SYNTAX Integer32 (1..2147483647)
        MAX-ACCESS not-accessible
        STATUS current
        DESCRIPTION
	"This object represents the index of this entry in the
	cwrRfEntityTable."
        ::= { cwrRfEntityEntry 1 }

cwrRfSwRevision OBJECT-TYPE
        SYNTAX Unsigned32
        MAX-ACCESS read-only
        STATUS current
        DESCRIPTION
        "This object represents the software revision number of controlling the
	RF subsystem."
        ::= { cwrRfEntityEntry 2 }

cwrRfAssemblyPartNumberClass OBJECT-TYPE
        SYNTAX Unsigned32
        MAX-ACCESS read-only
        STATUS current
        DESCRIPTION
        "This object represents the assembly part number class of the RF
	subsystem."
        ::= { cwrRfEntityEntry 3 }

cwrRfAssemblyPartNumberBase OBJECT-TYPE
        SYNTAX Unsigned32
        MAX-ACCESS read-only
        STATUS current
        DESCRIPTION
        "This object represents the assembly part number base of the RF
	subsystem."
        ::= { cwrRfEntityEntry 4 }

cwrRfAssemblyPartNumberVersion OBJECT-TYPE
        SYNTAX Unsigned32
        MAX-ACCESS read-only
        STATUS current
        DESCRIPTION
        "This object represents the assembly part number version of the RF
	subsystem."
        ::= { cwrRfEntityEntry 5 }

cwrRfBoardPartNumberClass OBJECT-TYPE
        SYNTAX Unsigned32
        MAX-ACCESS read-only
        STATUS current
        DESCRIPTION
        "This object represents the board part number class of the RF
	subsystem."
        ::= { cwrRfEntityEntry 6 }

cwrRfBoardPartNumberBase OBJECT-TYPE
        SYNTAX Unsigned32
        MAX-ACCESS read-only
        STATUS current
        DESCRIPTION
        "This object represents the board part number base of the RF
	subsystem."
        ::= { cwrRfEntityEntry 7 }

cwrRfBoardPartNumberVersion OBJECT-TYPE
        SYNTAX Unsigned32
        MAX-ACCESS read-only
        STATUS current
        DESCRIPTION
        "This object represents the board part number version of the RF
	subsystem."
        ::= { cwrRfEntityEntry 8 }

cwrRfBoardRevision OBJECT-TYPE
        SYNTAX DisplayString
        MAX-ACCESS read-only
        STATUS current
        DESCRIPTION
        "This object represents the board revision of the RF subsystem."
        ::= { cwrRfEntityEntry 9 }

cwrRfSerialNumber OBJECT-TYPE
        SYNTAX DisplayString
        MAX-ACCESS read-only
        STATUS current
        DESCRIPTION
        "This object represents the serial number of the RF subsystem."
        ::= { cwrRfEntityEntry 10 }

cwrRfManfDate OBJECT-TYPE
        SYNTAX DateAndTime
        MAX-ACCESS read-only
        STATUS current
        DESCRIPTION
        "This object represents the manufacturing date of the RF subsystem."
        ::= { cwrRfEntityEntry 11 }

cwrRfVendorId OBJECT-TYPE
        SYNTAX Integer32 (1..256)
        MAX-ACCESS read-only
        STATUS current
        DESCRIPTION
        "This object represents the Radio frequency device vendor ID."
        ::= { cwrRfEntityEntry 12 }

cwrRfDuplexorIndex OBJECT-TYPE
        SYNTAX Integer32 (1..2147483647)
        MAX-ACCESS read-only
        STATUS current
        DESCRIPTION
	"This object represents the index into cwrDuplexorTable.
	This index identifies the Duplexor associated with this 
	RF resource."
        ::= { cwrRfEntityEntry 13 }


--
--      The Intermediate Frequency Entity table. This table contains
--      information about the Intermediate Frequency subsystem on the radio
--      card.
-- 

cwrIntFreqEntityTable OBJECT-TYPE
        SYNTAX SEQUENCE OF CwrIntFreqEntityEntry
        MAX-ACCESS not-accessible
        STATUS current
        DESCRIPTION
        "This table contains information about the intermediate frequency
        subsystem on the radio card."
        ::= { cwrRadioFreqEntityGroup 2 }

cwrIntFreqEntityEntry OBJECT-TYPE
        SYNTAX CwrIntFreqEntityEntry
        MAX-ACCESS not-accessible
        STATUS current
        DESCRIPTION
        "This represents one entry in the cwrIntFreqEntityTable. This table
	is largely a read only table which provides details on the intermediate
	frequency subsystem available on the radio card. 
	It is indexed by the ifIndex."
        INDEX { ifIndex }
        ::= { cwrIntFreqEntityTable 1 }

CwrIntFreqEntityEntry ::= SEQUENCE {
        cwrIfAssemblyPartNumberClass    Unsigned32,
        cwrIfAssemblyPartNumberBase     Unsigned32,
        cwrIfAssemblyPartNumberVersion  Unsigned32,
        cwrIfBoardPartNumberClass       Unsigned32,
        cwrIfBoardPartNumberBase        Unsigned32,
        cwrIfBoardPartNumberVersion     Unsigned32,
        cwrIfBoardRevision              DisplayString,
	cwrIfSerialNumber               DisplayString,
	cwrIfManfDate		        DateAndTime,
        cwrIfVendorId                   Integer32,
        cwrIfSwRevision                 Unsigned32 
        }

cwrIfAssemblyPartNumberClass OBJECT-TYPE
        SYNTAX Unsigned32
        MAX-ACCESS read-only
        STATUS current
        DESCRIPTION
        "This object represents the assembly part number class of the IF
	subsystem."
        ::= { cwrIntFreqEntityEntry 1 }

cwrIfAssemblyPartNumberBase OBJECT-TYPE
        SYNTAX Unsigned32
        MAX-ACCESS read-only
        STATUS current
        DESCRIPTION
        "This object represents the assembly part number base of the IF
	subsystem."
        ::= { cwrIntFreqEntityEntry 2 }

cwrIfAssemblyPartNumberVersion OBJECT-TYPE
        SYNTAX Unsigned32
        MAX-ACCESS read-only
        STATUS current
        DESCRIPTION
        "This object represents the assembly part number version of the IF
	subsystem."
        ::= { cwrIntFreqEntityEntry 3 }

cwrIfBoardPartNumberClass OBJECT-TYPE
        SYNTAX Unsigned32
        MAX-ACCESS read-only
        STATUS current
        DESCRIPTION
        "This object represents the board part number class of the IF
	subsystem."
        ::= { cwrIntFreqEntityEntry 4 }

cwrIfBoardPartNumberBase OBJECT-TYPE
        SYNTAX Unsigned32
        MAX-ACCESS read-only
        STATUS current
        DESCRIPTION
        "This object represents the board part number base of the IF
	subsystem."
        ::= { cwrIntFreqEntityEntry 5 }

cwrIfBoardPartNumberVersion OBJECT-TYPE
        SYNTAX Unsigned32
        MAX-ACCESS read-only
        STATUS current
        DESCRIPTION
        "This object represents the board part number version of the IF
	subsystem."
        ::= { cwrIntFreqEntityEntry 6 }

cwrIfBoardRevision OBJECT-TYPE
        SYNTAX DisplayString 
        MAX-ACCESS read-only
        STATUS current
        DESCRIPTION
        "This object represents the board revision of the IF subsystem."
        ::= { cwrIntFreqEntityEntry 7 }

cwrIfSerialNumber OBJECT-TYPE
        SYNTAX DisplayString 
        MAX-ACCESS read-only
        STATUS current
        DESCRIPTION
        "This object represents the serial number of the IF subsystem."
        ::= { cwrIntFreqEntityEntry 8 }

cwrIfManfDate OBJECT-TYPE
        SYNTAX DateAndTime
        MAX-ACCESS read-only
        STATUS current
        DESCRIPTION
        "This object represents the manufacturing date of the IF subsystem."
        ::= { cwrIntFreqEntityEntry 9 }

cwrIfVendorId OBJECT-TYPE
        SYNTAX Integer32 (1..256)
        MAX-ACCESS read-only
        STATUS current
        DESCRIPTION
        "This object represents the IF vendor ID."
        ::= { cwrIntFreqEntityEntry 10 }

cwrIfSwRevision OBJECT-TYPE
        SYNTAX Unsigned32
        MAX-ACCESS read-only
        STATUS current
        DESCRIPTION
        "This object represents the IF software revision."
        ::= { cwrIntFreqEntityEntry 11 }

--
--	The Image Group. 
--

--
--      The Firmware Image Table. This table provides facilities to manage
--      the firmware images that the router will use for configuring the 
--      radio line cards.
-- 

cwrImageTable OBJECT-TYPE
        SYNTAX SEQUENCE OF CwrImageEntry
        MAX-ACCESS not-accessible
        STATUS current
        DESCRIPTION
        "This table provides facilities to manage the firmware images that the
        router will use to configure the radio line cards.

	When images need to be downloaded, the software will
	search this list starting from the first, for an image whose
	capabilities match the configuration specified in the
	cwrRadioBaseTable and the cwrRadioPhyTable and download that image
	to the appropriate hardware component. 

	Insertion into the table at arbitrary points is not supported.
	Any new image URL added to this table will be inserted at index
	1 only. 

	Also note that an image gets downloaded to the hardware only when
	when a radio link is administratively enabled."
        ::= { cwrRadioImageGroup 1 }

cwrImageEntry OBJECT-TYPE
        SYNTAX CwrImageEntry
        MAX-ACCESS not-accessible
        STATUS current
        DESCRIPTION
        "This represents one entry in the cwrImageTable."
        INDEX { cwrImageIndex }
        ::= { cwrImageTable 1 }

CwrImageEntry ::= SEQUENCE {
	cwrImageIndex		Integer32,
	cwrImageNameUrl	        DisplayString,
	cwrImageState           INTEGER,
	cwrImageSize		Unsigned32,
	cwrImageChipType        Unsigned32,
	cwrImageChipClass       Unsigned32,
	cwrImageCapability1     Unsigned32,
	cwrImageCapability2     Unsigned32,
	cwrImageVersion		Unsigned32,
	cwrImageTag	        DisplayString,
	cwrImageOp		INTEGER
        }

cwrImageIndex OBJECT-TYPE
        SYNTAX  Integer32(1..2147483647)
        MAX-ACCESS not-accessible
        STATUS current
        DESCRIPTION
        "This represents the one entry in this table. It also represents
	the search order. When images need to be downloaded to the 
	hardware, the images are searched in the order of this index
	for an image that matches the hardware capabilities and uses it."
        ::= { cwrImageEntry 1 }

cwrImageNameUrl OBJECT-TYPE
        SYNTAX  DisplayString (SIZE(1..255))
        MAX-ACCESS read-write
        STATUS current
        DESCRIPTION
        "This object is the name of the image in the Universal Resource Locator
	(URL) format. This URL will be used to access the image when needed."
        ::= { cwrImageEntry 2 }

cwrImageState OBJECT-TYPE
        SYNTAX  INTEGER {
		imageInvalid(1),
		imageValid(2)
		}
        MAX-ACCESS read-only
        STATUS current
        DESCRIPTION
        "This represents the state of the image.
	image_invalid(1): If the image could not be accessed for any reason.
	image_valid(2)  : Image accessible and available for use."
        ::= { cwrImageEntry 3 }

cwrImageSize OBJECT-TYPE
        SYNTAX Unsigned32 
        MAX-ACCESS read-only
        STATUS current
        DESCRIPTION
        "This represents the size of the image in bytes."
        ::= { cwrImageEntry 4 }

cwrImageChipClass OBJECT-TYPE
        SYNTAX Unsigned32 
        MAX-ACCESS read-only
        STATUS current
        DESCRIPTION
        "This represents the class of chips onto which this image may be
	loaded."
        ::= { cwrImageEntry 5 }

cwrImageChipType OBJECT-TYPE
        SYNTAX Unsigned32 
        MAX-ACCESS read-only
        STATUS current
        DESCRIPTION
        "This represents the download method to use."
        ::= { cwrImageEntry 6 }

cwrImageCapability1 OBJECT-TYPE
        SYNTAX Unsigned32 
        MAX-ACCESS read-only
        STATUS current
        DESCRIPTION
        "This represents a bitmask. The bit mask identifies the capabilities of
	this image. See also cwrImageCapability2."
        ::= { cwrImageEntry 7 }

cwrImageCapability2 OBJECT-TYPE
        SYNTAX Unsigned32 
        MAX-ACCESS read-only
        STATUS current
        DESCRIPTION
        "This represents a bitmask. The bit mask identifies the capabilities of
	this image in addition to cwrImageCapability1."
        ::= { cwrImageEntry 8 }

cwrImageVersion OBJECT-TYPE
        SYNTAX Unsigned32 
        MAX-ACCESS read-only
        STATUS current
        DESCRIPTION
        "This represents the version number of this image."
        ::= { cwrImageEntry 9 }

cwrImageTag OBJECT-TYPE
        SYNTAX  DisplayString (SIZE(1..255))
        MAX-ACCESS read-only
        STATUS current
        DESCRIPTION
        "This object is the tag string associated with the image. Normally used
	to trace the source code used to generate this image."
        ::= { cwrImageEntry 10 }

cwrImageOp OBJECT-TYPE
        SYNTAX INTEGER {
		nop(0),
		add(1),
		delete(2),
		move(3)
	}
        MAX-ACCESS read-write
        STATUS current
        DESCRIPTION
	"This object represents the operation to be performed on the
	identified image. 
	nop(0)    - This value will be returned when this object is
		    read.
	add(1)    - Will add the image URL, as the first entry in the image
		    table.
	delete(2) - Will delete the specified ULR from the image table.
	move(3)   - Will make the image specified by the URL the first entry
		    in the imageTable."
        ::= { cwrImageEntry 11 }

--
--  The LED Group.
--

cwrLedTable OBJECT-TYPE
       	SYNTAX     SEQUENCE OF CwrLedEntry
	MAX-ACCESS not-accessible
	STATUS     current
	DESCRIPTION
        "Entity (Light emitting diode) LED information.  For each LED on the
	entity, an entry will exist in this table, describing the location
        and current status of that LED."
        ::= { cwrRadioLedGroup 1 }

cwrLedEntry OBJECT-TYPE
        SYNTAX     CwrLedEntry
        MAX-ACCESS not-accessible
        STATUS     current
        DESCRIPTION
        "An entry in the table, containing the LED information
        about the entity. The entPhysicalIndex identifies
        the entity on which the Led's are present."
        INDEX { entPhysicalIndex, cwrLedIndex }
        ::= { cwrLedTable 1 }

CwrLedEntry ::=
        SEQUENCE {
           cwrLedIndex                  INTEGER,
           cwrLedName                   DisplayString,
           cwrLedVerticalPosition       Integer32,
           cwrLedHorizontalPosition     Integer32,
	   cwrLedMode                   INTEGER,
           cwrLedCurrentColor           INTEGER
        }

cwrLedIndex OBJECT-TYPE
         SYNTAX      INTEGER (1..16)
         MAX-ACCESS  not-accessible
         STATUS      current
         DESCRIPTION
         "For a given entPhysicalIndex, this index value uniquely identifies
         an entry in the cwrLedTable."
         ::= { cwrLedEntry 1 }

cwrLedName OBJECT-TYPE
        SYNTAX     DisplayString 
        MAX-ACCESS read-only
        STATUS     current
        DESCRIPTION
        "The label of the LED on the physical entity or a textual 
        description to identify the usage of the LED."
        ::= { cwrLedEntry 2 }
 
cwrLedVerticalPosition OBJECT-TYPE
        SYNTAX      Integer32 (1..16)
        MAX-ACCESS  read-only
        STATUS      current
        DESCRIPTION
        "The position of the LED in the entity.  It is counted from 
        top to bottom." 
        ::= { cwrLedEntry 3 }

cwrLedHorizontalPosition OBJECT-TYPE
        SYNTAX      Integer32 (1..16)
        MAX-ACCESS  read-only
        STATUS      current
        DESCRIPTION
        "The position of the LED in the entity.  It is counted from 
        from left to right." 
        ::= { cwrLedEntry 4 }

cwrLedMode OBJECT-TYPE
        SYNTAX INTEGER {
		automatic(1),
		latched(2),
		forceOff(3),
		forceSolidGreen(4),
		forceSolidYellow(5),
		forceBlinkGreen(6),
		forceBlinkYellow(7),
		forceBlinkBoth(8)
        }
        MAX-ACCESS read-write
        STATUS     current
        DESCRIPTION
        "This objects specifies the desired mode of LED updates.
       
        automatic(1) and latched(2) are settings used by the software
        to determine how the LED should be updated.
       
        The others are for diagnostic purposes. The LED will be turned on 
        or off as specified by the other (3-8) settings.

        The modes mean the following:
        automatic(1):	The system updates the LED according to the
			default settings for that entity.
        latched(2):	Once the LED is turned on, user has to turn it off.
			This applies only to alarm LEDs.
        forceOff(3):	Force the LED off.
        forceSolidGreen(4): Force the LED to be solid green in on state.
        forceSolidYellow(5):Force the LED to be solid Yellow in on state
        forceBlinkGreen(6): Force the LED to blink in Green.
        forceBlinkYellow(7):Force the LED to blink in Yellow.
        forceBlinkBoth(8):  Force the LED to blink Yellow and
			   Green alternatively."
        ::= { cwrLedEntry 5 }

cwrLedCurrentColor OBJECT-TYPE
        SYNTAX INTEGER {
		green(1),
		yellow(2),
		blinkGreen(3),
		blinkYellow(4),
		blinkGreenYellow(5),
		off(6)
        }
        MAX-ACCESS read-only
        STATUS     current
        DESCRIPTION
        "Indicates the current color of the LED."
        ::= { cwrLedEntry 6 }


--
--	The Duplexor Group.
--
--      The Duplexor Table. This table contains information about the
--      Duplexor Entities available for use on the system.
--      A Duplexor is a mechanical device, that acts as a bandpass filter
--	when installed in an RF resource.
--

cwrDuplexorTable OBJECT-TYPE
        SYNTAX SEQUENCE OF CwrDuplexorEntry
        MAX-ACCESS not-accessible
        STATUS current
        DESCRIPTION
        "This table contains information about the Duplexors
	available for use on the system."
        ::= { cwrRadioDuplexorGroup 1 }

cwrDuplexorEntry OBJECT-TYPE
        SYNTAX CwrDuplexorEntry
        MAX-ACCESS not-accessible
        STATUS current
        DESCRIPTION
        "This represents one entry in the cwrDuplexorTable. This table
	provides details on the Duplexors available on the system. 

	It is indexed by the ifIndex and cwrDuplexorIndex."
        INDEX { ifIndex, cwrDuplexorIndex }
        ::= { cwrDuplexorTable 1 }

CwrDuplexorEntry ::= SEQUENCE {
	cwrDuplexorIndex	        Integer32,
	cwrDuplexorCiscoPartNumber	DisplayString,
	cwrDuplexorLoPassbandRange      DisplayString,
	cwrDuplexorHiPassbandRange      DisplayString,
	cwrDuplexorReceivePassband      INTEGER,
	cwrDuplexorCLEICode		DisplayString,
	cwrDuplexorVendorName		DisplayString,
	cwrDuplexorSerialNumber		DisplayString
        }

cwrDuplexorIndex OBJECT-TYPE
        SYNTAX Integer32 (1..2147483647)
        MAX-ACCESS not-accessible
        STATUS current
        DESCRIPTION
	"This object represents the index of this entry in the
	cwrDuplexorTable."
        ::= { cwrDuplexorEntry 1 }

cwrDuplexorCiscoPartNumber OBJECT-TYPE
        SYNTAX DisplayString
        MAX-ACCESS read-write
        STATUS current
        DESCRIPTION
        "This object represents the Cisco part number for this Duplexor."
        ::= { cwrDuplexorEntry 2 }

cwrDuplexorLoPassbandRange OBJECT-TYPE
        SYNTAX DisplayString
        MAX-ACCESS read-write
        STATUS current
        DESCRIPTION
        "This object represents the low frequency range that this Duplexor will
	pass through without any attenuation. All low frequencies outside this
	range will be attenuated to a level such that an RF resource that
	uses this Duplexor will be unable to transmit or receive those
	frequencies."
        ::= { cwrDuplexorEntry 3 }

cwrDuplexorHiPassbandRange OBJECT-TYPE
        SYNTAX DisplayString
        MAX-ACCESS read-write
        STATUS current
        DESCRIPTION
        "This object represents the high frequency range that this Duplexor will
	pass through without any attenuation. All high frequencies outside this
	range will be attenuated to a level such that an RF resource that
	uses this Duplexor will be unable to transmit or receive those
	frequencies."
        ::= { cwrDuplexorEntry 4 }

cwrDuplexorReceivePassband OBJECT-TYPE
        SYNTAX INTEGER {
                   loPassband(1),
                   hiPassband(2)
                   }
        MAX-ACCESS read-write
        STATUS current
        DESCRIPTION
        "This object indicates which of the two passbands are being used
         to receive transmissions.  The RF Resource can receive on either of 
         the duplexor passbands.
         loPassband(1) - The RF Resource is receiving on a frequency within
                         the range identified by cwrDuplexorLoPassbandRange.
         hiPassband(2) - The RF Resource is receiving on a frequency within
                         the range identified by cwrDuplexorHiPassbandRange."
        ::= { cwrDuplexorEntry 5 }

cwrDuplexorCLEICode OBJECT-TYPE
        SYNTAX DisplayString
        MAX-ACCESS read-write
        STATUS current
        DESCRIPTION
        "The CLEI code for this Duplexor."
        ::= { cwrDuplexorEntry 6 }

cwrDuplexorVendorName OBJECT-TYPE
        SYNTAX DisplayString
        MAX-ACCESS read-write
        STATUS current
        DESCRIPTION
        "The Vendor Name for this Duplexor."
        ::= { cwrDuplexorEntry 7 }

cwrDuplexorSerialNumber OBJECT-TYPE
        SYNTAX DisplayString
        MAX-ACCESS read-write
        STATUS current
        DESCRIPTION
        "The Serial number of this Duplexor."
        ::= { cwrDuplexorEntry 8 }

-- ============================================================================
--
-- Compliance Statements
--

cwrRadioExpConformance  OBJECT IDENTIFIER ::= { ciscoWirelessExpMIB 2 }
cwrRadioExpCompliances  OBJECT IDENTIFIER ::= { cwrRadioExpConformance 1 }
cwrRadioExpGroups       OBJECT IDENTIFIER ::= { cwrRadioExpConformance 2 }

cwrRadioExpCompliance MODULE-COMPLIANCE
        STATUS      current
        DESCRIPTION
            "The compliance statement for Point to Point wireless interface
	     devices compliant to Cisco Systems Inc. specification."

MODULE  -- ciscoWirelesExpMib

-- unconditionally mandatory groups
MANDATORY-GROUPS {
	cwrComplianceRadioRFGroup,
	cwrComplianceRadioImageGroup,
	cwrComplianceRadioLEDGroup,
	cwrComplianceRadioDuplexorGroup
        }
        ::= { cwrRadioExpCompliances 1 }

--
-- Required Radio frequency resource Group.
--
cwrComplianceRadioRFGroup OBJECT-GROUP
        OBJECTS {
	        cwrRfSwRevision,
                cwrRfAssemblyPartNumberClass,
                cwrRfAssemblyPartNumberBase,
                cwrRfAssemblyPartNumberVersion,
                cwrRfBoardPartNumberClass,
                cwrRfBoardPartNumberBase,
                cwrRfBoardPartNumberVersion,
                cwrRfBoardRevision,
	        cwrRfSerialNumber,
		cwrRfManfDate,
	        cwrRfVendorId,
		cwrRfDuplexorIndex,
                cwrIfAssemblyPartNumberClass,
                cwrIfAssemblyPartNumberBase,
                cwrIfAssemblyPartNumberVersion,
                cwrIfBoardPartNumberClass,
                cwrIfBoardPartNumberBase,
                cwrIfBoardPartNumberVersion,
                cwrIfBoardRevision,
	        cwrIfSerialNumber,
	        cwrIfManfDate,
                cwrIfVendorId,
                cwrIfSwRevision
	        }
	STATUS      current
	DESCRIPTION
	"Group of objects implemented in the point to point wireless
	 system for managing the Radio Frequency resources on the link."
	::= { cwrRadioExpGroups 1 }

--
-- Required Image Group.
--
cwrComplianceRadioImageGroup OBJECT-GROUP
        OBJECTS {
		cwrImageNameUrl,
		cwrImageState,
		cwrImageSize,
		cwrImageChipType,
		cwrImageChipClass,
		cwrImageCapability1,
		cwrImageCapability2,
		cwrImageVersion,
		cwrImageTag,
		cwrImageOp
        }
	STATUS      current
	DESCRIPTION
	"Group of objects implemented in the point to point wireless
	system for managing images related to the point-to-point wireless
	firmware."
	::= { cwrRadioExpGroups 2 }

--
--  Required LED group.
--
cwrComplianceRadioLEDGroup OBJECT-GROUP
        OBJECTS {
		cwrLedName,
		cwrLedVerticalPosition,
		cwrLedHorizontalPosition,
		cwrLedMode,
		cwrLedCurrentColor
	        }
	STATUS      current
	DESCRIPTION
	"Group of objects implemented in the point to point wireless
	card to provide information about the LEDs on the card."
	::= { cwrRadioExpGroups 3 }

--
--  Required Duplexor group.
--
cwrComplianceRadioDuplexorGroup OBJECT-GROUP
        OBJECTS {
		cwrDuplexorCiscoPartNumber,
		cwrDuplexorLoPassbandRange,
		cwrDuplexorHiPassbandRange,
		cwrDuplexorReceivePassband,
		cwrDuplexorCLEICode,
		cwrDuplexorVendorName,
		cwrDuplexorSerialNumber
	        }
	STATUS      current
	DESCRIPTION
	"Group of objects implemented in the point to point wireless
	card to provide information about the duplexor's in the system."
	::= { cwrRadioExpGroups 4 }
END
