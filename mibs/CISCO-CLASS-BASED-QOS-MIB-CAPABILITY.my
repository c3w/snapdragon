-- *****************************************************************
-- CISCO-CLASS-BASED-QOS-MIB-CAPABILITY.my: 
-- Cisco CISCO-CLASS-BASED-QOS-MIB AGENT-CAPABILITIES
--
-- April 2000,2001 Anders Fung
--
-- Copyright (c) 2000 by cisco Systems, Inc.
-- All rights reserved.
--
-- *****************************************************************

CISCO-CLASS-BASED-QOS-MIB-CAPABILITY DEFINITIONS ::= BEGIN

IMPORTS
        MODULE-IDENTITY
                FROM SNMPv2-SMI
        AGENT-CAPABILITIES
                FROM SNMPv2-CONF
        ciscoAgentCapability
                FROM CISCO-SMI;   

ciscoCBQosMibCapability MODULE-IDENTITY
                        LAST-UPDATED    "200106130000Z"
                        ORGANIZATION    "Cisco Systems, Inc."
                        CONTACT-INFO  
                                "       Cisco Systems
                                        Customer Service

                                Postal: 170 West Tasman Drive
                                        San Jose, CA  95134
                                        USA

                                Tel: +1 800 553-NETS

                                E-mail: cs-qos@cisco.com"
                        DESCRIPTION
                                "Agent capabilities for 
                                 CLASS-BASED-QOS-MIB"
                        REVISION        "200106130000Z"
                        DESCRIPTION
                                "Added agent capabilities for Mainline.
                                 Modified capabilities for T train."
                        REVISION        "200012010000Z"
                        DESCRIPTION
                                "Added agent capabilities for T train."
                        REVISION        "200007130000Z"
                        DESCRIPTION
                                "The capabilities description of 
                                 Cisco Class Based QoS MIB."
        ::= { ciscoAgentCapability 186 }

ciscoCBQosMibCapabilityV121R02E7500 AGENT-CAPABILITIES

PRODUCT-RELEASE "Cisco IOS 12.1(2)E on 7500"
STATUS          current
DESCRIPTION     "Class-Based QoS MIB capabilities"

SUPPORTS        CISCO-CLASS-BASED-QOS-MIB
INCLUDES        { 
			cbQosServicePolicyGroup,
			cbQosObjectsGroup,           
			cbQosPolicyMapCfgGroup,      
			cbQosClassMapCfgGroup,       
			cbQosMatchStmtCfgGroup,      
			cbQosQueueingCfgGroup,       
			cbQosREDCfgGroup,            
			cbQosREDClassCfgGroup,       
			cbQosPoliceCfgGroup,         
			cbQosTSCfgGroup,             
			cbQosSetCfgGroup,            
			cbQosClassMapStatsGroup,     
			cbQosMatchStmtStatsGroup,    
			cbQosPoliceStatsGroup,       
			cbQosQueueingStatsGroup,     
			cbQosTSStatsGroup,           
			cbQosREDClassStatsGroup     
                }

    ::= { ciscoCBQosMibCapability 1 } 

ciscoCBQosMibCapabilityV120R12S7500 AGENT-CAPABILITIES

PRODUCT-RELEASE "Cisco IOS 12.0(12)S on 7500"
STATUS          current
DESCRIPTION     "Class-Based QoS MIB capabilities"

SUPPORTS        CISCO-CLASS-BASED-QOS-MIB
INCLUDES        { 
			cbQosServicePolicyGroup,
			cbQosObjectsGroup,           
			cbQosPolicyMapCfgGroup,      
			cbQosClassMapCfgGroup,       
			cbQosMatchStmtCfgGroup,      
			cbQosQueueingCfgGroup,       
			cbQosREDCfgGroup,            
			cbQosREDClassCfgGroup,       
			cbQosPoliceCfgGroup,         
			cbQosTSCfgGroup,             
			cbQosSetCfgGroup,            
			cbQosClassMapStatsGroup,     
			cbQosMatchStmtStatsGroup,    
			cbQosPoliceStatsGroup,       
			cbQosQueueingStatsGroup,     
			cbQosTSStatsGroup,           
			cbQosREDClassStatsGroup,
			cbQosREDClassXmitCountersGroup
                }

    ::= { ciscoCBQosMibCapability 2 } 

ciscoCBQosMibCapabilityV121R05T7200 AGENT-CAPABILITIES

PRODUCT-RELEASE "Cisco IOS 12.1(5)T/12.2 for 7200/lower-end platforms"
STATUS          current
DESCRIPTION     "Class-Based QoS MIB capabilities"

SUPPORTS        CISCO-CLASS-BASED-QOS-MIB
INCLUDES        {
                      cbQosServicePolicyGroup,
                      cbQosObjectsGroup,
                      cbQosPolicyMapCfgGroup,
                      cbQosClassMapCfgGroup,
                      cbQosMatchStmtCfgGroup,
                      cbQosQueueingCfgGroup,
                      cbQosREDCfgGroup,
                      cbQosREDClassCfgGroup,
                      cbQosPoliceCfgGroup,
                      cbQosTSCfgGroup,
                      cbQosSetCfgGroup,
                      cbQosClassMapStatsGroup,
                      cbQosMatchStmtStatsGroup,
                      cbQosPoliceStatsGroup,
                      cbQosQueueingStatsGroup,
                      cbQosTSStatsGroup,
                      cbQosREDClassStatsGroup,
                      cbQosAFPoliceCfgGroup,
                      cbQosAFPoliceStatsGroup,
                      cbQosREDDscpCfgGroup
                }

VARIATION       cbQosQueueingCfgBandwidthUnits
DESCRIPTION     "percentageRemaining not supported"

VARIATION       cbQosSetCfgFeature
DESCRIPTION     "AtmClpBit, FrDeBit and L2Cos not supported" 

    ::= { ciscoCBQosMibCapability 3 }

ciscoCBQosMibCapabilityV122R01T7200 AGENT-CAPABILITIES

PRODUCT-RELEASE "Cisco IOS 12.2(2)T on 7200 and lower-end platforms"
STATUS          current
DESCRIPTION     "Class-Based QoS MIB capabilities"

SUPPORTS        CISCO-CLASS-BASED-QOS-MIB
INCLUDES        {
                      cbQosServicePolicyGroup,
                      cbQosObjectsGroup,
                      cbQosPolicyMapCfgGroup,
                      cbQosClassMapCfgGroup,
                      cbQosMatchStmtCfgGroup,
                      cbQosQueueingCfgGroup,
                      cbQosREDCfgGroup,
                      cbQosREDClassCfgGroup,
                      cbQosPoliceCfgGroup,
                      cbQosTSCfgGroup,
                      cbQosSetCfgGroup,
                      cbQosClassMapStatsGroup,
                      cbQosMatchStmtStatsGroup,
                      cbQosPoliceStatsGroup,
                      cbQosQueueingStatsGroup,
                      cbQosTSStatsGroup,
                      cbQosREDClassStatsGroup,
                      cbQosAFPoliceCfgGroup,
                      cbQosAFPoliceStatsGroup,
                      cbQosREDDscpCfgGroup,
                      cbQosNewSetCfgGroup
                }

    ::= { ciscoCBQosMibCapability 4 }
END
