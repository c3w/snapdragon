-- *****************************************************************
-- CISCO-ITP-XUA-CAPABILITY.my:  ITP M3UA/SUA capability MIB
--
-- April 2002, Shekhar Acharya
--
-- Copyright (c) 2002 by cisco Systems, Inc.
-- All rights reserved.
-- *****************************************************************
CISCO-ITP-XUA-CAPABILITY DEFINITIONS ::= BEGIN

IMPORTS
        MODULE-IDENTITY
                FROM SNMPv2-SMI
                
        AGENT-CAPABILITIES
                FROM SNMPv2-CONF
                
        ciscoAgentCapability
                FROM CISCO-SMI; 
                

ciscoItpXuaCapability MODULE-IDENTITY
        LAST-UPDATED    "200205080000Z"
        ORGANIZATION    "Cisco Systems, Inc."
        CONTACT-INFO
                        "Cisco Systems
                         Customer Service
                        
                         Postal: 170 West Tasman Drive
                                 San Jose, CA  95134
                                 USA
                        
                         Tel: +1 800 553-NETS
                        
                         E-mail: cs-ss7@cisco.com"
        DESCRIPTION
                "Agent capabilities for the CISCO-ITP-XUA-MIB."
                        
        REVISION        "200205080000Z"
        DESCRIPTION
                "Initial version of this MIB module."
        ::= { ciscoAgentCapability 268 }

ciscoItpXuaCapabilityV12R0204MB5 AGENT-CAPABILITIES

        PRODUCT-RELEASE "Cisco IOS 12.2(4)MB5"
        STATUS          current
        DESCRIPTION
                "IOS 12.2(4)MB5 Cisco CISCO-ITP-XUA-MIB.my
                 User Agent MIB capabilities."

        SUPPORTS    CISCO-ITP-XUA-MIB
        INCLUDES    { 
                        ciscoItpXuaScalarsGroup,
                        ciscoItpXuaInstGroup,
                        ciscoItpXuaInstLocalIpGroup,
                        ciscoItpXuaSgmGroup,
                        ciscoItpXuaAspGroup,
                        ciscoItpXuaAspRemoteIpGroup,
                        ciscoItpXuaAspStatsGroup,
                        ciscoItpXuaAsGroup,
                        ciscoItpXuaAspAsGroup,
                        ciscoItpXuaNotifObjectsGroup,
                        ciscoItpXuaNotificationsGroup
                    }

--              Entries in XUA Instance Table

VARIATION       cItpXuaInstProtocol
ACCESS          read-only
DESCRIPTION     "Create/Write access is not supported."

VARIATION       cItpXuaInstShut
ACCESS          read-only
DESCRIPTION     "Create/Write access is not supported."

VARIATION       cItpXuaInstRowStatus
ACCESS          read-only
DESCRIPTION     "Create/Write access is not supported."

--              Entries in XUA Instance Local IP Table

VARIATION       cItpXuaInstLocalIpType
ACCESS          read-only
DESCRIPTION     "Create/Write access is not supported."

VARIATION       cItpXuaInstLocalIpAddr
ACCESS          read-only
DESCRIPTION     "Create/Write access is not supported."

VARIATION       cItpXuaInstLocalIpRowStatus
ACCESS          read-only
DESCRIPTION     "Create/Write access is not supported."

--              Entries in Signaling Gateway Mate (SGM) Table

VARIATION       cItpXuaSgmLocalPort
ACCESS          read-only
DESCRIPTION     "Create/Write access is not supported."

VARIATION       cItpXuaSgmRemotePort
ACCESS          read-only
DESCRIPTION     "Create/Write access is not supported."

VARIATION       cItpXuaSgmShut
ACCESS          read-only
DESCRIPTION     "Create/Write access is not supported."

VARIATION       cItpXuaSgmQosClass
ACCESS          read-only
DESCRIPTION     "Create/Write access is not supported."

VARIATION       cItpXuaSgmPassive
ACCESS          read-only
DESCRIPTION     "Create/Write access is not supported."

VARIATION       cItpXuaSgmRowStatus
ACCESS          read-only
DESCRIPTION     "Create/Write access is not supported."

--              Entries in Application Server Process (ASP) Table

VARIATION       cItpXuaAspLocalPort
ACCESS          read-only
DESCRIPTION     "Create/Write access is not supported."

VARIATION       cItpXuaAspRemotePort
ACCESS          read-only
DESCRIPTION     "Create/Write access is not supported."

VARIATION       cItpXuaAspProtocol
ACCESS          read-only
DESCRIPTION     "Create/Write access is not supported."

VARIATION       cItpXuaAspShut
ACCESS          read-only
DESCRIPTION     "Create/Write access is not supported."

VARIATION       cItpXuaAspBlocked
ACCESS          read-only
DESCRIPTION     "Create/Write access is not supported."

VARIATION       cItpXuaAspQosClass
ACCESS          read-only
DESCRIPTION     "Create/Write access is not supported."

VARIATION       cItpXuaAspRowStatus
ACCESS          read-only
DESCRIPTION     "Create/Write access is not supported."

--              Entries in ASP Remote IP Table

VARIATION       cItpXuaAspRemoteIpType
ACCESS          read-only
DESCRIPTION     "Create/Write access is not supported."

VARIATION       cItpXuaAspRemoteIpAddr
ACCESS          read-only
DESCRIPTION     "Create/Write access is not supported."

VARIATION       cItpXuaAspRemoteIpRowStatus
ACCESS          read-only
DESCRIPTION     "Create/Write access is not supported."

--              Entries in Application Server (AS) Table

VARIATION       cItpXuaAsProtocol
ACCESS          read-only
DESCRIPTION     "Create/Write access is not supported."

VARIATION       cItpXuaAsShut
ACCESS          read-only
DESCRIPTION     "Create/Write access is not supported."

VARIATION       cItpXuaAsQosClass
ACCESS          read-only
DESCRIPTION     "Create/Write access is not supported."

VARIATION       cItpXuaAsTrafMode
ACCESS          read-only
DESCRIPTION     "Create/Write access is not supported."

VARIATION       cItpXuaAsRkParameters
ACCESS          read-only
DESCRIPTION     "Create/Write access is not supported."

VARIATION       cItpXuaAsRkDpc
ACCESS          read-only
DESCRIPTION     "Create/Write access is not supported."

VARIATION       cItpXuaAsRkOpc
ACCESS          read-only
DESCRIPTION     "Create/Write access is not supported."

VARIATION       cItpXuaAsRkOpcMask
ACCESS          read-only
DESCRIPTION     "Create/Write access is not supported."

VARIATION       cItpXuaAsRkSi
ACCESS          read-only
DESCRIPTION     "Create/Write access is not supported."

VARIATION       cItpXuaAsRkSsn
ACCESS          read-only
DESCRIPTION     "Create/Write access is not supported."

VARIATION       cItpXuaAsRkGtt
ACCESS          read-only
DESCRIPTION     "Create/Write access is not supported."

VARIATION       cItpXuaAsRkCicMin
ACCESS          read-only
DESCRIPTION     "Create/Write access is not supported."

VARIATION       cItpXuaAsRkCicMax
ACCESS          read-only
DESCRIPTION     "Create/Write access is not supported."

VARIATION       cItpXuaAsRowStatus
ACCESS          read-only
DESCRIPTION     "Create/Write access is not supported."

--              Entries in ASP-AS Table

VARIATION       cItpXuaAspAsRowStatus
ACCESS          read-only
DESCRIPTION     "Create/Write access is not supported."

    ::= { ciscoItpXuaCapability 1 }

END
