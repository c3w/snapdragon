-- *********************************************************************
-- CISCO-PORT-CHANNEL-MIB.my: Port Channel mib
--
-- September 2002, Srini Kode
--
-- Copyright (c) 2002 by cisco Systems, Inc.
-- All rights reserved.
-- 
-- *********************************************************************
CISCO-PORT-CHANNEL-MIB DEFINITIONS ::= BEGIN

IMPORTS
        MODULE-IDENTITY, OBJECT-TYPE,
        Unsigned32                             FROM SNMPv2-SMI
        MODULE-COMPLIANCE, OBJECT-GROUP        FROM SNMPv2-CONF
        TEXTUAL-CONVENTION, RowStatus,
        TimeStamp                              FROM SNMPv2-TC
        SnmpAdminString                        FROM SNMP-FRAMEWORK-MIB
        InterfaceIndex                         FROM IF-MIB
        ciscoMgmt                              FROM CISCO-SMI
        PortMemberList                         FROM CISCO-ST-TC;
                
         
ciscoPortChannelMIB MODULE-IDENTITY
        LAST-UPDATED "200210020000Z"
        ORGANIZATION "Cisco Systems Inc."
        CONTACT-INFO
                "     Cisco Systems
                      Customer Service
                Postal: 170 W Tasman Drive
                      San Jose, CA  95134
                      USA
                Tel: +1 800 553 -NETS
                E-mail: cs-san@cisco.com"
        DESCRIPTION
            "The MIB module for management of Port Channel ports.
             In addition to this MIB, CISCO-FC-FE-MIB and interface
             mib (rfc2863) will also contain entries for Port Channel
             ports."
        REVISION    "200210020000Z"
        DESCRIPTION
            "Initial version of this MIB module."
        ::= { ciscoMgmt 285 }

ciscoPortChannelObjects   OBJECT IDENTIFIER 
                               ::= { ciscoPortChannelMIB 1 }
portChannelMIBConformance OBJECT IDENTIFIER 
                               ::= { ciscoPortChannelMIB 2 }
portChannelConfig         OBJECT IDENTIFIER 
                               ::= { ciscoPortChannelObjects 1 }
portChannelStatistics     OBJECT IDENTIFIER 
                               ::= { ciscoPortChannelObjects 2 }
portChannelNotification   OBJECT IDENTIFIER 
                               ::= { ciscoPortChannelObjects 3 }
portChannelNotifications   OBJECT IDENTIFIER 
                               ::= { portChannelNotification 0 }

-- Textual Conventions

PortChannelMode ::= TEXTUAL-CONVENTION
     STATUS         current
     DESCRIPTION    
           "Defines how a Port Channel does channeling.
                     auto(1)      - place the port into passive 
                                    negotiation state, in which the
                                    port waits for its peer to 
                                    initiate negotiation.
                     on(2)        - force the port to enable 
                                    channeling.
                     off(3)       - channeling is disabled.
                     desirable(4) - place the port into active
                                    negotiating state, in which the
                                    port initiates negotiations with
                                    its peer and if the peer end 
                                    agrees, channeling is enabled 
                                    between them. "
     SYNTAX         INTEGER {
                       auto(1),
                       on(2),
                       off(3),
                       desirable(4)
                    }

--
-- Port Channel Table
--

portChannelTable  OBJECT-TYPE
        SYNTAX     SEQUENCE OF PortChannelEntry 
        MAX-ACCESS not-accessible
        STATUS     current
        DESCRIPTION
              "This table facilitates the creation and deletion of a
               Port Channel interface to achieve higher bandwidths
               than just one E_port. More than one E_port can be a 
               member of an Port Channel port.
               NOTE:Only E_ports can be members of an Port Channel
               port.
               
               A port is added to a Port Channel port by setting 
               portChannelMemberList,and the 'manner' in which the 
               agent performs the type of addition is determined 
               by the value of portChannelAddType.
               
               During the period when port(s) is being added to the
               Port Channel, the agent will not allow to change any 
               parameters of the port(s) being added. Also if the 
               operation is successful (i.e. port(s) is added to the 
               Port Channel) then also the agent will not allow to 
               change any parameters of the individual port(s) that is
               added. But any change done to the Port Channel port
               will also be applied to the port(s) which are member(s)
               of this Port channel port. Once a port(s) is removed
               from a Port Channel Port it will retain the values that
               it had when it was a member of the Port Channel port.
               It will not have the old values it had before joining
               the Port Channel port. 

               The port(s) that are added/removed to/from a 
               Port Channel port will be put into administratively
               down (ifAdminStatus='down') which results into
               operationally down(ifOperStatus='down'). To bring the 
               port up again, the user has to set the port to be
               administratively up(ifAdminStatus='up'). Then the port
               goes through its initialization cycle to become 
               active(ifOperStatus='up'). "
        ::= { portChannelConfig 1 }

portChannelEntry OBJECT-TYPE
        SYNTAX     PortChannelEntry 
        MAX-ACCESS not-accessible
        STATUS     current
        DESCRIPTION
              "There is one entry in this table for each created
               Port Channel port. "
        INDEX { portChannelIndex }
        ::= { portChannelTable 1 }

PortChannelEntry ::= SEQUENCE {
              portChannelIndex                  Unsigned32,
              portChannelIfIndex                InterfaceIndex,
              portChannelAdminChannelMode       PortChannelMode,
              portChannelOperChannelMode        PortChannelMode,
              portChannelAddType                INTEGER,
              portChannelLastActionStatus       INTEGER,
              portChannelLastActionStatusCause  SnmpAdminString,
              portChannelLastActionTime         TimeStamp,
              portChannelMemberList             PortMemberList,
              portChannelCreationTime           TimeStamp,
              portChannelRowStatus              RowStatus
}

portChannelIndex OBJECT-TYPE
        SYNTAX      Unsigned32 (1..2048)
        MAX-ACCESS  not-accessible
        STATUS      current
        DESCRIPTION
              "An index that uniquely identifies an entry in the
               portChannelTable table. "
        ::= { portChannelEntry 1 }

portChannelIfIndex OBJECT-TYPE
        SYNTAX      InterfaceIndex
        MAX-ACCESS  read-only
        STATUS      current
        DESCRIPTION
              "The ifIndex of this interface. "
        ::= { portChannelEntry 2 }

portChannelAdminChannelMode OBJECT-TYPE
        SYNTAX      PortChannelMode
        MAX-ACCESS  read-create
        STATUS      current
        DESCRIPTION
              "The channel mode desired by the network manager.
               If this object is configured to be auto(1), then the 
               'portChannelOperChannelMode' will show the current
                operating channel mode of port. "
        DEFVAL {on}
        ::= { portChannelEntry 3 }

portChannelOperChannelMode OBJECT-TYPE
        SYNTAX      PortChannelMode
        MAX-ACCESS  read-only
        STATUS      current
        DESCRIPTION
              "The current operating channel mode of the port. "
        ::= { portChannelEntry 4 }

portChannelAddType OBJECT-TYPE
        SYNTAX      INTEGER {
                       normal(1),
                       force(2)
                    }
        MAX-ACCESS  read-create
        STATUS      current
        DESCRIPTION
              "The method to be adopted by the agent to add 
               port(s) to a Port Channel port.
               If normal(1), then a compatibility check is done on the
               parameters of the port(s) being added to this Port
               Channel. The port(s) being added must have the same
               physical and configured parameters as the Port
               Channel port.
               If force(2), a compatibility check is done on only
               physical parameters. The port(s) being added to this
               Port Channel port must have same physical parameters.
               The operation will fail only if the physical parameters
               are not same. The configured parameters of the 
               port(s) being added are overwritten by 
               configured parameters of this Port Channel port. "
        DEFVAL {normal}
        ::= { portChannelEntry 5 }

portChannelLastActionStatus OBJECT-TYPE
        SYNTAX      INTEGER {
                       successful(1),
                       failed(2)
                    }
        MAX-ACCESS  read-only
        STATUS      current
        DESCRIPTION
              "The status of the last operation (add or remove a 
               member) done to change the member list of a Port 
               Channel Port.
               When no ports are added or the last operation is
               successful then this object will be successful(1).
               If this value is failed(2) then the user can look
               at portChannelLastAddStatusCause to find the reason
               of failure. "
        ::= { portChannelEntry 6 }

portChannelLastActionStatusCause OBJECT-TYPE
        SYNTAX      SnmpAdminString
        MAX-ACCESS  read-only
        STATUS      current
        DESCRIPTION
              "The cause of failure to last operation (add or remove
               a member) done to change the member list of a Port
               Channel port. This object will be zero length string
               if 'portChannelLastActionStatus' is successful(1). "
        ::= { portChannelEntry 7 }

portChannelLastActionTime OBJECT-TYPE
        SYNTAX      TimeStamp
        MAX-ACCESS  read-only
        STATUS      current
        DESCRIPTION
              "The timestamp indicating the time of last action
               performed on this entry. "
        ::= { portChannelEntry 8 }

portChannelMemberList OBJECT-TYPE
        SYNTAX      PortMemberList
        MAX-ACCESS  read-create
        STATUS      current
        DESCRIPTION
              "The list of ifIndex's of the E_ports that are members
               of this Port Channel port. "
        DEFVAL {''H}
        ::= { portChannelEntry 9 }

portChannelCreationTime OBJECT-TYPE
        SYNTAX      TimeStamp
        MAX-ACCESS  read-only
        STATUS      current
        DESCRIPTION
              "The timestamp of this entry's creation time.
               Note that at this creation time, a discontinuity occurs
               in the statistic/error counters which are defined in
               CISCO-FC-FE-MIB, and which are associated with this
               Port Channel. "
        ::= { portChannelEntry 10 }

portChannelRowStatus OBJECT-TYPE
        SYNTAX      RowStatus
        MAX-ACCESS  read-create
        STATUS      current
        DESCRIPTION
              "The status of this conceptual row. "   
        ::= { portChannelEntry 11 }



-- Conformance


portChannelMIBCompliances OBJECT IDENTIFIER 
                             ::= { portChannelMIBConformance 1 }
portChannelMIBGroups OBJECT IDENTIFIER 
                             ::= { portChannelMIBConformance 2 }
portChannelMIBCompliance MODULE-COMPLIANCE
        STATUS   current
        DESCRIPTION
                "The compliance statement for entities which 
                implement the CISCO-PORT-CHANNEL-MIB mib."
        MODULE MANDATORY-GROUPS { portChannelGroup } 
 
--      OBJECT  portChannelIndex
--          SYNTAX     Unsigned32 (1..128)
--          DESCRIPTION 
--                 "It is compliant to support a maximum value for 
--                  this object which is smaller than the defined 
--                  maximum value."
                                            
        OBJECT  portChannelRowStatus
            SYNTAX     INTEGER {             
                     active(1),
                     createAndGo(4),
                     destroy(6)}
            DESCRIPTION 
                   "Only three values 'createAndGo', 'destroy' and 
                   'active' out of the six enumerated values need to
                    be supported."
                   
        ::= { portChannelMIBCompliances 1 }       

-- Units of Conformance

portChannelGroup  OBJECT-GROUP
     OBJECTS  { portChannelIfIndex, portChannelAdminChannelMode, 
                portChannelOperChannelMode, portChannelAddType,
                portChannelLastActionStatus,
                portChannelLastActionStatusCause,
                portChannelLastActionTime,
                portChannelMemberList,portChannelCreationTime,
                portChannelRowStatus }
     STATUS  current
     DESCRIPTION
            "A collection of objects related to Port Channel Interface
             parameters."
        ::= { portChannelMIBGroups 1 }    
END
