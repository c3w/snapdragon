CISCO-IGMP-SNOOPING-MIB DEFINITIONS ::= BEGIN

IMPORTS 
    OBJECT-TYPE,
    MODULE-IDENTITY, 
    Counter32
        FROM SNMPv2-SMI

    TruthValue
        FROM SNMPv2-TC

    MODULE-COMPLIANCE, OBJECT-GROUP
        FROM SNMPv2-CONF
    
    ifIndex
        FROM IF-MIB

    ciscoMgmt
        FROM CISCO-SMI;
    
ciscoIgmpSnoopingMIB MODULE-IDENTITY
    LAST-UPDATED "200205050000Z" 
    ORGANIZATION "Cisco System, Inc."
    CONTACT-INFO 
            "         Cisco Systems
                      Customer Service

              Postal: 170 W Tasman Drive
                      San Jose, CA  95134
                      USA

                 Tel: +1 800 553-NETS

        E-mail: cs-snmp@cisco.com, cs-ipmulticast@cisco.com"
    DESCRIPTION 
        "The MIB module for IGMP Snooping feature. 

         Internet Group Management Protocol (IGMP) is the protocol used 
         by IPv4 end hosts to indicates their interest in receiving 
         multicast traffic for certain multicast groups to neighboring 
         multicast routers. Version 3 of IGMP adds support for source 
         base filtering; which means the end hosts can specifically 
         indicate to receive or not-receive multicast packets from 
         specific source addresses. This information is used by the 
         multicast routers to restrict forwarding of multicast traffic 
         for the host.

         IGMPv3 Snooping is a switch protocol. A switch that implements 
         IGMPv3 Snooping listens to the IGMP messages exchanged between 
         the hosts and router, then provides selective transmission of 
         multicast traffic based on source lists contained in the 
         messages. It also provides selective transmission of multicast 
         data based on source IP address onto the ports that are 
         interested."
 
    REVISION    "200205050000Z"
    DESCRIPTION
        "Initial version of this MIB module."

    ::= {ciscoMgmt 263}

ciscoIgmpSnoopingNotification 
                    OBJECT IDENTIFIER ::= {ciscoIgmpSnoopingMIB 0}
ciscoIgmpSnoopingMIBObject 
                    OBJECT IDENTIFIER ::= {ciscoIgmpSnoopingMIB 1}


-------------------------------------------

cisSystemInfo  OBJECT IDENTIFIER ::= {ciscoIgmpSnoopingMIBObject 1}
cisStatisticsInfo OBJECT IDENTIFIER ::= {ciscoIgmpSnoopingMIBObject 2}

------------------------------------------

------------------------------------------
--- The cisSystemInfo group
------------------------------------------


cisIgmpSnoopingEnabled OBJECT-TYPE
    SYNTAX       TruthValue
    MAX-ACCESS   read-write
    STATUS       current
    DESCRIPTION
        "This object indicates whether IGMP Snooping has been 
        enabled for the system."
    ::= {cisSystemInfo 1}

cisV3ProcessEnabledAdminStatus OBJECT-TYPE
    SYNTAX       TruthValue
    MAX-ACCESS   read-write
    STATUS       current
    DESCRIPTION
        "This object indicates the administrative status of IGMP v3
         processing in the system. With the condition that IGMP
         protocol has been enabled, a system will process IGMPv3 
         messages if this object is set to 'true', or it will process
         only IGMPv1/v2 messages if this object is set to 'false'."
    ::= {cisSystemInfo 2}

cisV3ProcessEnabledOperStatus OBJECT-TYPE
    SYNTAX       TruthValue
    MAX-ACCESS   read-only
    STATUS       current
    DESCRIPTION
        "This object indicates the current operational status of IGMP 
         v3 processing in the system. This object is enabled if the 
         system is operating with IGMPv3 protocol. Value of this object
         will be set to 'true' if the system is operating in IGMP v3,
         and 'false' if it is operating in IGMPv1/v2."
    ::= {cisSystemInfo 3}

cisFastLeaveEnabled OBJECT-TYPE
    SYNTAX       TruthValue
    MAX-ACCESS   read-write
    STATUS       current
    DESCRIPTION
        "This object indicates whether Fast-Leave mechanism has been
         configured to be enabled in the system. If Fast-Leave is 
         enabled in the switch, IGMP Snooping will prune the port on 
         which an IGMP leave message has been received without waiting 
         for the Group Specific Query to timeout to determine whether 
         there are any more hosts on that port for that group. If 
         cisV3ProcessEnabledOperStatus's value is 'false', this object 
         will not have any effect."
    ::= {cisSystemInfo 4}

cisFastBlockEnabled OBJECT-TYPE
    SYNTAX       TruthValue
    MAX-ACCESS   read-write
    STATUS       current
    DESCRIPTION
        "The object indicates whether Fast-Block mechanism has been 
         enabled for the system. This object only has effect if the
         value of cisV3ProcessEnabledOperStatus is 'true'."
    ::= {cisSystemInfo 5}



------------------------------------------
--- The cisStatisticsInfo group.
------------------------------------------

cisInterfaceStatsTable OBJECT-TYPE
    SYNTAX       SEQUENCE OF CisInterfaceStatsEntry
    MAX-ACCESS   not-accessible
    STATUS       current
    DESCRIPTION
        "Table contains statistics information of IGMP snooping. An 
         entry appears in this table for each IGMP Snooping capable 
         interface in the device."
    ::= {cisStatisticsInfo 1}

cisInterfaceStatsEntry OBJECT-TYPE
    SYNTAX       CisInterfaceStatsEntry
    MAX-ACCESS   not-accessible
    STATUS       current
    DESCRIPTION
        "An entry contains multicasting statistics information for a 
         specific IGMP Snooping capable interface. It provides statistic
         information of IGMP messages and reports that have been 
         transmitted and received at the interface." 
    INDEX {ifIndex}
    ::= {cisInterfaceStatsTable 1}
 
CisInterfaceStatsEntry ::= SEQUENCE {
    cisTxGeneralQueries        Counter32,
    cisTxGroupSpecificQueries  Counter32,
    cisTxReports               Counter32,
    cisTxLeaves                Counter32,
    cisRxGeneralQueries        Counter32,
    cisRxGroupSpecificQueries  Counter32,
    cisRxReports               Counter32,
    cisRxLeaves                Counter32,
    cisRxValidPackets          Counter32,
    cisRxInvalidPackets        Counter32,
    cisRxOtherPackets          Counter32,
    cisRxMACGeneralQueries     Counter32,
    cisRxTopoNotifications     Counter32,
    cisV3Allows                Counter32,
    cisV3Blocks                Counter32,
    cisV3IsIncluded            Counter32,
    cisV3IsExcluded            Counter32,
    cisV3ToIncluded            Counter32,
    cisV3ToExcluded            Counter32
}

cisTxGeneralQueries         OBJECT-TYPE
    SYNTAX       Counter32
    MAX-ACCESS   read-only
    STATUS       current
    DESCRIPTION  
        "Number of General Queries that have been transmitted through
         an interface."
    ::= {cisInterfaceStatsEntry 1}

cisTxGroupSpecificQueries   OBJECT-TYPE 
    SYNTAX       Counter32
    MAX-ACCESS   read-only
    STATUS       current
    DESCRIPTION
        "Total Group Specific Queries that have been transmitted
         through an interface."
    ::= {cisInterfaceStatsEntry 2}

cisTxReports                OBJECT-TYPE
    SYNTAX       Counter32
    MAX-ACCESS   read-only
    STATUS       current
    DESCRIPTION
        "Total Membership Reports that have been transmitted through
         an interface."
    ::= {cisInterfaceStatsEntry 3}

cisTxLeaves                 OBJECT-TYPE
    SYNTAX       Counter32
    MAX-ACCESS   read-only
    STATUS       current
    DESCRIPTION
        "Total Leave messages that have been transmitted through an 
         interface."
    ::= {cisInterfaceStatsEntry 4}

cisRxGeneralQueries         OBJECT-TYPE
    SYNTAX       Counter32
    MAX-ACCESS   read-only
    STATUS       current
    DESCRIPTION 
        "Total General Queries that have been received at an interface."
    ::= {cisInterfaceStatsEntry 5}

cisRxGroupSpecificQueries   OBJECT-TYPE
    SYNTAX       Counter32
    MAX-ACCESS   read-only
    STATUS       current
    DESCRIPTION
        "Total Group Specific Queries that have been received at an 
         interface."
    ::= {cisInterfaceStatsEntry 6}

cisRxReports                 OBJECT-TYPE 
    SYNTAX       Counter32
    MAX-ACCESS   read-only
    STATUS       current
    DESCRIPTION
        "Total Membership Reports that have been received at an 
         interface."
    ::= {cisInterfaceStatsEntry 7}

cisRxLeaves                  OBJECT-TYPE
    SYNTAX       Counter32
    MAX-ACCESS   read-only
    STATUS       current
    DESCRIPTION
        "Total Leave messages that have been received at an interface."
    ::= {cisInterfaceStatsEntry 8}

cisRxValidPackets           OBJECT-TYPE
    SYNTAX       Counter32
    MAX-ACCESS   read-only
    STATUS       current
    DESCRIPTION
        "Total valid IGMP packets have been received at an interface."
    ::= {cisInterfaceStatsEntry 9}

cisRxInvalidPackets         OBJECT-TYPE
    SYNTAX       Counter32
    MAX-ACCESS   read-only
    STATUS       current
    DESCRIPTION
        "Total packets those are not a valid IGMP messages received
         at an interface."
    ::= {cisInterfaceStatsEntry 10}

cisRxOtherPackets           OBJECT-TYPE
    SYNTAX       Counter32
    MAX-ACCESS   read-only
    STATUS       current
    DESCRIPTION
        "Total other types of valid IGMP messages have been received
         at an interface, comprising learning queries and messages."
    ::= {cisInterfaceStatsEntry 11}

cisRxMACGeneralQueries      OBJECT-TYPE
    SYNTAX       Counter32
    MAX-ACCESS   read-only
    STATUS       current
    DESCRIPTION
        "Total MAC-based General Queries that have been received at
         an interface."
    ::= {cisInterfaceStatsEntry 12}

cisRxTopoNotifications      OBJECT-TYPE
    SYNTAX       Counter32
    MAX-ACCESS   read-only
    STATUS       current
    DESCRIPTION
        "Total Topology Notification that have been received at an 
         interface."
    ::= {cisInterfaceStatsEntry 13}

cisV3Allows                 OBJECT-TYPE
    SYNTAX       Counter32
    MAX-ACCESS   read-only
    STATUS       current
    DESCRIPTION
        "Number of Source-List-Change records with the record type 
         ALLOW_NEW_SOURCES that have been sent from hosts connected 
         to an interface. This record type indicates that the Source
         Address fields in this Group Record contain a list of 
         additional sources that the system wishes to hear from, for
         packets sent to the specified multicast address."
    ::= {cisInterfaceStatsEntry 14}


cisV3Blocks                 OBJECT-TYPE
    SYNTAX       Counter32
    MAX-ACCESS   read-only
    STATUS       current
    DESCRIPTION
        "Number of Source-List-Change records with the record type
         BLOCK_OLD_SOURCE that have been sent from hosts connected to
         an interface. This record type indicates that the Source
         Address fields in this Group Record contain a list of the 
         sources that the system no longer wishes to hear from, for 
         packets sent to the specified multicast address."
    ::= {cisInterfaceStatsEntry 15}

cisV3IsIncluded             OBJECT-TYPE
    SYNTAX       Counter32
    MAX-ACCESS   read-only
    STATUS       current
    DESCRIPTION
        "Number of Current-State records with the state MODE_IS_INCLUDE 
         that have been sent from hosts in response to a Query received
         at an interface. This state indicates that the interface has a 
         filter mode of INCLUDE for the specified multicast address."
    ::= {cisInterfaceStatsEntry 16}

cisV3IsExcluded             OBJECT-TYPE
    SYNTAX       Counter32
    MAX-ACCESS   read-only
    STATUS       current
    DESCRIPTION
        "Number of Current-State records with the state MODE_IS_EXCLUDE
         that have been sent from hosts in response to a Query received
         at an interfaces. This state indicates that the interface has a
         filter mode of EXCLUDE for the specified multicast address."
    ::= {cisInterfaceStatsEntry 17}

cisV3ToIncluded             OBJECT-TYPE
    SYNTAX       Counter32
    MAX-ACCESS   read-only
    STATUS       current
    DESCRIPTION 
        "Number of Filter-Mode-Change records with the record type 
         CHANGE_TO_INCLUDE_MODE that have been sent through an 
         interface. This type of record indicates that the filter mode
         has been changed to INCLUDE mode for the specified multicast 
         address, and the Source Address fields in this Group Record 
         will contain the new source list for the specified multicast
         address, if it is not empty."
    ::= {cisInterfaceStatsEntry 18}

cisV3ToExcluded             OBJECT-TYPE
    SYNTAX       Counter32
    MAX-ACCESS   read-only
    STATUS       current
    DESCRIPTION
        "Number of Filter-Mode-Change records with the record type
         CHANGE_TO_EXCLUDE_MODE that have been sent through an 
         interface. This type of record indicates that the filter mode
         has been changed to EXCLUDE mode for the specified multicast
         address, and the Source Address fields in this Group Record
         will contain the new source list for the specified multicast
         address, if it is not empty."
    ::= {cisInterfaceStatsEntry 19}

------------------------------------------
-- Conformance Information
------------------------------------------
cisMIBConformance OBJECT IDENTIFIER ::= {ciscoIgmpSnoopingMIB 2}
cisMIBCompliances OBJECT IDENTIFIER ::= {cisMIBConformance 1}
cisMIBGroups OBJECT IDENTIFIER ::= {cisMIBConformance 2}

-- Compliance statements

cisV2Compliance MODULE-COMPLIANCE
     STATUS        current
     DESCRIPTION
         "The compliance statement for device support IGMPv1/v2 
          Snooping protocol."
     MODULE
         MANDATORY-GROUPS {
             cisSystemGroup
         }

         GROUP     cisSystemV2Group
         DESCRIPTION
             "This group is mandatory in systems that supports
              global configuration for IGMPv2 Snooping feature."

         GROUP    cisStatsGroup
         DESCRIPTION
             "This group is optional, and should be implemented if the
              system provides statistics information of IGMP Snooping
              protocol version 1 and 2."
     ::= {cisMIBCompliances 1}

cisV3Compliance MODULE-COMPLIANCE
     STATUS         current
     DESCRIPTION
         "The compliance statement for device support IGMPv3 Snooping
          protocol."
     MODULE
         MANDATORY-GROUPS {
             cisSystemGroup
         }

         GROUP     cisSystemV2Group
         DESCRIPTION
             "This group is mandatory in systems that support global
              configuration for IGMPv2 Snooping feature."
       
         GROUP     cisSystemV3Group
         DESCRIPTION
             "This group is mandatory in systems that support global
              configuration for IGMPv3 Snooping feature."

         GROUP    cisStatsGroup
         DESCRIPTION
             "This group is optional, and should be implemented if the 
              system provides statistics information of IGMP Snooping 
              protocol version 1 and 2."

         GROUP    cisV3StatsGroup
         DESCRIPTION
             "This group is optional, and should be implemented if the
              system provides statistics information of IGMP Snooping
              protocol version 3."
     ::= {cisMIBCompliances 2}

-- Units of Conformance
cisSystemGroup OBJECT-GROUP
     OBJECTS {
         cisIgmpSnoopingEnabled
     }
     STATUS   current
     DESCRIPTION
         "A collection of objects providing global system information 
          about, and control over, IGMP Snooping protocol operation on
          device."
     ::= {cisMIBGroups 1}

cisSystemV2Group OBJECT-GROUP
     OBJECTS {
          cisFastLeaveEnabled
     }
     STATUS  current
     DESCRIPTION
         "A collection of additional objects providing global system 
          information about, and control over, IGMPv2 Snooping protocol 
          operation on the device."
     ::= {cisMIBGroups 2}

cisSystemV3Group OBJECT-GROUP
     OBJECTS {
         cisV3ProcessEnabledAdminStatus,
         cisV3ProcessEnabledOperStatus,
         cisFastBlockEnabled
     }
     STATUS   current
     DESCRIPTION
         "A collection of additional objects providing global system 
          information about, and control over, IGMPv3 Snooping protocol 
          operation on the device."
     ::= {cisMIBGroups 3}
     
cisStatsGroup OBJECT-GROUP
     OBJECTS {
         cisTxGeneralQueries,       
         cisTxGroupSpecificQueries, 
         cisTxReports,              
         cisTxLeaves,               
         cisRxGeneralQueries,       
         cisRxGroupSpecificQueries, 
         cisRxReports,               
         cisRxLeaves,                
         cisRxValidPackets,         
         cisRxInvalidPackets,       
         cisRxOtherPackets,         
         cisRxMACGeneralQueries,      
         cisRxTopoNotifications       
     }
     STATUS   current
     DESCRIPTION
         "A collection of objects providing statistics information of
          IGMP Snooping version 1 and 2."
     ::= {cisMIBGroups 4}

cisV3StatsGroup OBJECT-GROUP
     OBJECTS {
          cisV3Allows,
          cisV3Blocks,
          cisV3IsIncluded,
          cisV3IsExcluded,
          cisV3ToIncluded,
          cisV3ToExcluded
     }
     STATUS current
     DESCRIPTION
         "A collection of objects providing additional statistics
          information of IGMP Snooping version 3."
     ::= {cisMIBGroups 5}

END
