--*****************************************************************
-- CISCO-AAL5-MIB.my : CISCO AAL5 MIB file
--      
-- Novermber 1996, Liqin Dong
--
-- Copyright (c) 1997 by cisco Systems, Inc.
-- All rights reserved.
--
--*****************************************************************

CISCO-AAL5-MIB DEFINITIONS ::= BEGIN
 
IMPORTS
        MODULE-IDENTITY,
        OBJECT-TYPE,
        Counter32
                FROM SNMPv2-SMI
        MODULE-COMPLIANCE,
        OBJECT-GROUP
                FROM SNMPv2-CONF
        ciscoMgmt
                FROM CISCO-SMI
        aal5VccEntry
                FROM ATM-MIB;
 
ciscoAal5MIB    MODULE-IDENTITY
        LAST-UPDATED    "9611150000Z"
        ORGANIZATION    "Cisco Systems, Inc."
        CONTACT-INFO
                "       Cisco Systems
                        Customer Service
 
                Postal: 170 W Tasman Drive
                        San Jose, CA  95134
                        USA
 
                   Tel: +1 800 553-NETS
 
                E-mail: cs-atm@cisco.com"
        DESCRIPTION
                "Cisco Enterprise AAL5 MIB file that provide AAL5
		 specific information that are either excluded by 
	         RFC 1695 or specific to Cisco product"
        REVISION        "9611150000Z"
        DESCRIPTION
                "Initial version of this MIB module."
        ::= { ciscoMgmt 66 }
 
 
ciscoAal5MIBObjects    	OBJECT IDENTIFIER ::= { ciscoAal5MIB 1 } 
cAal5Connections	OBJECT IDENTIFIER ::= { ciscoAal5MIBObjects 1 }
 
-- This table augments the aal5VccTable defined in RFC 1695.
-- It contains additional AAL5 performance statistics of a VCC 
-- at the interface associated with an AAL5 entity in an ATM 
-- host or ATM switch. 

cAal5VccTable OBJECT-TYPE
	SYNTAX      SEQUENCE OF CAal5VccEntry
        MAX-ACCESS   not-accessible
        STATUS       current
        DESCRIPTION
         "This table contains AAL5 VCC performance 
          parameters beyond that provided by aal5VccEntry
	  defined in RFC1695."
        ::= { cAal5Connections 1 }
 
cAal5VccEntry OBJECT-TYPE
	SYNTAX         CAal5VccEntry
	MAX-ACCESS     not-accessible
        STATUS         current
        DESCRIPTION
         "This list contains the additional AAL5 VCC performance 
	  parameters beyond that provided by aal5VccEntry defined
	  in RFC1695."
        AUGMENTS { aal5VccEntry }
        ::= { cAal5VccTable 1 }
 
CAal5VccEntry ::= SEQUENCE  {
        cAal5VccInPkts		Counter32,
        cAal5VccOutPkts		Counter32,
        cAal5VccInOctets	Counter32,
        cAal5VccOutOctets	Counter32
        }
 
cAal5VccInPkts 		OBJECT-TYPE
	SYNTAX      	Counter32
        MAX-ACCESS  	read-only
        STATUS      	current
        DESCRIPTION
         "The number of AAL5 CPCS PDUs received on this AAL5 VCC at the
          interface associated with an AAL5 entity."
        ::= { cAal5VccEntry 1 }
 
cAal5VccOutPkts		OBJECT-TYPE
	SYNTAX  	Counter32
        MAX-ACCESS  	read-only
        STATUS          current
        DESCRIPTION
         "The number of AAL5 CPCS PDUs transmitted on this AAL5 VCC at
	  the interface associated with an AAL5 entity."
	::= { cAal5VccEntry 2 }

cAal5VccInOctets	OBJECT-TYPE
	SYNTAX  	Counter32
        MAX-ACCESS  	read-only
        STATUS          current
        DESCRIPTION
         "The number of AAL5 CPCS PDU octets received on this AAL5 VCC
	  at the interface associated with an AAL5 entity."
	::= { cAal5VccEntry 3 }

cAal5VccOutOctets	OBJECT-TYPE
	SYNTAX  	Counter32
        MAX-ACCESS  	read-only
        STATUS          current
        DESCRIPTION
         "The number of AAL5 CPCS PDU octets transmitted on this AAL5 VCC
 	 at the interface associated with an AAL5 entity."
	::= { cAal5VccEntry 4 } 
 
 
-- Conformance Information
 
ciscoAal5MIBConformance OBJECT IDENTIFIER ::= { ciscoAal5MIB 3 }
ciscoAal5MIBCompliances OBJECT IDENTIFIER ::= { ciscoAal5MIBConformance 1 }
ciscoAal5MIBGroups      OBJECT IDENTIFIER ::= { ciscoAal5MIBConformance 2 }

-- Compliance Statement 
ciscoAal5MIBCompliance MODULE-COMPLIANCE
	STATUS  current
        DESCRIPTION
                "The compliance statement for entities which implement
                this Cisco AAL5 MIB."
        MODULE  -- this module
                MANDATORY-GROUPS { ciscoAal5MIBGroup }
        ::= { ciscoAal5MIBCompliances 1 }
 
-- units of conformance:
 
ciscoAal5MIBGroup OBJECT-GROUP
        OBJECTS {
		cAal5VccInPkts,
        	cAal5VccOutPkts,
        	cAal5VccInOctets,
        	cAal5VccOutOctets
        }
        STATUS  current
        DESCRIPTION
                "A collection of objects providing AAL5 related parameters."
        ::= { ciscoAal5MIBGroups 1 }

END
