-- *****************************************************************
-- CISCO-SNMPv2-CAPABILITY.my: SNMPv2-MIB AGENT-CAPABILITIES
-- 
-- February 2002, Patrick Hamel, Subra Hegde
-- August   1994, Jeffrey T. Johnson
-- 
-- Copyright (c) 1994, 2002 by cisco Systems, Inc.
-- All rights reserved.
-- 
-- *****************************************************************

CISCO-SNMPv2-CAPABILITY DEFINITIONS ::= BEGIN

IMPORTS
        MODULE-IDENTITY
                FROM SNMPv2-SMI
        AGENT-CAPABILITIES
                FROM SNMPv2-CONF
        ciscoAgentCapability
                FROM CISCO-SMI;

ciscoSnmpV2Capability   MODULE-IDENTITY
                LAST-UPDATED    "200202070000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-snmp@cisco.com"
                DESCRIPTION
                        "Agent capabilities for SNMPv2-MIB"

                REVISION        "200202070000Z"
                DESCRIPTION
                        "Added following agent capabilities:
                          - ciscoMgxSnmpV2CapabilityV20 for
                            MGX8850 series
                          - ciscoBpxSesSnmpV2CapabilityV10 for
                             BPX SES."

                REVISION        "200201310000Z"
                DESCRIPTION
                        "Added 'ciscoRpmsSnmpV2CapabilityV20' for
                         Cisco Resource Policy Management Server
                         (RPMS) 2.0."
                REVISION        "199408180000Z"
                DESCRIPTION
                        "Initial version of this MIB module."
        ::= { ciscoAgentCapability 113 }

ciscoSnmpV2CapabilityV10R02 AGENT-CAPABILITIES

PRODUCT-RELEASE "Cisco IOS 10.2"
STATUS          current
DESCRIPTION     "IOS 10.2 SNMPv2 MIB capabilities"

SUPPORTS        SNMPv2-MIB
INCLUDES        { snmpStatsGroup, snmpV1Group, snmpORGroup, snmpTrapGroup, 
                snmpSetGroup }

        ::= { ciscoSnmpV2Capability 1 }




ciscoRpmsSnmpV2CapabilityV20 AGENT-CAPABILITIES

PRODUCT-RELEASE "Cisco Resource Policy Management Server (RPMS) 2.0"
STATUS          current
DESCRIPTION     "Cisco RPMS 2.0 SNMPv2 MIB capabilities."

SUPPORTS       SNMPv2-MIB
INCLUDES       {
                  snmpGroup,
                  snmpCommunityGroup,
                  snmpSetGroup,
                  systemGroup,
                  snmpBasicNotificationsGroup
               }

------- SNMP Community Group
VARIATION      snmpInBadCommunityUses
ACCESS         not-implemented
DESCRIPTION    "This object is not implemented."

------- System Group
VARIATION      sysORLastChange
ACCESS         not-implemented
DESCRIPTION    "This object is not implemented."

VARIATION      sysORID
ACCESS         not-implemented
DESCRIPTION    "This object is not implemented."

VARIATION      sysORUpTime
ACCESS         not-implemented
DESCRIPTION    "This object is not implemented."

VARIATION      sysORDescr
ACCESS         not-implemented
DESCRIPTION    "This object is not implemented."

------- SNMP Basic Notifications Group
VARIATION      coldStart
DESCRIPTION    "A coldStart trap is generated on RPMS entity reboots."


        ::= { ciscoSnmpV2Capability 2 }

ciscoMgxSnmpV2CapabilityV20 AGENT-CAPABILITIES
    PRODUCT-RELEASE      "MGX8850 Release 2.0.00"
    STATUS                current
    DESCRIPTION          "SNMPv2-MIB capabilities in MGX Series."

    SUPPORTS SNMPv2-MIB
        INCLUDES { snmpGroup, systemGroup, snmpCommunityGroup,
                   snmpBasicNotificationsGroup }

        VARIATION   sysName
        SYNTAX      DisplayString (SIZE(1..32))
        DESCRIPTION "The maximum length supported for the
                    name is 32 characters."

        VARIATION   sysORLastChange
        ACCESS      not-implemented
        DESCRIPTION "Not supported."

        VARIATION   sysORID
        ACCESS      not-implemented
        DESCRIPTION "Not supported."

        VARIATION   sysORUpTime
        ACCESS      not-implemented
        DESCRIPTION "Not supported."

        VARIATION   sysORDescr
        ACCESS      not-implemented
        DESCRIPTION "Not supported."

    ::= { ciscoSnmpV2Capability 3 }


ciscoBpxSesSnmpV2CapabilityV10 AGENT-CAPABILITIES
    PRODUCT-RELEASE      "Cisco BPX SES Release 1.0.00"
    STATUS               current
    DESCRIPTION          "SNMPv2-MIB capabilities."

    SUPPORTS SNMPv2-MIB
        INCLUDES { snmpGroup, systemGroup, snmpCommunityGroup,
                   snmpBasicNotificationsGroup }

        VARIATION   sysName
        SYNTAX      DisplayString (SIZE(1..8))
        DESCRIPTION "The maximum length supported for the
                    name is 8 characters."
      
        VARIATION   sysORLastChange
        ACCESS      not-implemented
        DESCRIPTION "Not supported."

        VARIATION   sysORID
        ACCESS      not-implemented
        DESCRIPTION "Not supported."

        VARIATION   sysORUpTime
        ACCESS      not-implemented
        DESCRIPTION "Not supported."

        VARIATION   sysORDescr
        ACCESS      not-implemented
        DESCRIPTION "Not supported."

    ::= { ciscoSnmpV2Capability 4 }

END
