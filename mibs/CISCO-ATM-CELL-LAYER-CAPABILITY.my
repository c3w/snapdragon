-- *****************************************************************
-- ciscoAtmCellLayerCapabilities MIB
--
-- AGENT-CAPABILITIES for CISCO-ATM-CELL-LAYER-MIb
--
-- May 2002, Subra Hegde
--
-- Copyright(c) 2002 by Cisco Systems,Inc.
--
-- *****************************************************************

CISCO-ATM-CELL-LAYER-CAPABILITY DEFINITIONS ::= BEGIN
IMPORTS
        MODULE-IDENTITY
                FROM SNMPv2-SMI
        AGENT-CAPABILITIES
                FROM SNMPv2-CONF
        ciscoAgentCapability
                FROM CISCO-SMI;   

ciscoAtmCellLayerCapability MODULE-IDENTITY
        LAST-UPDATED    "200205140000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for 
            CISCO-ATM-CELL-LAYER-MIB.

            - cacLayerCapabilityAxsmV2R00 is for
              ATM Switch Service Module(AXSM).

            - cacLayerCapabilityAxsmeV2R0160 is for
              Enhanced AXSM(AXSM-E)."

        REVISION "200205140000Z"
        DESCRIPTION
            "Initial version of this MIB module."
        ::= { ciscoAgentCapability 99999 }

cacLayerCapabilityAxsmV2R00 AGENT-CAPABILITIES

PRODUCT-RELEASE "MGX8850 Release 2.0.00"
STATUS          current
DESCRIPTION     "CISCO-ATM-CELL-LAYER-MIB Capabilities for
                AXSM Service Module."

SUPPORTS CISCO-ATM-CELL-LAYER-MIB
INCLUDES { caclMIBGroup,
           caclATMSwitchStatsMIBGroup,
           caclATMEndSyatemStatsMIBGroup
}
    ::= { ciscoAtmCellLayerCapability 1 }

cacLayerCapabilityAxsmeV2R0160 AGENT-CAPABILITIES

PRODUCT-RELEASE "MGX8850 Release 2.1.60"
STATUS          current
DESCRIPTION     "CISCO-ATM-CELL-LAYER-MIB Capabilities for
                Enhanced AXSM(AXSM-E) Service Module."

SUPPORTS CISCO-ATM-CELL-LAYER-MIB
INCLUDES { caclMIBGroup,
           caclATMSwitchStatsMIBGroup,
           caclATMEndSyatemStatsMIBGroup,
           caclIntervalStatsMIBGroup    
}

VARIATION   caclInXmtCLP0Cells   
ACCESS      not-implemented      
DESCRIPTION "Not supported."

VARIATION   caclInXmtCLP1Cells   
ACCESS      not-implemented      
DESCRIPTION "Not supported."

VARIATION   caclInUpcCLP0DiscCells   
ACCESS      not-implemented      
DESCRIPTION "Not supported."

VARIATION   caclInUpcTotalDiscCells   
ACCESS      not-implemented      
DESCRIPTION "Not supported."

VARIATION   caclInUpcTotalNonCompCells   
ACCESS      not-implemented      
DESCRIPTION "Not supported."

VARIATION   caclOutXmtCLP0Cells   
ACCESS      not-implemented      
DESCRIPTION "Not supported."

VARIATION   caclOutXmtCLP1Cells   
ACCESS      not-implemented      
DESCRIPTION "Not supported."
VARIATION   caclOutRcvIdleCells
ACCESS      not-implemented      
DESCRIPTION "Not supported."

VARIATION   caclOutVpiVciErrCells
ACCESS      not-implemented      
DESCRIPTION "Not supported."

VARIATION   caclIntervalInXmtCLP0Cells   
ACCESS      not-implemented      
DESCRIPTION "Not supported."

VARIATION   caclIntervalInXmtCLP1Cells   
ACCESS      not-implemented      
DESCRIPTION "Not supported."

VARIATION   caclIntervalInUpcCLP0DiscCells   
ACCESS      not-implemented      
DESCRIPTION "Not supported."

VARIATION   caclIntervalInUpcTotalDiscCells   
ACCESS      not-implemented      
DESCRIPTION "Not supported."

VARIATION   caclIntervalInUpcTotNonCmpCells   
ACCESS      not-implemented      
DESCRIPTION "Not supported."

VARIATION   caclIntervalOutXmtCLP0Cells   
ACCESS      not-implemented      
DESCRIPTION "Not supported."

VARIATION   caclIntervalOutXmtCLP1Cells   
ACCESS      not-implemented      
DESCRIPTION "Not supported."

VARIATION   caclIntervalOutRcvIdleCells   
ACCESS      not-implemented      
DESCRIPTION "Not supported."

VARIATION   caclIntervalOutVpiVciErrCells   
ACCESS      not-implemented      
DESCRIPTION "Not supported."

    ::= { ciscoAtmCellLayerCapability 2 }
END
