--
-- Sorrento Networks Private MIB common for GigaMux Cards.
--
-- Revision 1.0   11/19/2001  gmuxEng
--
-- This MIB file is shared by various GigaMux Cards.
--
-- Copyright 2001, Sorrento Networks. All Rights Reserved.
-- Reproduction of this document is authorized on condition that this
-- copyright notice is included. This Sorrento Networks' SNMP
-- Management Information Base Specification (Specification) embodies
-- Sorrento Networks' proprietary intellectual property.  Sorrento Networks
-- retains all title and ownership in the Specification,including any revisions.
--
-- It is Sorrento Networks' intent to encourage the widespread use
-- of this Specification in connection with the management of Sorrento Networks'
-- products. Sorrento Networks grants vendors,
-- end-users, and other interested parties a non-exclusive license to
-- use this Specification in connection with the management of
-- Sorrento Networks' products.
--
-- This Specification is supplied "AS IS," and Sorrento Networks
-- makes no warranty, either express or implied, as to the use,
-- operation, condition, or performance of the Specification.
--

	GMux-Common-MIB DEFINITIONS ::= BEGIN

	IMPORTS
		  enterprises, TimeTicks, IpAddress
			  FROM RFC1155-SMI
		  DisplayString
			  FROM RFC1213-MIB
		  OBJECT-TYPE
			  FROM RFC-1212
		  TRAP-TYPE
			  FROM RFC-1215;

	osicomTechnologies	OBJECT IDENTIFIER ::= { enterprises 2522 }
	gigaNest		OBJECT IDENTIFIER ::= { osicomTechnologies 1 }
	gigaMuxCommon		OBJECT IDENTIFIER ::= { gigaNest 22 }
		unit		OBJECT IDENTIFIER ::= { gigaMuxCommon 1 }
		management	OBJECT IDENTIFIER ::= { gigaMuxCommon 2 }
		client		OBJECT IDENTIFIER ::= { gigaMuxCommon 3 }
		tftp		OBJECT IDENTIFIER ::= { gigaMuxCommon 4 }
		inventory	OBJECT IDENTIFIER ::= { gigaMuxCommon 5 }

--
--
--	Unit group
--
--

	unitName OBJECT-TYPE
		SYNTAX DisplayString (SIZE (0..8))
		ACCESS read-only
		STATUS mandatory
		DESCRIPTION
			"Short name for the card."
		::= { unit 1 }

	unitDescription OBJECT-TYPE
		SYNTAX DisplayString (SIZE (0..40))
		ACCESS read-only
		STATUS mandatory
		DESCRIPTION
			"Additional description information about
			 the card, expanding upon the short name."
		::= { unit 2 }

	unitVersion OBJECT-TYPE
		SYNTAX DisplayString (SIZE (0..16))
		ACCESS read-only
		STATUS mandatory
		DESCRIPTION
			"The software version number."
		::= { unit 3 }

	unitCommand OBJECT-TYPE
		SYNTAX INTEGER
			{
			noAction(1),
			warmResetNow(2),
			saveConfigurationNow(3)
			}
		ACCESS read-write
		STATUS mandatory
		DESCRIPTION
			"Set this object to one of the following
			 values to perform one of a variety of
			 actions:
			 nothing(1)		 - Do nothing.
			 warmResetNow(2)	 - Causes a system
						   restart.
			 saveConfigurationNow(3) - Stores active
						   configuration into
						   non-volatile flash
						   memory.
			 The default is nothing(1)."
		::= { unit 4 }

	unitConfigurationState OBJECT-TYPE
		SYNTAX INTEGER
		{
			unchanged(1),
			changed(2)
		}
		ACCESS read-only
		STATUS mandatory
		DESCRIPTION
			"Indicates the state of the active
			 configuration as compared to that saved in
			 flash memory.
			 unchanged(1) - Flash is up-to-date
			 changed(2)   - operating configuration differs
					from that saved in the flash
					memory."
		::= { unit 5 }

	
--
--	Management group
--
--	Internet management (SNMP/TCP/IP) configuration options.
--

	internetAddress OBJECT-TYPE
		SYNTAX IpAddress
		ACCESS read-only
		STATUS mandatory
		DESCRIPTION
			"internetAddress is the IP address that is
			 assigned to the card."
		::= { management 1 }

	subnetMask OBJECT-TYPE
		SYNTAX IpAddress
		ACCESS read-only
		STATUS mandatory
		DESCRIPTION
			"subnetMask is the IP subnet mask that is
			 assigned to the card."
		::= { management 2 }

	enterpriseTraps OBJECT-TYPE
		SYNTAX INTEGER
		     {
			enabled(1),
			disabled(2)
		     }
		ACCESS read-write
		STATUS mandatory
		DESCRIPTION
			"enterpriseTraps enables or disables the sending
			 of the private enterprise traps specified in
			this MIB."
		::= { management 3 }

	trapPriorityThreshold OBJECT-TYPE
		SYNTAX INTEGER {
			minor(1),
			major(2),
			critical(3),
			none(4)
		}
		ACCESS read-write
		STATUS optional
		DESCRIPTION
			"Specifies the minimum priority of an alarm
			 condition for which a trap will be generated.
			 minor(1)    - all traps will be sent
			 major(2)    - only critical and major traps
			 critical(3) - only critical traps are sent
			 none(4)     - no traps will be sent."
		::= { management 4 }

	trapDelay OBJECT-TYPE
		SYNTAX INTEGER (0..255)
		ACCESS read-write
		STATUS optional
		DESCRIPTION
			"Specifies the delay between detection of a
			 alarm condition and the sending of a trap.
			 During this delay period, if the trap
			 condition clears, then the trap will not be
			 sent. This delay is used to avoid
			 transmission of traps for momentary
			 problems."
		::= { management 5 }

	clientAutoLearn OBJECT-TYPE
		SYNTAX INTEGER	{
			enabled(1),
			disabled(2)
		     }
		ACCESS read-write
		STATUS mandatory
		DESCRIPTION
			"clientAutoLearn allows the card to
			 automatically learn client SNMP addresses. If
			 enabled, the card can automatically learn 16
			 Client IP addresses and store them in the
			 clientTable as dynamic. Addresses are
			 learned from incoming SNMP messages. If set
			 to disabled, only the addresses that are
			 manually entered in the unitClientTable are
			 available.
			 The default is enabled(1)."
		::= { management 6 }

	circuitId OBJECT-TYPE
		SYNTAX DisplayString	(SIZE (0..20))
		ACCESS read-write
		STATUS mandatory
		DESCRIPTION
			"This optional field can be used by a network
			 management system to provide an end-to-end
			 view of a single channel which is
			 cross-connected through multiple
			 multiplexers. Enter the same number into all
			 modules which carry the same channel of
			 traffic. Up to 20 alphanumeric characters can
			 be entered."
		::= { management 7 }

	sequenceNumber OBJECT-TYPE
		SYNTAX INTEGER
		ACCESS read-write
		STATUS mandatory
		DESCRIPTION
			"This optional field is used along with the
			 CircuitId field to portray and end-to-end
			 view of each channel which is cross-connected
			 through multiplexers. Enter a two digit
			 number, starting with 01 on the module
			 interfacing to the customers equipment on the
			 one end. Increment this number as the
			 connection traverses other modules
			 to the far end of the circuit."
		::= { management 8 }
	
--
--	Client Table
--
--	Contains the IP addresses of SNMP network management stations
--	that will receive SNMP traffic.  The agent will only
--	communicated with managers whose IP addresses are in the
--	table.	Entries can be either learned automatically, from
--	requests received by the card, or via configuration, by
--	terminal or SNMP. See also the clientAutoLearn object in the
--	management group.
--

	clientTable OBJECT-TYPE
		SYNTAX SEQUENCE OF ClientEntry
		ACCESS not-accessible
		STATUS mandatory
		DESCRIPTION
			"Client IP addresses of SNMP network
			 management stations that should receive SNMP
			 traffic generated by the card."
		::= { client 1 }

	clientEntry OBJECT-TYPE
		SYNTAX ClientEntry
		ACCESS not-accessible
		STATUS mandatory
		DESCRIPTION
			""
		INDEX	{ clientIndex }
		::= { clientTable 1 }

	ClientEntry ::=
		SEQUENCE {
			clientIndex
				INTEGER,
			clientAddress
				IpAddress,
			clientType
				INTEGER
		}

	clientIndex OBJECT-TYPE
		SYNTAX INTEGER
		ACCESS read-only
		STATUS mandatory
		DESCRIPTION
			"Number for this entry in the client table."
		::= { clientEntry 1 }

	clientAddress OBJECT-TYPE
		SYNTAX IpAddress
		ACCESS read-write
		STATUS mandatory
		DESCRIPTION
			"IP address for an SNMP network management
			 station. Set the address to 0.0.0.0 to remove
			 the entry."
		::= { clientEntry 2 }

	clientType OBJECT-TYPE
		SYNTAX INTEGER
		     {
			dynamic(1),
			static(2),
			unused(3)
		     }
		ACCESS read-only
		STATUS mandatory
		DESCRIPTION
			"Status of the entry:
			 dynamic(1) - Auto-learned from an SNMP request
			 static(2)  - Configured statically
			 unused(3)  - As yet unused entry."
		::= { clientEntry 3 }


--
--
-- tftp Group
--
--

	tftpSoftwareServerIPAddress OBJECT-TYPE
		SYNTAX IpAddress
		ACCESS read-write
		STATUS optional
		DESCRIPTION
			"IP address of TFTP Server for Operational Code."
	::= { tftp 1 }
														
	tftpSoftwareFileName OBJECT-TYPE
		SYNTAX DisplayString (SIZE (0..32))
		ACCESS read-write
		STATUS optional
		DESCRIPTION
			"File name of operational code."
		::= { tftp 2}

	tftpAction OBJECT-TYPE
		SYNTAX INTEGER
		{
			no-action(1),
			start-software-download(2)
		}
		ACCESS read-write
		STATUS optional
		DESCRIPTION
			"Set download state.
			no-action(1)			- no TFTP activity
			start-software-download(2) 	- start software download"
		::= { tftp 3 }

	tftpStatus OBJECT-TYPE
		SYNTAX INTEGER  
		{
			file-not-found(1),
			access-violation(2),
			disk-full(3),
			illegal-TFTP-operation(4),
			unknown-part-TID(5),
			file-already-exists(6),
			no-such-user(7),
			missing-software-server-address(8),
			missing-software-file-name(9),
			file-type-error(10),
			bad-db-version(11),
			no-memory(12),
			crc-Error(13),
			time-out(14),
			transfer-ok(15),
			tftp-in-progress(16),
			none(99)
		}
		ACCESS read-only
		STATUS optional
		DESCRIPTION
			"Status of TFTP operation."
		::= { tftp 4 }

--
--
-- Inventory information Group
--
--

	hardwareRevision OBJECT-TYPE
		SYNTAX DisplayString (SIZE (0..5))
		ACCESS read-only
		STATUS optional
		DESCRIPTION
			"Hardware Revision for this circuit pack.
			 Format is nn.nn
			 (n = 0..9)"
		::= { inventory 1 }

	gmCLEICode OBJECT-TYPE
		SYNTAX DisplayString (SIZE (0..10))
		ACCESS read-only
		STATUS optional
		DESCRIPTION
			"Common Language Equipment Identification (CLEI) code
			 for this circuit pack.
			 Format is alpha-numeric ASCII string."
		::= { inventory 2 }


	serialNumber OBJECT-TYPE
		SYNTAX DisplayString (SIZE (0..11))
		ACCESS read-only
		STATUS optional
		DESCRIPTION
			"Serial Number for this circuit pack.
			 Format is nnnnnn-mmyy
			 where 	n = 0..9
				mm = month of manufacturing
				yy = year of manufacturing"
		::= { inventory 3 }

	partNumber OBJECT-TYPE
		SYNTAX DisplayString (SIZE (0..11))
		ACCESS read-only
		STATUS optional
		DESCRIPTION
			"Part Number for this circuit pack.
			 Format is nn-nnnnn-nn
			 where 	n = 0..9"
		::= { inventory 4 }

	mfgDate OBJECT-TYPE
		SYNTAX DisplayString (SIZE (0..10))
		ACCESS read-only
		STATUS optional
		DESCRIPTION
			"Manufacturing Date for this circuit pack.
			 Format is mm/dd/yyyy"
		::= { inventory 5 }

--
--
--	Common Traps
--
--

    	tftpDownloadFailed TRAP-TYPE
		ENTERPRISE gigaMuxCommon
		VARIABLES { tftpStatus }
		DESCRIPTION
			"TFTP download operation failed.
			tftpStatus is the error code."
		::= 1

	tftpDownloadSuccessful TRAP-TYPE
		ENTERPRISE gigaMuxCommon
		DESCRIPTION
			"TFTP download operation was successful.
			 Circuit Pack will automatically reboot
			 and come up with new image."
		::= 2
END
