-- *********************************************************************
-- CISCO-ZS-MIB.my: Zone Server Mib
--
-- September 2002, H K Vivek
--
-- Copyright (c) 2002 by cisco Systems, Inc.
-- All rights reserved.
-- 
-- *********************************************************************

 
CISCO-ZS-MIB  DEFINITIONS ::= BEGIN
IMPORTS
        MODULE-IDENTITY, OBJECT-TYPE,
        NOTIFICATION-TYPE,
        Counter32, Integer32, Unsigned32  FROM    SNMPv2-SMI
        MODULE-COMPLIANCE, OBJECT-GROUP,
        NOTIFICATION-GROUP                FROM    SNMPv2-CONF
        TEXTUAL-CONVENTION, RowStatus,
        TruthValue, TestAndIncr,
        TimeStamp                         FROM    SNMPv2-TC
        ciscoMgmt                         FROM    CISCO-SMI
        SnmpAdminString                   FROM    SNMP-FRAMEWORK-MIB
        ifIndex, InterfaceIndexOrZero     FROM    IF-MIB
        vsanIndex                         FROM    CISCO-VSAN-MIB
        VsanIndex                         FROM    CISCO-ST-TC
        FcGs3RejectReasonCode             FROM    CISCO-NS-MIB;


ciscoZsMIB  MODULE-IDENTITY
        LAST-UPDATED  "200211080000Z"
        ORGANIZATION  "Cisco Systems Inc."
        CONTACT-INFO
                "     Cisco Systems
                      Customer Service
                Postal: 170 W Tasman Drive
                      San Jose, CA  95134
                      USA
                Tel: +1 800 553 -NETS
                E-mail: cs-san@cisco.com"
        DESCRIPTION
                "The MIB module for the management of zoning within 
                 the framework of Cisco's Zoning Server (ZS) Archi-
                 tecture which realizes the FC-GS3 requirements for
                 Zone Server. This MIB enables managers to configure 
                 and monitor zoning server parameters.
                 Additionally, Cisco's Zoning Server allows for
                 configuration of Lun zoning, which is an extension
                 to the Zoning Server standard specified by FC-GS3."
        REVISION  "200211080000Z"
        DESCRIPTION
                "Added zoneCopyActiveToFullOnVsan object."
        REVISION  "200210280000Z"
        DESCRIPTION
                "Added zoneSetPropagationTable."
        REVISION  "200210030000Z"
        DESCRIPTION
                "Initial version of this MIB."
        ::= { ciscoMgmt 294 }

ciscoZoningMIBObjects    OBJECT IDENTIFIER ::= { ciscoZsMIB 1 }
zoneServerMIBConformance OBJECT IDENTIFIER ::= { ciscoZsMIB 2 }
zoneConfiguration        OBJECT IDENTIFIER 
                         ::= { ciscoZoningMIBObjects 1 }
zoneStats                OBJECT IDENTIFIER 
                         ::= { ciscoZoningMIBObjects 2 }
zoneInformation          OBJECT IDENTIFIER 
                         ::= { ciscoZoningMIBObjects 3 }
zoneNotification         OBJECT IDENTIFIER 
                         ::= { ciscoZoningMIBObjects 4 }
zoneNotifications        OBJECT IDENTIFIER ::= { zoneNotification 0 }

-- Textual Conventions

ZoneMemberType ::= TEXTUAL-CONVENTION
        STATUS     current
        DESCRIPTION
           "Represents the addressing mechanism by 
            which a member is identified.

            wwn(1)    -  The Port World Wide Name (PWWN).
            fcAddr(3) -  FC-ID.
            fwwn(4)   -  Fabric Port World Wide Name. This
                         is used for Port based zoning."

        SYNTAX   INTEGER {
                    wwn(1),
                    fcAddr(3),
                    fwwn(4)
                 }

FcZoneServerRejReasonExpl ::= TEXTUAL-CONVENTION
        STATUS     current
        DESCRIPTION
           "The reject reason code explanation for a zone server
            request.
            noAdditionalExplanation(1) - there is no additional
                                         explanation.
            zonesNotSupported(2) - zones are not supported.
            zoneSetNameUnknown(3) - zone set name is not known.
            noZoneSetActive(4) - no zone set is currently active.
            zoneNameUnknown(5) - zone name is unknown.
            zoneStateUnknown(6) - state of the zone is not known.
            incorrectPayloadLen(7) - payload len is not correct.
            tooLargeZoneSet(8) - zone set is larger than
                                 permitted size.
            deactivateZoneSetFailed(9) - deactivation of zone set
                                         failed.
            reqNotSupported(10) - request is not supported.
            capabilityNotSupported(11) - capability is not 
                                         supported.
            zoneMemberIDTypeNotSupp(12)-  type of zone member is not
                                          supported.
            invalidZoneSetDefinition(13) - zone set definition is
                                           invalid."
        SYNTAX  INTEGER {
                   noAdditionalExplanation(1),
                   zonesNotSupported(2),
                   zoneSetNameUnknown(3),
                   noZoneSetActive(4),
                   zoneNameUnknown(5),
                   zoneStateUnknown(6),
                   incorrectPayloadLen(7),
                   tooLargeZoneSet(8),
                   deactivateZoneSetFailed(9),
                   reqNotSupported(10),
                   capabilityNotSupported(11),
                   zoneMemberIDTypeNotSupp(12),                        
                   invalidZoneSetDefinition(13)
                }

FcList ::= TEXTUAL-CONVENTION
       STATUS  current
       DESCRIPTION
          "Represents a list of entities.
           Each octet within the value of an object of this type,
           specifies a set of eight entities, with the first 
           octet specifying entities 1 through 8, the second
           octet specifying entities 9 through 16, etc. 

           Within each octet, the most significant bit
           represents the lowest numbered entity and the
           least significant bit represents the highest
           numbered entity.

           If the length of an object of this type is less
           than 256 bytes, then the entities which are not
           represented are not considered to be part of this
           list, i.e., effectively, the string is extended to
           be of length 256 bytes by appending bytes
           containing x'00'. Note that this means that the
           zero length string represents the 'list is empty'
           value."
       SYNTAX OCTET STRING (SIZE (0..256))

--
-- zoneDefaultZoneTable
--

zoneDefaultZoneTable OBJECT-TYPE
        SYNTAX         SEQUENCE OF ZoneDefaultZoneEntry
        MAX-ACCESS     not-accessible
        STATUS         current
        DESCRIPTION
                "A table containing information on all
                 default zones on all VSANs on the local
                 Zone Server."
        ::= { zoneConfiguration 1 }

zoneDefaultZoneEntry OBJECT-TYPE
        SYNTAX         ZoneDefaultZoneEntry
        MAX-ACCESS     not-accessible
        STATUS         current
        DESCRIPTION
                "An entry (conceptual row) in this table."
        INDEX { vsanIndex }
        ::= { zoneDefaultZoneTable 1 }

ZoneDefaultZoneEntry ::= SEQUENCE {
        zoneDefaultZoneBehaviour   INTEGER
}

zoneDefaultZoneBehaviour OBJECT-TYPE
        SYNTAX         INTEGER {
                          permit(1), -- allow communication
                          deny(2) -- deny communication
                       }
        MAX-ACCESS     read-write
        STATUS         current
        DESCRIPTION
                "This object controls the behaviour of the
                 default zone on this VSAN.

                 If this object is set to 'permit', then the
                 members of the default zone on this VSAN can 
                 communicate with each other.

                 If this object is set to 'deny', then the
                 members of the default zone on this VSAN cannot
                 communicate with each other."
        DEFVAL { deny }
        ::= { zoneDefaultZoneEntry 1 }


--
-- zoneSetPropagationTable
--

zoneSetPropagationTable OBJECT-TYPE
        SYNTAX         SEQUENCE OF ZoneSetPropagationEntry
        MAX-ACCESS     not-accessible
        STATUS         current
        DESCRIPTION
                "A table containing information related to
                 propagation of zone set information during
                 Merge/Change protocols on all VSANs on the
                 local Zone Server."
        ::= { zoneConfiguration 2 }

zoneSetPropagationEntry OBJECT-TYPE
        SYNTAX         ZoneSetPropagationEntry
        MAX-ACCESS     not-accessible
        STATUS         current
        DESCRIPTION
                "An entry (conceptual row) in this table."
        INDEX { vsanIndex }
        ::= { zoneSetPropagationTable 1 }

ZoneSetPropagationEntry ::= SEQUENCE {
        zoneSetPropagationMode      INTEGER
}

zoneSetPropagationMode OBJECT-TYPE
        SYNTAX         INTEGER {
                          fullZoneSet(1),
                          activeZoneSet(2)
                       }
        MAX-ACCESS     read-write
        STATUS         current
        DESCRIPTION
                "This object controls the way zone set
                 information is propagated during 
                 Merge/Change protocols on this VSAN.

                 If this object is set to 'fullZoneSet',
                 then the entire zone set database is
                 sent during Change/Merge protocol
                 exchanges on this VSAN.

                 If this object is set to 'activeZoneSet',
                 only the active zone set is sent during
                 Change/Merge protocol exchanges on this
                 VSAN."
        DEFVAL { activeZoneSet }
        ::= { zoneSetPropagationEntry 1 }


zoneSetNumber OBJECT-TYPE
        SYNTAX         Integer32 (0..8388608)
        MAX-ACCESS     read-only
        STATUS         current
        DESCRIPTION
                "The number of entries currently present in the
                 zoneSetTable."
        ::= { zoneConfiguration 3 }

--
-- zoneSetTable
--

zoneSetTable  OBJECT-TYPE
        SYNTAX         SEQUENCE OF ZoneSetEntry
        MAX-ACCESS     not-accessible
        STATUS         current
        DESCRIPTION
                "A table containing information on each Zone 
                 Set which is configured and available on
                 any VSAN known to the local Zone Server.
                 The zoneSetTable lists all the zone sets 
                 configured on all the VSANs configured on the 
                 local zone server. There could be multiple zone 
                 sets configured on a VSAN. But only one zone set 
                 is allowed to be active at a time in each VSAN. A 
                 Zone Set is a collection of zones."
        ::= { zoneConfiguration 4 }

zoneSetEntry  OBJECT-TYPE
        SYNTAX        ZoneSetEntry
        MAX-ACCESS    not-accessible
        STATUS        current
        DESCRIPTION
                "An entry (conceptual row) in the zoneSetTable. The 
                 zone sets are defined with respect to a VSAN. Hence,
                 this table is indexed by the vsanIndex, in addition to
                 the zoneSetIndex.
                 The sequence of operations to be performed in order
                 to create a zone set is as follows:

                 - create zone entries in the ZoneTable. 

                 - create an entry in this table and set the 
                   zoneSetZoneList bitmap object to contain the 
                   required zones.

                 - Note that it is perfectly valid to create an
                   empty zone set."
        INDEX { vsanIndex, zoneSetIndex }
        ::= { zoneSetTable 1 }

ZoneSetEntry ::= SEQUENCE {
        zoneSetIndex            Unsigned32,
        zoneSetName             SnmpAdminString,
        zoneSetZoneList         FcList,
        zoneSetLastChange       TimeStamp,
        zoneSetRowStatus        RowStatus
}

zoneSetIndex  OBJECT-TYPE
        SYNTAX        Unsigned32 (1..2048)
        MAX-ACCESS    not-accessible
        STATUS        current
        DESCRIPTION
                "The index of a zone set. This object uniquely 
                 identifies a zone set on a particular VSAN."
        ::= { zoneSetEntry 1 }

zoneSetName OBJECT-TYPE
        SYNTAX        SnmpAdminString (SIZE (1..64))
        MAX-ACCESS    read-create
        STATUS        current
        DESCRIPTION
                "The name of this zone set. The zoneSetName
                 should be unique within a VSAN.

                 This object cannot be modified while the
                 corresponding value of zoneSetRowStatus
                 is equal to 'active'.

                 This object MUST be set before or concurrently
                 with setting the corresponding instance of
                 zoneSetRowStatus to 'active'."
        ::= { zoneSetEntry 2 }

zoneSetZoneList  OBJECT-TYPE
        SYNTAX        FcList
        MAX-ACCESS    read-create
        STATUS        current
        DESCRIPTION
                "The set of zones which form this zone set on this
                 VSAN. The zones are identified by zoneIndex object 
                 in the zoneTable.

                 If a particular bit has a value of '1', then the 
                 corresponding zone is a part of this zone set.
                 All other zones have '0' in their positions or
                 not present in the string.

                 The default value is the zero length string."
        DEFVAL { ''H }
        ::= { zoneSetEntry 3 }

zoneSetLastChange OBJECT-TYPE
        SYNTAX        TimeStamp
        MAX-ACCESS    read-only
        STATUS        current
        DESCRIPTION
                "The value of sysUpTime at the time of the last
                 change to this zone set entry. If the entry has
                 not been modified since the last re-initialization
                 of the local network management system, then this
                 object will contain a zero value."
        ::= { zoneSetEntry 4 }

zoneSetRowStatus OBJECT-TYPE
        SYNTAX        RowStatus
        MAX-ACCESS    read-create
        STATUS        current
        DESCRIPTION
                "The status of this conceptual row.

                 This object can not be set to 'active' unless 
                 the corresponding value of zoneSetName is 
                 unique within the VSAN."
        ::= { zoneSetEntry 5 }

--
-- zoneSetActivateTable
--

zoneSetActivateTable  OBJECT-TYPE
        SYNTAX         SEQUENCE OF ZoneSetActivateEntry
        MAX-ACCESS     not-accessible
        STATUS         current
        DESCRIPTION
                "This table contains atmost one entry for
                 each VSAN that is configured. These entries
                 reflect the state of the activation of a 
                 zone set on the corresponding VSAN.

                 The management station needs to create an
                 entry in this table on the desired VSAN before
                 a zone set can be activated on that VSAN."
        ::= { zoneConfiguration 5 }

zoneSetActivateEntry OBJECT-TYPE
        SYNTAX         ZoneSetActivateEntry
        MAX-ACCESS     not-accessible
        STATUS         current
        DESCRIPTION
                "An entry (conceptual row) in this table."
        INDEX { vsanIndex }
        ::= { zoneSetActivateTable 1 }

ZoneSetActivateEntry ::= SEQUENCE {
        zoneSetActivate           Unsigned32,
        zoneSetActivateResult     INTEGER,
        zoneSetDeActivate         INTEGER,
        zoneSetActivateRowStatus  RowStatus
}


zoneSetActivate OBJECT-TYPE
        SYNTAX        Unsigned32 (1..2048)
        MAX-ACCESS    read-create
        STATUS        current
        DESCRIPTION
                "Setting this object to a value is a request for a 
                 zone set to be activated on the particular VSAN,
                 i.e., for the current configuration of that zone
                 set to be cloned with the clone becoming the
                 active zone set for the particular VSAN.

                 Setting this object to a value (say, N) identifies
                 the zone set to be cloned as the zone set 
                 identified by zoneSetIndex object having the same
                 value N.

                 Even though there could be multiple zone sets on a 
                 VSAN, only one can be active at a time. If a zone
                 set is already active on a VSAN and a second zone
                 set is activated on the same VSAN, then the first 
                 zone set is automatically deactivated and the second 
                 zone set is activated.

                 The value of this object when read is always 0."
        ::= { zoneSetActivateEntry 1 }

zoneSetActivateResult OBJECT-TYPE
        SYNTAX        INTEGER {
                         activateSuccess(1), -- activation success
                         activateFailure(2), -- activation failure
                         deactivateSuccess(3), -- deactivation success
                         deactivateFailure(4), -- deactivation failure
                         inProgress(5), -- in progress
                         newEntry(6) -- entry just created
                      }
        MAX-ACCESS    read-only
        STATUS        current
        DESCRIPTION
                "This object indicates the outcome of the most
                 recent activation/deactivation.

                 When the value of this object is 'inProgress',
                 the values of the corresponding instances of
                 zoneSetActivate, zoneSetDeActivate and
                 zoneSetActivateRowStatus cannot be modified.

                 The value 'newEntry' indicates that after the
                 entry has been created, activation/de-activation
                 has not yet been attempted on the entry."
        ::= { zoneSetActivateEntry 2 }

zoneSetDeActivate OBJECT-TYPE
        SYNTAX        INTEGER {
                         deactivate(1), -- deactivate zone set
                         noop(2) -- no operation
                      }
        MAX-ACCESS    read-create
        STATUS        current
        DESCRIPTION
                "Setting this object to 'deactivate' is a request
                 to deactivate the currently active zone set on
                 this VSAN.

                 No action is taken if this object is set to
                 'noop'.

                 The value of this object when read is always 
                 'noop'."
        ::= { zoneSetActivateEntry 3 }

zoneSetActivateRowStatus OBJECT-TYPE
        SYNTAX        RowStatus
        MAX-ACCESS    read-create
        STATUS        current
        DESCRIPTION
                "The status of this conceptual row."
        ::= { zoneSetActivateEntry 4 }
                         


zoneNumber OBJECT-TYPE
        SYNTAX        Integer32 (0..8388608)
        MAX-ACCESS    read-only
        STATUS        current
        DESCRIPTION
                "The number of entries currently present in the
                 zoneTable."
        ::= { zoneConfiguration 6 }

--
-- zoneTable
--

zoneTable OBJECT-TYPE
        SYNTAX        SEQUENCE OF ZoneEntry
        MAX-ACCESS    not-accessible
        STATUS        current
        DESCRIPTION
                "This table gives information on all the 
                 zones/aliases and lists all their members."
        ::= { zoneConfiguration 7 }

zoneEntry OBJECT-TYPE
        SYNTAX         ZoneEntry
        MAX-ACCESS     not-accessible
        STATUS         current
        DESCRIPTION
                "An entry (conceptual row) in the zoneTable.
                 The sequence of operations to be performed in 
                 order to create a zone is as follows:

                 - create an entry in this table.

                 - create zone members in the zoneMemberTable
                   that belong to this zone.

                 - if aliases need to be created, create an
                   alias entry in the zoneAliasTable, create
                   alias members in the zoneMemberTable and
                   associate the alias with the required zone
                   entry by setting the zoneAliasList object
                   in this table appropriately."
        INDEX { vsanIndex, zoneIndex }
        ::= { zoneTable 1 }

ZoneEntry ::= SEQUENCE {
        zoneIndex            Unsigned32,
        zoneName             SnmpAdminString,
        zoneMemberList       FcList,
        zoneAliasList        FcList,
        zoneLastChange       TimeStamp,
        zoneRowStatus        RowStatus
}

zoneIndex  OBJECT-TYPE
        SYNTAX        Unsigned32 (1..2048)
        MAX-ACCESS    not-accessible
        STATUS        current
        DESCRIPTION
                "The index of a zone on this VSAN."
        ::= { zoneEntry 1 }

zoneName OBJECT-TYPE
        SYNTAX        SnmpAdminString (SIZE (1..64))
        MAX-ACCESS    read-create
        STATUS        current
        DESCRIPTION
                "The name of this zone. The zoneName should be
                 unique within a VSAN.

                 This object can not be modified while the
                 corresponding value of zoneRowStatus is
                 'active'.

                 This object MUST be set before or concurrently
                 with setting the corresponding instance of
                 zoneRowStatus to 'active'."
        ::= { zoneEntry 2 }

zoneMemberList  OBJECT-TYPE
        SYNTAX        FcList
        MAX-ACCESS    read-only
        STATUS        current
        DESCRIPTION
                "The set of zone members that form this zone on 
                 this VSAN. 

                 The zone members are identified by zoneMemberIndex 
                 object in the zoneMemberTable.

                 If a particular bit has a value of '1', then the 
                 corresponding zone member is a part of this zone.
                 All other zone members have '0' in their 
                 positions or not present in the string.

                 This object is read-only; changes to its value
                 are made by the agent as and when associated
                 entries are created/deleted in the 
                 zoneMemberTable.

                 The default value is the zero length string."
        DEFVAL { ''H }
       ::= { zoneEntry 3 }

zoneAliasList  OBJECT-TYPE
        SYNTAX        FcList
        MAX-ACCESS    read-create
        STATUS        current
        DESCRIPTION
                "The set of aliases that form this zone on this
                 VSAN. 

                 The aliases are identified by the zoneAliasIndex
                 object in the zoneAliasTable.

                 If a particular bit has a value of '1', then 
                 the corresponding alias is a part of this zone.
                 All other aliases have '0' in their positions 
                 or not present in the string.

                 The default value is the zero length string."
        DEFVAL {''H}
       ::= { zoneEntry 4 }

zoneLastChange OBJECT-TYPE
        SYNTAX        TimeStamp
        MAX-ACCESS    read-only
        STATUS        current
        DESCRIPTION
                "The value of sysUpTime at the time of the last
                 change to this zone entry. If the entry has not 
                 been modified since the last re-initialization
                 of the local network management system, then this
                 object will contain a zero value."
        ::= { zoneEntry 5 }

zoneRowStatus OBJECT-TYPE
        SYNTAX        RowStatus
        MAX-ACCESS    read-create
        STATUS        current
        DESCRIPTION
                "The status of this conceptual row.

                 This object can not be set to 'active'
                 unless the corresponding value of zoneName
                 is unique within the VSAN."
        ::= { zoneEntry 6 }

--
-- zoneAliasTable
--


zoneAliasNumber OBJECT-TYPE
        SYNTAX        Integer32 (0..8388608)
        MAX-ACCESS    read-only
        STATUS        current
        DESCRIPTION
                "The number of entries currently present in the
                 zoneAliasTable."
        ::= { zoneConfiguration 8 }

zoneAliasTable OBJECT-TYPE 
        SYNTAX        SEQUENCE OF ZoneAliasEntry
        MAX-ACCESS    not-accessible
        STATUS        current
        DESCRIPTION
                "This table gives information on all the aliases and 
                 their members."
        ::= { zoneConfiguration 9 }

zoneAliasEntry OBJECT-TYPE
        SYNTAX        ZoneAliasEntry
        MAX-ACCESS    not-accessible
        STATUS        current
        DESCRIPTION
                "An entry (conceptual row) in this table."
        INDEX { vsanIndex, zoneAliasIndex }
        ::= { zoneAliasTable 1 }

ZoneAliasEntry ::= SEQUENCE {
        zoneAliasIndex                  Unsigned32,
        zoneAliasName                   SnmpAdminString,
        zoneAliasMemberList             FcList,
        zoneAliasRowStatus              RowStatus
}

zoneAliasIndex OBJECT-TYPE
        SYNTAX        Unsigned32 (1..2048)
        MAX-ACCESS    not-accessible
        STATUS        current
        DESCRIPTION
                "The index of an alias entry on this VSAN."
        ::= { zoneAliasEntry 1 }

zoneAliasName OBJECT-TYPE
        SYNTAX        SnmpAdminString (SIZE (1..64))
        MAX-ACCESS    read-create
        STATUS        current
        DESCRIPTION
                "The name of this alias. The name of the alias
                 should be unique within a VSAN.

                 This object can not be modified while the
                 corresponding value of zoneAliasRowStatus is
                 equal to 'active'.

                 This object MUST be set before or concurrently
                 with setting the corresponding instance of
                 zoneAliasRowStatus to 'active'."
        ::= { zoneAliasEntry 2 }

zoneAliasMemberList OBJECT-TYPE
        SYNTAX        FcList
        MAX-ACCESS    read-only
        STATUS        current
        DESCRIPTION
                "The set of zone members which form this alias
                 on this VSAN. 

                 The members of an alias are identified by the 
                 zoneMemberIndex object in the zoneMemberTable.

                 If a particular bit has a value of '1', then the 
                 corresponding zone member is a part of this alias.
                 All other zone members have '0' in their positions 
                 or not present in the string.

                 This object is read-only; changes to its value are
                 made by the agent as and when associated entries are
                 created/deleted in the zoneMemberTable.

                 The default value is the zero length string."
        DEFVAL { ''H }
        ::= { zoneAliasEntry 3 }

zoneAliasRowStatus OBJECT-TYPE
        SYNTAX        RowStatus
        MAX-ACCESS    read-create
        STATUS        current
        DESCRIPTION
                "The status of this conceptual row.

                 This object can not be set to 'active'
                 unless the corresponding value of
                 zoneAliasName is unique within the VSAN."

        ::= { zoneAliasEntry 4 }

--
-- zoneMemberTable
--

zoneMemberNumber OBJECT-TYPE
        SYNTAX        Integer32 (0..16777216)
        MAX-ACCESS    read-only
        STATUS        current
        DESCRIPTION
                "The number of entries currently present in the
                 zoneMemberTable."
        ::= { zoneConfiguration 10 }

zoneMemberTable  OBJECT-TYPE
        SYNTAX        SEQUENCE OF ZoneMemberEntry
        MAX-ACCESS    not-accessible
        STATUS        current
        DESCRIPTION
                "This table contains all members of a zone/alias 
                 and information about those members."
        ::= { zoneConfiguration 11 }

zoneMemberEntry OBJECT-TYPE
        SYNTAX        ZoneMemberEntry
        MAX-ACCESS    not-accessible
        STATUS        current
        DESCRIPTION
                "An entry (conceptual row) in the zoneMemberTable.
                 Each entry represents the relationship between
                 a member and (one of) its 'parent(s)', i.e., a 
                 zone or alias to which the member belongs, within
                 a particular VSAN."
        INDEX { vsanIndex, zoneMemberTypeIndex, 
                zoneMemberParentIndex, zoneMemberIndex }
        ::= { zoneMemberTable 1 }

ZoneMemberEntry ::= SEQUENCE {
        zoneMemberTypeIndex             INTEGER,
        zoneMemberParentIndex           Unsigned32,
        zoneMemberIndex                 Unsigned32,
        zoneMemberFormat                ZoneMemberType,
        zoneMemberID                    OCTET STRING,
        zoneMemberLunID                 OCTET STRING,
        zoneMemberRowStatus             RowStatus
}


zoneMemberTypeIndex  OBJECT-TYPE
        SYNTAX        INTEGER {
                         zone(1), -- member belongs to a zone
                         alias(2) -- member belongs to an alias
                      }
        MAX-ACCESS    not-accessible
        STATUS        current
        DESCRIPTION
                "This object determines whether this member belongs
                 to a zone or an alias."
        ::= { zoneMemberEntry 1 }

zoneMemberParentIndex  OBJECT-TYPE
        SYNTAX        Unsigned32 (1..2048)
        MAX-ACCESS    not-accessible
        STATUS        current
        DESCRIPTION
                "This object contains the value of the index of
                 the zone or alias to which this member belongs to.

                 If the value of the corresponding instance of 
                 zoneMemberTypeIndex is 'zone', then this object 
                 will contain the value of the zoneIndex object of 
                 the zone to which this member belongs to.

                 If the value of the corresponding instance of
                 zoneMemberTypeIndex is 'alias', then this object 
                 will contain the value of the zoneAliasIndex object 
                 of the alias to which this member belongs to."
        ::= { zoneMemberEntry 2 }


zoneMemberIndex  OBJECT-TYPE
        SYNTAX        Unsigned32 (1..2048)
        MAX-ACCESS    not-accessible
        STATUS        current
        DESCRIPTION
                "The index of this zone member on this VSAN on this
                 zone/alias."
        ::= { zoneMemberEntry 3 }

zoneMemberFormat OBJECT-TYPE
        SYNTAX        ZoneMemberType
        MAX-ACCESS    read-create
        STATUS        current
        DESCRIPTION
                "This object identifies the format of the 
                 zone/alias member's identifier contained in 
                 zoneMemberID.

                 This object cannot be modified while the 
                 corresponding value of zoneMemberRowStatus object
                 is 'active'."
        ::= { zoneMemberEntry 4 }

zoneMemberID OBJECT-TYPE
        SYNTAX        OCTET STRING (SIZE (3 | 8))
        MAX-ACCESS    read-create
        STATUS        current
        DESCRIPTION
                "This object represents the zone/alias member ID. The 
                 interpretation of this object depends on the 
                 zoneMemberFormat object. 

                 If the value of corresponding instance of 
                 zoneMemberFormat object is 'wwn', then this object 
                 holds an 8 octet long Port WWN. 

                 If the value of the corresponding instance of 
                 zoneMemberFormat object is 'fcAddr', then this 
                 object contains the 3 octet N_Port FC-ID.

                 If the value of the corresponding instance of
                 zoneMemberFormat object is 'fwwn', then this object
                 contains the 8 octet Fabric Port WWN.

                 This object cannot be modified while the 
                 corresponding value of zoneMemberRowStatus object
                 is 'active'."
        ::= { zoneMemberEntry 5 }

zoneMemberLunID OBJECT-TYPE
        SYNTAX        OCTET STRING (SIZE (0 | 8))
        MAX-ACCESS    read-create
        STATUS        current
        DESCRIPTION
                "This object specifies the Lun ID if Lun
                 zoning is configured.

                 If this object is the zero-length string, then
                 Lun zoning is not configured.

                 Lun zoning cannot be configured when the
                 corresponding instance of zoneMemberFormat
                 object has a value of 'fwwn'.

                 This object cannot be modified while the 
                 corresponding value of zoneMemberRowStatus object
                 is 'active'."
        DEFVAL { ''H }
        ::= { zoneMemberEntry 6 }

zoneMemberRowStatus OBJECT-TYPE
        SYNTAX        RowStatus
        MAX-ACCESS    read-create
        STATUS        current
        DESCRIPTION
                "The status of this conceptual row.

                 zoneMemberID and zoneMemberFormat objects MUST
                 be set before or concurrently with setting the
                 corresponding instance of zoneMemberRowStatus 
                 to 'active'. If Lun zoning needs to be configured, 
                 then zoneMemberLunID object also needs to be set 
                 before or concurrently with setting the 
                 corresponding instance of zoneMemberRowStatus to
                 'active'."
        ::= { zoneMemberEntry 7 }



zoneEnforcedZoneSetNumber OBJECT-TYPE
        SYNTAX         Integer32 (0..2048)
        MAX-ACCESS     read-only
        STATUS         current
        DESCRIPTION
                "The number of entries currently present in the
                 zoneEnforcedZoneSetTable."
        ::= { zoneConfiguration 12 }

zoneEnforcedZoneSetTable OBJECT-TYPE
        SYNTAX         SEQUENCE OF ZoneEnforcedZoneSetEntry
        MAX-ACCESS     not-accessible
        STATUS         current
        DESCRIPTION
                "A table containing information on all currently
                 enforced zone sets (active zone sets) on all VSANs.
                 Only one zone set can be activated per VSAN. The
                 active zone set is one which is copied from the
                 zone set database (zoneSetTable) at the time it
                 was activated. This active zone set is then
                 enforced on the fabric. This active zone set
                 cannot be modified.                 
                 Note that this table will be empty when no zone set
                 is activated."
        ::= { zoneConfiguration 13 }

zoneEnforcedZoneSetEntry OBJECT-TYPE
        SYNTAX         ZoneEnforcedZoneSetEntry
        MAX-ACCESS     not-accessible
        STATUS         current
        DESCRIPTION
                "An entry (conceptual row) in the 
                 zoneEnforcedZoneSetTable."
        INDEX { vsanIndex }
        ::= { zoneEnforcedZoneSetTable 1 }

ZoneEnforcedZoneSetEntry ::= SEQUENCE {
        zoneEnforcedZoneSetName           SnmpAdminString,
        zoneEnforcedZoneSetZoneList       FcList,
        zoneEnforcedZoneSetActivateTime   TimeStamp
}

zoneEnforcedZoneSetName OBJECT-TYPE
        SYNTAX        SnmpAdminString (SIZE (1..64))
        MAX-ACCESS    read-only
        STATUS        current
        DESCRIPTION
                "The name of this zone set on this VSAN."
        ::= { zoneEnforcedZoneSetEntry 1 }

zoneEnforcedZoneSetZoneList  OBJECT-TYPE
        SYNTAX        FcList
        MAX-ACCESS    read-only
        STATUS        current
        DESCRIPTION
                "The set of zones which form this zone set on
                 this VSAN. This object was copied from the 
                 zoneSetZoneList object in the zoneSetTable at
                 the time when the currently active zone set was
                 activated."
        ::= { zoneEnforcedZoneSetEntry 2 }

zoneEnforcedZoneSetActivateTime OBJECT-TYPE
        SYNTAX         TimeStamp
        MAX-ACCESS     read-only
        STATUS         current
        DESCRIPTION
                "The sysUpTime at which this entry was
                 most recently activated. If this entry has 
                 been activated prior to the last 
                 re-initialization of the local network 
                 management system, then this object will 
                 contain a zero value."
        ::= { zoneEnforcedZoneSetEntry 3 }


zoneEnforcedZoneNumber OBJECT-TYPE
        SYNTAX         Integer32 (0..8388608)
        MAX-ACCESS     read-only
        STATUS         current
        DESCRIPTION
                "The number of entries currently present in the
                 zoneEnforcedZoneTable."
        ::= { zoneConfiguration 14 }

zoneEnforcedZoneTable OBJECT-TYPE
        SYNTAX        SEQUENCE OF ZoneEnforcedZoneEntry
        MAX-ACCESS    not-accessible
        STATUS        current
        DESCRIPTION
                "This table contains all the zones/aliases that are 
                 present in the active zone sets on all VSANs."
        ::= { zoneConfiguration 15 }

zoneEnforcedZoneEntry OBJECT-TYPE
        SYNTAX        ZoneEnforcedZoneEntry
        MAX-ACCESS    not-accessible
        STATUS        current
        DESCRIPTION
                "An entry (conceptual row) in this table."
        INDEX { vsanIndex, zoneIndex }
        ::= { zoneEnforcedZoneTable 1 }

ZoneEnforcedZoneEntry ::= SEQUENCE {
        zoneEnforcedZoneName          SnmpAdminString,
        zoneEnforcedZoneMemberList    FcList,
        zoneEnforcedZoneAliasList     FcList,
        zoneEnforcedZoneActivateTime  TimeStamp
}

zoneEnforcedZoneName OBJECT-TYPE
        SYNTAX        SnmpAdminString (SIZE (1..64))
        MAX-ACCESS    read-only
        STATUS        current
        DESCRIPTION
                "The name of this zone."
        ::= { zoneEnforcedZoneEntry 1 }

zoneEnforcedZoneMemberList OBJECT-TYPE
        SYNTAX        FcList
        MAX-ACCESS    read-only
        STATUS        current
        DESCRIPTION
                "The set of members that form this zone on this
                 VSAN. This object was copied from the zoneMemberList
                 object in the zoneTable at the time when the 
                 currently active zone set was activated."
        ::= { zoneEnforcedZoneEntry 2 }

zoneEnforcedZoneAliasList OBJECT-TYPE
        SYNTAX        FcList
        MAX-ACCESS    read-only
        STATUS        current
        DESCRIPTION
                "The set of aliases that form this zone on this
                 VSAN. This object was copied from the zoneAliasList
                 object in the zoneTable at the time when the
                 currently active zone set was activated."
        ::= { zoneEnforcedZoneEntry 3 }

zoneEnforcedZoneActivateTime OBJECT-TYPE
        SYNTAX         TimeStamp
        MAX-ACCESS     read-only
        STATUS         current
        DESCRIPTION
                "The sysUpTime at which this entry was
                 most recently activated. If this entry has 
                 been activated prior to the last 
                 re-initialization of the local network 
                 management system, then this object will 
                 contain a zero value."
        ::= { zoneEnforcedZoneEntry 4 }

zoneEnforcedZoneAliasNumber OBJECT-TYPE
        SYNTAX         Integer32 (0..8488608)
        MAX-ACCESS     read-only
        STATUS         current
        DESCRIPTION
                "The number of entries currently present in the
                 zoneEnforcedZoneAliasTable."
        ::= { zoneConfiguration 16 }

zoneEnforcedZoneAliasTable OBJECT-TYPE
        SYNTAX        SEQUENCE OF ZoneEnforcedZoneAliasEntry
        MAX-ACCESS    not-accessible
        STATUS        current
        DESCRIPTION
                "This table contains all the aliases that
                 are a part of active zone sets on all VSANs."
        ::= { zoneConfiguration 17 }

zoneEnforcedZoneAliasEntry OBJECT-TYPE
        SYNTAX        ZoneEnforcedZoneAliasEntry
        MAX-ACCESS    not-accessible
        STATUS        current
        DESCRIPTION
                "An entry (conceptual row) in this table."
        INDEX { vsanIndex, zoneAliasIndex }
        ::= { zoneEnforcedZoneAliasTable 1 }

ZoneEnforcedZoneAliasEntry ::= SEQUENCE {
        zoneEnforcedZoneAliasName        SnmpAdminString,
        zoneEnforcedZoneAliasMemberList  FcList
}

zoneEnforcedZoneAliasName OBJECT-TYPE
        SYNTAX        SnmpAdminString (SIZE (1..64))
        MAX-ACCESS    read-only
        STATUS        current
        DESCRIPTION
                "The name of this alias."
        ::= { zoneEnforcedZoneAliasEntry 1 }

zoneEnforcedZoneAliasMemberList OBJECT-TYPE
        SYNTAX        FcList
        MAX-ACCESS    read-only
        STATUS        current
        DESCRIPTION
                "The set of members that form this alias on this
                 VSAN. This object was copied from the 
                 zoneAliasMemberList object in the zoneAliasTable at
                 the time when the currently active zone set was
                 activated."
        ::= { zoneEnforcedZoneAliasEntry 2 }

zoneEnforcedZoneMemberNumber OBJECT-TYPE
        SYNTAX         Integer32 (0..16777216)
        MAX-ACCESS     read-only
        STATUS         current
        DESCRIPTION
                "The number of entries currently present in the
                 zoneEnforcedZoneMemberTable."
        ::= { zoneConfiguration 18 }

zoneEnforcedZoneMemberTable OBJECT-TYPE
        SYNTAX         SEQUENCE OF ZoneEnforcedZoneMemberEntry
        MAX-ACCESS     not-accessible
        STATUS         current
        DESCRIPTION
                "This table contains all members that are part 
                 of a zone/alias and are part of the active zone 
                 sets on all VSANs."
        ::= { zoneConfiguration 19 }

zoneEnforcedZoneMemberEntry OBJECT-TYPE
        SYNTAX          ZoneEnforcedZoneMemberEntry
        MAX-ACCESS      not-accessible
        STATUS          current
        DESCRIPTION
                "An entry (conceptual row) in this table."
        INDEX { vsanIndex, zoneMemberTypeIndex,
                zoneMemberParentIndex, zoneMemberIndex }
        ::= { zoneEnforcedZoneMemberTable 1 }

ZoneEnforcedZoneMemberEntry ::= SEQUENCE {
        zoneEnforcedZoneMemberFormat       ZoneMemberType,
        zoneEnforcedZoneMemberID           OCTET STRING,
        zoneEnforcedZoneMemberLunID        OCTET STRING
}

zoneEnforcedZoneMemberFormat OBJECT-TYPE
        SYNTAX       ZoneMemberType
        MAX-ACCESS   read-only
        STATUS       current
        DESCRIPTION
                "This object identifies the address format of this
                 member. The address is contained in the 
                 corresponding instance of zoneEnforcedZoneMemberID
                 object."
        ::= { zoneEnforcedZoneMemberEntry 1 }

zoneEnforcedZoneMemberID OBJECT-TYPE
        SYNTAX       OCTET STRING (SIZE (3 | 8))
        MAX-ACCESS   read-only
        STATUS       current
        DESCRIPTION
                "This object represents this member's address.
                 This object was copied from the zoneMemberID
                 object in the zoneMemberTable at the time when
                 the currently active zone set was activated."
        ::= { zoneEnforcedZoneMemberEntry 2 }

zoneEnforcedZoneMemberLunID OBJECT-TYPE
        SYNTAX       OCTET STRING (SIZE (0 | 8))
        MAX-ACCESS   read-only
        STATUS       current
        DESCRIPTION
                "This object specifies the Lun ID if LUN
                 zoning is configured. This object was copied
                 from the zoneMemberLunID object in the
                 zoneMemberTable at the time when the currently
                 active zone set was activated."
        ::= { zoneEnforcedZoneMemberEntry 3 }




zoneMergeFailRecoverSpinLock OBJECT-TYPE
        SYNTAX        TestAndIncr
        MAX-ACCESS    read-write
        STATUS        current
        DESCRIPTION
                "This object is used to facilitate modification
                 of zoneMergeFailRecoverInterface, 
                 zoneMergeFailRecoverVsan and 
                 zoneMergeFailRecoverOper by multiple managers.
                 The procedure for modifying these objects is
                 as follows:

                 1. Determine new values for 
                    zoneMergeFailRecoverInterface, zoneMergeFail-
                    RecoverVsan and zoneMergeFailRecoverOper.

                 2. Retrieve the value of zoneMergeFailRecoverSpinLock.

                 3. Set the value of zoneMergeFailRecoverSpinLock to 
                    the retrieved value, and (in the same PDU) the value
                    of zoneMergeFailRecoverInterface to the new
                    value. If the set fails for 
                    zoneMergeFailRecoverSpinLock object, go back to step
                    2.

                 4. Set the value of zoneMergeFailRecoverSpinLock to
                    the retrieved value plus one, and (in the same PDU)
                    the value of zoneMergeFailRecoverVsan to the new
                    value. If the set fails for 
                    zoneMergeFailRecoverSpinLock object, go back to step
                    2.

                 5. Set the value of zoneMergeFailRecoverSpinLock to
                    the retrieved value plus two, and (in the same PDU)
                    the value of zoneMergeFailRecoverOper to the new
                    value. If the set fails for 
                    zoneMergeFailRecoverSpinLock object, go back to step
                    2.

                    Note that if it's possible to include 
                    zoneMergeFailRecoverVsan and/or 
                    zoneMergeFailRecoverOper in the (Set Req) PDU 
                    of an earlier step, then steps 4 and/or 5 can 
                    be eliminated."
        ::= { zoneConfiguration 20 }

zoneMergeFailRecoverInterface OBJECT-TYPE
        SYNTAX        InterfaceIndexOrZero
        MAX-ACCESS    read-write
        STATUS        current
        DESCRIPTION
                "The interface on which the Merge Failure Recovery
                 needs to be carried out. The value of this object
                 before the first set operation will be zero."
        ::= { zoneConfiguration 21 }

zoneMergeFailRecoverVsan OBJECT-TYPE
        SYNTAX        VsanIndex
        MAX-ACCESS    read-write
        STATUS        current
        DESCRIPTION
                "The VSAN on which the Merge Failure Recovery
                 needs to be carried out."
        DEFVAL { 1 }
        ::= { zoneConfiguration 22 }

zoneMergeFailRecoverOper OBJECT-TYPE
        SYNTAX        INTEGER {
                         import(1), -- import the active zone set
                         export(2), -- export the active zone set
                         noop(3)    -- no operation
                      }
        MAX-ACCESS    read-write
        STATUS        current
        DESCRIPTION
                "The operation to be carried out. 

                 If this object is set to 'import', then the
                 Active Zone Set from across the isolated link 
                 is imported.

                 If this object is set to 'export', then the
                 Active Zone Set on the local system is 
                 exported across the isolated link.

                 No action is taken if this object is set
                 to 'noop'.

                 The value of this object when read is always
                 'noop'."
        ::= { zoneConfiguration 23 }

zoneMergeFailRecoverResult OBJECT-TYPE
        SYNTAX        INTEGER {
                         success(1), -- merge fail recovery successful
                         failure(2), -- merge fail recovery fail
                         inProgress(3) -- recovery in progress
                      }
        MAX-ACCESS    read-only
        STATUS        current
        DESCRIPTION
                "The result of the last Merge Failure Recovery
                 operation that was attempted.

                 If the value of this object is 'success', then
                 the merge fail recovery operation was 
                 successful.
      
                 If the value of this object is 'failure', then
                 the merge fail recovery operation failed.

                 If the value of this object is 'inProgress',
                 then the merge fail recovery operation is
                 still in progress."
        ::= { zoneConfiguration 24 }


zoneCopyActiveToFullOnVsan OBJECT-TYPE
        SYNTAX        VsanIndex
        MAX-ACCESS    read-write
        STATUS        current
        DESCRIPTION
                "The VSAN on which the enforced zone set 
                 (active zone set) needs to be copied to the
                 zone set database (full zone set). Setting
                 this object to a valid VSAN will trigger a 
                 copy of the enforced zone set on that VSAN
                 to the zone set database on the same VSAN.

                 Setting this object to an invalid VSAN-id
                 will result in an error and no copy will
                 take place."
        ::= { zoneConfiguration 25 }

-- Zone Server Statistics

zoneTotalGS3Rejects OBJECT-TYPE
        SYNTAX        Counter32
        MAX-ACCESS    read-only
        STATUS        current
        DESCRIPTION
                "The total number of GS3 requests rejected 
                 by this Zone Server across all VSANs."
        ::= { zoneStats 1 }

zoneStatsTable OBJECT-TYPE
        SYNTAX SEQUENCE OF ZoneStatsEntry
        MAX-ACCESS    not-accessible
        STATUS        current
        DESCRIPTION
                "This table contains statistic counters which are
                 maintained by the Zone Server. These counters are
                 maintained per VSAN."
        ::= { zoneStats 2 }

zoneStatsEntry OBJECT-TYPE
        SYNTAX        ZoneStatsEntry
        MAX-ACCESS    not-accessible
        STATUS        current
        DESCRIPTION
                "An entry (conceptual row) in this table."
        INDEX { vsanIndex }
        ::= { zoneStatsTable 1 }

ZoneStatsEntry ::= SEQUENCE {
        zoneTxMergeReqs          Counter32,
        zoneRxMergeAccepts       Counter32,
        zoneRxMergeReqs          Counter32,
        zoneTxMergeAccepts       Counter32,
        zoneTxChangeReqs         Counter32,
        zoneRxChangeAccepts      Counter32,
        zoneRxChangeReqs         Counter32,
        zoneTxChangeAccepts      Counter32,
	zoneRxGS3Reqs            Counter32,
        zoneTxGS3Rejects         Counter32
}

zoneTxMergeReqs OBJECT-TYPE
        SYNTAX        Counter32
        MAX-ACCESS    read-only
        STATUS        current
        DESCRIPTION
                "The number of Merge Request Frames sent by this 
                 Zone Server to other Zone Servers in the fabric 
                 on this VSAN."
        ::= { zoneStatsEntry 1 }

zoneRxMergeAccepts OBJECT-TYPE
        SYNTAX        Counter32
        MAX-ACCESS    read-only
        STATUS        current
        DESCRIPTION
                "The number of Merge Accept Frames received by this 
                 Zone Server from other Zone Servers in the fabric on 
                 this VSAN."
        ::= { zoneStatsEntry 2 }

zoneRxMergeReqs OBJECT-TYPE
        SYNTAX        Counter32
        MAX-ACCESS    read-only
        STATUS        current
        DESCRIPTION
                "The number of Merge Request Frames received by this 
                 Zone Server from other Zone Servers in the fabric on 
                 this VSAN."
        ::= { zoneStatsEntry 3 }

zoneTxMergeAccepts OBJECT-TYPE
        SYNTAX        Counter32
        MAX-ACCESS    read-only
        STATUS        current
        DESCRIPTION
                "The number of Merge Accept Frames sent by this 
                 Zone Server to other Zone Servers in the fabric on 
                 this VSAN."
        ::= { zoneStatsEntry 4 }

zoneTxChangeReqs OBJECT-TYPE
        SYNTAX        Counter32
        MAX-ACCESS    read-only
        STATUS        current
        DESCRIPTION
                "The number of Change Requests sent by this Zone 
                 Server to other Zone Servers in the fabric on 
                 this VSAN. 

                 This includes Acquire Change Authorization 
                 requests, Stage Fabric Config Update requests, 
                 Update Fabric Config requests and Release Change 
                 Authorization requests."
        ::= { zoneStatsEntry 5 }

zoneRxChangeAccepts OBJECT-TYPE
        SYNTAX        Counter32
        MAX-ACCESS    read-only
        STATUS        current
        DESCRIPTION
                "The number of Change Responses received by this 
                 Zone Server from other Zone Servers in the fabric 
                 on this VSAN. 

                 This includes Acquire Change Authorization Accept, 
                 Stage Fabric Config Update Accept, Update Fabric 
                 Config Accept and Release Change Authorization 
                 Accept frames."
        ::= { zoneStatsEntry 6 }

zoneRxChangeReqs OBJECT-TYPE
        SYNTAX        Counter32
        MAX-ACCESS    read-only
        STATUS        current
        DESCRIPTION
                "The number of Change Requests received by this 
                 Zone Server from other Zone Servers in the fabric 
                 on this VSAN. 

                 This includes Acquire Change Authorization requests, 
                 Stage Fabric Config Update requests, Update Fabric 
                 Config requests and Release Change Authorization 
                 requests."
        ::= { zoneStatsEntry 7 }

zoneTxChangeAccepts OBJECT-TYPE
        SYNTAX        Counter32
        MAX-ACCESS    read-only
        STATUS        current
        DESCRIPTION
                "The number of Change Responses sent by this 
                 Zone Server to other Zone Servers in the fabric 
                 on this VSAN. 

                 This includes Acquire Change Authorization Accept, 
                 Stage Fabric Config Update Accept, Update Fabric 
                 Config Accept and Release Change Authorization 
                 Accept frames."
        ::= { zoneStatsEntry 8 }

zoneRxGS3Reqs OBJECT-TYPE
        SYNTAX        Counter32
        MAX-ACCESS    read-only
        STATUS        current
        DESCRIPTION
                "The number of GS3 requests received by this Zone
                 Server on this VSAN."
        ::= { zoneStatsEntry 9 }
                

zoneTxGS3Rejects OBJECT-TYPE
        SYNTAX        Counter32
        MAX-ACCESS    read-only
        STATUS        current
        DESCRIPTION
                "The number of GS3 requests rejected by this Zone
                 Server on this VSAN."
        ::= { zoneStatsEntry 10 }


-- Notification information

zoneServiceRejReasonCode OBJECT-TYPE
        SYNTAX        FcGs3RejectReasonCode
        MAX-ACCESS    read-only
        STATUS        current
        DESCRIPTION
                "This object contains the reason code corresponding
                 to the latest Zone Server request rejection."
        ::= { zoneInformation 1 }

zoneServiceRejReasonCodeExp OBJECT-TYPE
        SYNTAX        FcZoneServerRejReasonExpl
        MAX-ACCESS    read-only
        STATUS        current
        DESCRIPTION
                "This object contains the reason code explanation
                 if the reason code is 'Unable to perform command 
                 req'. This object also corresponds to the latest 
                 Zone Server request rejection."
        ::= { zoneInformation 2 }

zoneMergeFailureVSANNum OBJECT-TYPE
        SYNTAX        Unsigned32 (0..4096)
        MAX-ACCESS    read-only
        STATUS        current
        DESCRIPTION
                "This object contains the number of the VSAN on an
                 interface on which the last zone merge failed.

                 If the zone merge has failed on all VSANs, then this
                 object will contain the value of 0."
        ::= { zoneInformation 3 }

zoneMergeSuccessVSANNum OBJECT-TYPE
        SYNTAX        Unsigned32 (0..4096)
        MAX-ACCESS    read-only
        STATUS        current
        DESCRIPTION
                "This object contains the number of the VSAN on an
                 interface on which the last zone merge succeeded.

                 If the zone merge has succeeded on all VSANs, then 
                 this object will contain the value of 0."
        ::= { zoneInformation 4 }


-- Notification control object

zoneServiceReqRejNotifyEnable OBJECT-TYPE
        SYNTAX        TruthValue
        MAX-ACCESS    read-write
        STATUS        current
        DESCRIPTION
                "This object specifies if the Zone Server should
                 issue a 'zoneServiceReqRejNotify' notification.

                 If the value of this object is 'true', then the 
                 notification is issued. 

                 If the value of this object is 'false', then the 
                 notification is not issued."
        ::= { zoneConfiguration 26 }

zoneMergeFailureNotifyEnable OBJECT-TYPE
        SYNTAX        TruthValue
        MAX-ACCESS    read-write
        STATUS        current
        DESCRIPTION
                "This object specifies if the zone server should
                 issue a zoneMergeFailureNotify notification.

                 If the value of this object is 'true', then the
                 notification is issued. 

                 If the value of this object is 'false', then the
                 notification is not issued."
        ::= { zoneConfiguration 27 }

zoneMergeSuccessNotifyEnable OBJECT-TYPE
        SYNTAX        TruthValue
        MAX-ACCESS    read-write
        STATUS        current
        DESCRIPTION
                "This object specifies if the zone server should
                 issue a zoneMergeSuccessNotify notification.

                 If the value of this object is 'true', then the
                 notification is issued. 

                 If the value of this object is 'false', then the
                 notification is not issued."
        ::= { zoneConfiguration 28 }

zoneDefZoneBehvrChngNotifyEnable OBJECT-TYPE
        SYNTAX        TruthValue
        MAX-ACCESS    read-write
        STATUS        current
        DESCRIPTION
                "This object specifies if the zone server should
                 issue a zoneDefZoneBehaviourChngNotify 
                 notification.

                 If the value of this object is 'true', then the
                 notification is issued. 

                 If the value of this object is 'false', then the
                 notification is not issued."
        ::= { zoneConfiguration 29 }


-- Notifications


zoneServiceReqRejNotify NOTIFICATION-TYPE
        OBJECTS { zoneMemberFormat, zoneMemberID, 
                  zoneServiceRejReasonCode,
                  zoneServiceRejReasonCodeExp }
        STATUS  current
        DESCRIPTION
                "This notification is generated whenever the local 
                 Zone Server rejects a registration request.
                 The Zone Server should update the 
                 zoneServiceRejReasonCode and zoneServiceRejReason-
                 CodeExp objects with the corresponding reason 
                 code and reason code explanation before sending the 
                 notification.
                 The zoneMemberType and zoneMemberID identify the 
                 source of the request."
        ::= { zoneNotifications 1 }

zoneMergeFailureNotify NOTIFICATION-TYPE
        OBJECTS  { ifIndex, zoneMergeFailureVSANNum }
        STATUS   current
        DESCRIPTION
                "This notification is generated whenever there is 
                 a zone merge failure.

                 If all VSANs on a link have a zone-merge failure
                 at the same time, then just one notification is
                 generated in which zoneMergeFailureVSANNum object
                 has a zero value."
        ::= { zoneNotifications 2 }        

zoneMergeSuccessNotify NOTIFICATION-TYPE
        OBJECTS  { ifIndex, zoneMergeSuccessVSANNum }
        STATUS   current
        DESCRIPTION
                "This notification is generated whenever a zone
                 merge happens successfully.

                 If all VSANs on a link have a zone-merge success
                 at the same time, then just one notification is
                 generated in which zoneMergeSuccessVSANNum object
                 has a zero value."
        ::= { zoneNotifications 3 }

zoneDefZoneBehaviourChngNotify NOTIFICATION-TYPE
        OBJECTS  { zoneDefaultZoneBehaviour }
        STATUS   current
        DESCRIPTION
                "This notification is generated whenever the
                 value of zoneDefaultZoneBehaviour changes."
        ::= { zoneNotifications 4 }


-- Conformance

zoneServerMIBCompliances OBJECT IDENTIFIER 
                         ::= { zoneServerMIBConformance 1 }
zoneServerMIBGroups      OBJECT IDENTIFIER 
                         ::= { zoneServerMIBConformance 2 }

zoneServerMIBCompliance MODULE-COMPLIANCE
        STATUS current
        DESCRIPTION
                "The compliance statement for entities which
                 implement the Zone Server."
        MODULE MANDATORY-GROUPS {zoneConfigurationGroup,
                                 zoneStatisticsGroup,
                                 zoneNotificationControlGroup,
                                 zoneNotificationGroup}

        OBJECT     zoneSetRowStatus             
        SYNTAX     INTEGER {             
                     active(1),
                     createAndGo(4),
                     destroy(6)}
        MIN-ACCESS read-create
        DESCRIPTION 
                "Only three values 'createAndGo', 'destroy' and 
                'active' out of the six enumerated values need to be
                supported."

        OBJECT     zoneSetActivateRowStatus             
        SYNTAX     INTEGER {             
                     active(1),
                     createAndGo(4),
                     destroy(6)}
        MIN-ACCESS read-create
        DESCRIPTION 
                "Only three values 'createAndGo', 'destroy' and 
                'active' out of the six enumerated values need to be
                supported."

        OBJECT     zoneRowStatus             
        SYNTAX     INTEGER {             
                     active(1),
                     createAndGo(4),
                     destroy(6)}
        MIN-ACCESS read-create
        DESCRIPTION 
                "Only three values 'createAndGo', 'destroy' and 
                'active' out of the six enumerated values need to be
                supported."

        OBJECT     zoneAliasRowStatus             
        SYNTAX     INTEGER {             
                     active(1),
                     createAndGo(4),
                     destroy(6)}
        MIN-ACCESS read-create
        DESCRIPTION 
                "Only three values 'createAndGo', 'destroy' and 
                'active' out of the six enumerated values need to be
                supported."

        OBJECT     zoneMemberRowStatus             
        SYNTAX     INTEGER {             
                     active(1),
                     createAndGo(4),
                     destroy(6)}
        MIN-ACCESS read-create
        DESCRIPTION 
                "Only three values 'createAndGo', 'destroy' and 
                'active' out of the six enumerated values need to be
                supported."

        ::= { zoneServerMIBCompliances 1 }

-- Units of Conformance                                  

zoneConfigurationGroup OBJECT-GROUP
        OBJECTS {zoneSetPropagationMode,
                 zoneDefaultZoneBehaviour,
                 zoneSetNumber,
                 zoneSetName,
                 zoneSetZoneList,
                 zoneSetLastChange,
                 zoneSetRowStatus,
                 zoneSetActivate,
                 zoneSetActivateResult,
                 zoneSetDeActivate,
                 zoneSetActivateRowStatus,
                 zoneNumber,
                 zoneName,
                 zoneMemberList,
                 zoneAliasList,
                 zoneLastChange,
                 zoneRowStatus,
                 zoneAliasNumber,
                 zoneAliasName,
                 zoneAliasMemberList,
                 zoneAliasRowStatus,
                 zoneMemberNumber,
                 zoneMemberFormat,
                 zoneMemberID,
                 zoneMemberLunID,
                 zoneMemberRowStatus,
                 zoneEnforcedZoneSetNumber,
                 zoneEnforcedZoneSetName,
                 zoneEnforcedZoneSetZoneList,
                 zoneEnforcedZoneSetActivateTime,
                 zoneEnforcedZoneNumber,
                 zoneEnforcedZoneName,
                 zoneEnforcedZoneMemberList,
                 zoneEnforcedZoneAliasList,
                 zoneEnforcedZoneActivateTime,
                 zoneEnforcedZoneAliasNumber,
                 zoneEnforcedZoneAliasName,
                 zoneEnforcedZoneAliasMemberList,
                 zoneEnforcedZoneMemberNumber,
                 zoneEnforcedZoneMemberFormat,
                 zoneEnforcedZoneMemberID,
                 zoneEnforcedZoneMemberLunID,
                 zoneMergeFailRecoverSpinLock,
                 zoneMergeFailRecoverInterface,
                 zoneMergeFailRecoverVsan,
                 zoneMergeFailRecoverOper,
                 zoneMergeFailRecoverResult,
                 zoneCopyActiveToFullOnVsan}
        STATUS   current
        DESCRIPTION
                "A collection of objects for displaying and configuring
                 Zone Membership."
        ::= { zoneServerMIBGroups 1 }

zoneStatisticsGroup OBJECT-GROUP
        OBJECTS {zoneTotalGS3Rejects,
                 zoneTxMergeReqs,
                 zoneRxMergeAccepts,
                 zoneRxMergeReqs,
                 zoneTxMergeAccepts,
                 zoneTxChangeReqs,
                 zoneRxChangeAccepts,
                 zoneRxChangeReqs,
                 zoneTxChangeAccepts,
                 zoneRxGS3Reqs,
                 zoneTxGS3Rejects}
        STATUS  current
        DESCRIPTION
                "A collection of objects for displaying the Zone 
                 Server statistics information."
        ::= { zoneServerMIBGroups 2 }

zoneNotificationControlGroup OBJECT-GROUP
        OBJECTS       {zoneServiceReqRejNotifyEnable,
                       zoneMergeFailureNotifyEnable,
                       zoneMergeSuccessNotifyEnable,
                       zoneDefZoneBehvrChngNotifyEnable,
                       zoneServiceRejReasonCode,
                       zoneServiceRejReasonCodeExp,
                       zoneMergeFailureVSANNum,
                       zoneMergeSuccessVSANNum}
        STATUS  current
        DESCRIPTION
                "A collection of notification control and 
                 notification information objects for monitoring 
                 Zone Server request rejection and zone merge
                 failures."
        ::= { zoneServerMIBGroups 3 }

zoneNotificationGroup NOTIFICATION-GROUP
        NOTIFICATIONS {zoneServiceReqRejNotify,
                       zoneMergeFailureNotify,
                       zoneMergeSuccessNotify,
                       zoneDefZoneBehaviourChngNotify}
        STATUS        current
        DESCRIPTION
                "A collection of notification(s) for monitoring 
                 Zone Server request rejection, zone merge
                 failures and successes and default zoning
                 behavioural changes."
        ::= { zoneServerMIBGroups 4 }

END
