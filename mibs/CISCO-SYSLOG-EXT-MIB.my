-- *********************************************************************
-- CISCO-SYSLOG-EXT-MIB.my: Syslog Extension Mib
--
-- October 2002, Vinay Gaonkar
--
-- Copyright (c) 2002 by cisco Systems, Inc.
-- All rights reserved.
-- 
-- *********************************************************************

CISCO-SYSLOG-EXT-MIB DEFINITIONS ::= BEGIN

IMPORTS        
     MODULE-IDENTITY, OBJECT-TYPE, 
     Unsigned32                             FROM SNMPv2-SMI
     MODULE-COMPLIANCE, OBJECT-GROUP        FROM SNMPv2-CONF
     TruthValue, RowStatus, 
     TEXTUAL-CONVENTION                     FROM SNMPv2-TC
     SnmpAdminString                        FROM SNMP-FRAMEWORK-MIB   
     InetAddressType, InetAddress           FROM INET-ADDRESS-MIB 
     ciscoMgmt                              FROM CISCO-SMI
     SyslogSeverity                         FROM CISCO-SYSLOG-MIB;

ciscoSyslogExtMIB MODULE-IDENTITY
        LAST-UPDATED "200211130000Z"
        ORGANIZATION "Cisco Systems Inc. "
        CONTACT-INFO
                "     Cisco Systems
                      Customer Service
                Postal: 170 W Tasman Drive
                      San Jose, CA  95134
                      USA
                Tel: +1 800 553 -NETS
                E-mail: cs-san@cisco.com"
        DESCRIPTION
		     "MIB module for configuring and monitoring System Log 
		     related management parameters as defined by RFC 3164." 
	REVISION   "200211130000Z"
        DESCRIPTION
            "Added cseSyslogServerFacility to cseSyslogServerTable.
             Added two TCs SyslogFacility and SyslogExFacility."
	REVISION   "200210040000Z"
        DESCRIPTION
            "Initial version of this MIB module."
        ::= { ciscoMgmt 301 }

ciscoSyslogExtMIBObjects
        OBJECT IDENTIFIER ::= { ciscoSyslogExtMIB 1 }

cseSyslogConfigurationGroup OBJECT IDENTIFIER ::=
        { ciscoSyslogExtMIBObjects 1 }       
                   
-- Textual Conventions

SyslogFacility ::= TEXTUAL-CONVENTION
	STATUS	current
	DESCRIPTION
	       "The Syslog standard facilities."
        REFERENCE 
               "RFC 3014 - The BSD Syslog protocol, Section 4."
	SYNTAX	INTEGER {
                          kernel (0),        -- Kernel
                          user (8),          -- User Level     
                          mail (16),         -- Mail System
                          daemon(24),        -- System Daemon
                          auth  (32),        -- Security/Authorization
                          syslog (40),       -- Internal Syslogd 
                          lpr (48),          -- Line Printer subsystem
                          news (56),         -- Network New subsystem
                          uucp (64),         -- UUCP subsystem
                          cron (72),         -- Clock Daemon
                          authPriv (80),     -- Security/Auth(private)
                          ftp (88),          -- FTP Daemon
                          local0 (128),      -- Reserved local use
                          local1 (136),      -- Reserved local use
                          local2 (144),      -- Reserved local use
                          local3 (152),      -- Reserved local use
                          local4 (160),      -- Reserved local use
                          local5 (168),      -- Reserved local use
                          local6 (176),      -- Reserved local use
                          local7 (184)       -- Reserved local use
        }

SyslogExFacility ::= TEXTUAL-CONVENTION
	STATUS	current
	DESCRIPTION
	       "The Syslog facilities including both standard and 
               proprietary facilities."
        REFERENCE 
               "RFC 3014 - The BSD Syslog protocol, Section 4."
	SYNTAX	INTEGER {
                          kernel (0),        -- Kernel
                          user (8),          -- User Level     
                          mail (16),         -- Mail System
                          daemon(24),         -- System Daemon
                          auth  (32),        -- Security/Authorization
                          syslog (40),       -- Internal Syslogd 
                          lpr (48),          -- Line Printer subsystem
                          news (56),         -- Network New subsystem
                          uucp (64),         -- UUCP subsystem
                          cron (72),         -- Clock Daemon
                          authPriv (80),     -- Security/Auth(private)
                          ftp (88),          -- FTP Daemon
                          local0 (128),      -- Reserved local use
                          local1 (136),      -- Reserved local use
                          local2 (144),      -- Reserved local use
                          local3 (152),      -- Reserved local use
                          local4 (160),      -- Reserved local use
                          local5 (168),      -- Reserved local use
                          local6 (176),      -- Reserved local use
                          local7 (184),      -- Reserved local use
                          vsanMgr (200),      -- VSAN Manager
                          fspf (208),         -- FSPF
                          domainMgr (216),    -- Domain Manager
                          mtsDaemon (224),    -- MTS Daemon
                          linecardMgr (232),  -- Line Card Mgr
                          sysMgr (240),       -- System Manager
                          sysMgrLib (248),    -- System Mgr Library
                          zoneServer (256),   -- Zone Server
                          virtualIfMgr (264), -- VirtualInterface Mgr
                          ipConfMgr (272),    -- IP Config Manager
                          ipfc (280),         -- IP Over FC
                          xBarMgr (288),      -- Xbar Manager
                          fcDns (296),        -- Fibre Channel DNS
                          fabricConfMgr (304),-- Fabric Config Server
                          aclMgr (312),       -- AccessControlList Mgr
                          tlPortMgr (320),    -- TL Port Manager
                          portMgr (328),      -- Port Manager    
                          fportServer (336),  -- FPort Server
                          portChMgr (344),    -- Port Channel Mgr
                          mpls (352),         -- MPLS
                          tftpLib (360),      -- TFTP Library
                          wwnMgr (368),       -- WWN Mgr  
                          fcc (376),          -- FCC Process
                          qosMgr (384),       -- QOS Mgr  
                          vhba (392),         -- VHBA
                          procMgr (400),      -- Proc Mgr  
                          vedbMgr (408),      -- VEBD Mgr  
                          span (416),         -- SPAN
                          vrrpMgr (424),      -- VRRP Mgr   
                          fcfwd (432),        -- FCFWD
                          ntp (440),          -- NTP
                          pltmfmMgr (448),    -- Platform Mgr  
                          xbarClient (456),   -- XBAR Client  
                          vrrpEngine (464),   -- VRRP Engine
                          callhome (472),     -- Callhome  
                          ipsMgr (480),       -- IPS Mgr  
                          fc2 (488),          -- FC2
                          debugLib (496),     -- Debug Library
                          vpm (504),          -- VPM
                          mcast (512),        -- Multicast
                          rdl (520),          -- RDL
                          rscn (536),         -- RSCN
                          bootvar (552),      -- BootVar
                          pss (576),          -- Persistent Storage 
                                              -- System
                          snmp (584),         -- SNMP
                          security (592),     -- Security
                          vhbad (608),        -- VHBAD
                          dns (648),          -- DNS
                          rib (656),          -- RIB
                          fvpd (688)          -- Fabric Virtual Port 
                                              -- Daemon
                      }

-- Syslog Configuration Group       
-- This group provides the System log (Syslog) configuration options.

cseSyslogConsoleEnable OBJECT-TYPE
        SYNTAX        TruthValue
        MAX-ACCESS    read-write
        STATUS        current
        DESCRIPTION   
               "Indicate whether the Syslog messages should be 
               sent to the console."
        DEFVAL { false }
        ::= { cseSyslogConfigurationGroup 1 }

cseSyslogConsoleMsgSeverity OBJECT-TYPE
        SYNTAX        SyslogSeverity
        MAX-ACCESS    read-write
        STATUS        current
        DESCRIPTION   
               "Minimum severity of the message that are sent to 
                the Console."
        DEFVAL { debug }
        ::= { cseSyslogConfigurationGroup 2 }

cseSyslogLogFileName OBJECT-TYPE
        SYNTAX        SnmpAdminString (SIZE (0..255))
        MAX-ACCESS    read-write
        STATUS        current
        DESCRIPTION   
               "Name of file to which the Syslog messages are 
               logged. Set operation with a zero length will 
               fail."
        DEFVAL      { "messages" }  
        ::= { cseSyslogConfigurationGroup 3 }

cseSyslogLogFileMsgSeverity OBJECT-TYPE
        SYNTAX        SyslogSeverity
        MAX-ACCESS    read-write
        STATUS        current
        DESCRIPTION   
               "Minimum severity of the message that are sent to 
                the log file (cseSyslogLogFileName)."
        DEFVAL { debug }
        ::= { cseSyslogConfigurationGroup 4 }

cseSyslogFileLoggingDisable OBJECT-TYPE
        SYNTAX        INTEGER {
                         true (1),
                         noOp (2)
                      }
        MAX-ACCESS    read-write 
        STATUS        current
        DESCRIPTION    
               "Indicates whether the Syslog messages should be
               sent to the file indicated by cseSyslogLogFileName.
               Once this object is set to 'true', the Syslog messages 
               are no longer sent to the file. The value of 
               'cseSyslogLogFileName' is set to zero length string.
               To restart the file logging, the cseSyslogLogFileName 
               should be set to a valid file name.

               No action is taken if this object is set to 'noOp'.
               The value of the object when read is always 'noOp'."  
        ::= { cseSyslogConfigurationGroup 5 }

cseSyslogServerTableMaxEntries OBJECT-TYPE
        SYNTAX        Unsigned32 (0..65535)
        MAX-ACCESS    read-only
        STATUS        current
        DESCRIPTION   
               "The maximum number of entries that the agent supports 
               in the cseSyslogServerTable."
        ::= { cseSyslogConfigurationGroup 6 }
                      
--
-- cseSyslogServerTable
--
            
cseSyslogServerTable OBJECT-TYPE
        SYNTAX        SEQUENCE OF CseSyslogServerEntry
        MAX-ACCESS    not-accessible
        STATUS        current
        DESCRIPTION   
               "This table contains all the Syslog servers which are
               configured."
        ::= { cseSyslogConfigurationGroup 7 }

cseSyslogServerEntry OBJECT-TYPE
        SYNTAX        CseSyslogServerEntry
        MAX-ACCESS    not-accessible
        STATUS        current
        DESCRIPTION   
               "An entry containing information about a 
               Syslog server." 
        INDEX         { cseSyslogServerIndex}
        ::= { cseSyslogServerTable 1 }

CseSyslogServerEntry ::=
        SEQUENCE {   
              cseSyslogServerIndex            Unsigned32,   
              cseSyslogServerAddressType      InetAddressType,
              cseSyslogServerAddress          InetAddress, 
              cseSyslogServerMsgSeverity      SyslogSeverity,
              cseSyslogServerStatus           RowStatus,
              cseSyslogServerFacility         SyslogFacility 
        }

cseSyslogServerIndex   OBJECT-TYPE
        SYNTAX     Unsigned32 (1..65535)
        MAX-ACCESS not-accessible
        STATUS     current
        DESCRIPTION
               "An arbitrary integer value, greater than zero, and 
               less than and equal to cseSyslogServerTableMaxEntries, 
               which identifies a Syslog server row in this table." 
        ::= { cseSyslogServerEntry 1 }

cseSyslogServerAddressType   OBJECT-TYPE
        SYNTAX     InetAddressType
        MAX-ACCESS read-create
        STATUS     current
        DESCRIPTION
               "The type of the address of the Syslog server which is
               given by the corresponding value of 
               cseSyslogServerAddress."
        ::= { cseSyslogServerEntry 2 }

cseSyslogServerAddress OBJECT-TYPE
        SYNTAX     InetAddress 
        MAX-ACCESS read-create
        STATUS     current
        DESCRIPTION
                "The address of the Syslog server."
        ::= { cseSyslogServerEntry 3 }

cseSyslogServerMsgSeverity OBJECT-TYPE
        SYNTAX     SyslogSeverity 
        MAX-ACCESS read-create
        STATUS     current
        DESCRIPTION
                "Minimum severity of the message that are sent to 
                this Syslog server."
        DEFVAL    {debug}
        ::= { cseSyslogServerEntry 4 }

cseSyslogServerStatus OBJECT-TYPE
        SYNTAX        RowStatus 
        MAX-ACCESS    read-create
        STATUS        current
        DESCRIPTION   
               "The status of this row.

              A row can not become 'active' until the values for
              cseSyslogServerAddressType and cseSyslogServerAddress in
              that row have both been set.

              A row cannot be created until corresponding instances
               of following objects are instantiated.
              - cseSyslogServerAddressType
              - cseSyslogServerAddress

              The following objects may not be modified while the
              value of this object is active (1):
              - cseSyslogServerAddressType
              - cseSyslogServerAddress."
        ::= { cseSyslogServerEntry 5 }

cseSyslogServerFacility OBJECT-TYPE
        SYNTAX        SyslogFacility
        MAX-ACCESS read-create
        STATUS     current
        DESCRIPTION
               "The facility to be used when sending Syslog messages to
               this server."
        DEFVAL    {local7}
        ::= { cseSyslogServerEntry 6 }
--
-- cseSyslogMessageControlTable
-- 

cseSyslogMessageControlTable OBJECT-TYPE
        SYNTAX        SEQUENCE OF CseSyslogMessageControlEntry
        MAX-ACCESS    not-accessible
        STATUS        current
        DESCRIPTION   
               "This table contains the information about what system
               log messages should be sent to Syslog host, console, 
               log file, and/or logged into the internal buffer."
        ::= { cseSyslogConfigurationGroup 8 }

cseSyslogMessageControlEntry OBJECT-TYPE
        SYNTAX        CseSyslogMessageControlEntry
        MAX-ACCESS    not-accessible
        STATUS        current
        DESCRIPTION   
               "A system log message control table entry.
               Each entry specifies a severity for a particular 
               'facility' which generates Syslog messages.  Any 
               generated message which is at least as severe as 
               the specified severity will be logged."
        INDEX         { cseSyslogMessageFacility }
        ::= { cseSyslogMessageControlTable 1 }

CseSyslogMessageControlEntry ::=
        SEQUENCE {
                cseSyslogMessageFacility
                        SyslogExFacility,
                cseSyslogMessageSeverity
                        SyslogSeverity
        }

cseSyslogMessageFacility OBJECT-TYPE
        SYNTAX        SyslogExFacility
        MAX-ACCESS    not-accessible
        STATUS        current
        DESCRIPTION   
               "System log message facility."
        ::= { cseSyslogMessageControlEntry 1 }

cseSyslogMessageSeverity OBJECT-TYPE
        SYNTAX        SyslogSeverity
        MAX-ACCESS    read-write
        STATUS        current
        DESCRIPTION   
               "Minimum severity of the message that are generated by 
               this Syslog message facility."
        ::= { cseSyslogMessageControlEntry 2 }


cseSyslogTerminalEnable OBJECT-TYPE
        SYNTAX        TruthValue
        MAX-ACCESS    read-write
        STATUS        current
        DESCRIPTION   
               "Indicate whether the Syslog messages should be 
               sent to the terminals."
        DEFVAL { false }
        ::= { cseSyslogConfigurationGroup 9 }

cseSyslogTerminalMsgSeverity OBJECT-TYPE
        SYNTAX        SyslogSeverity
        MAX-ACCESS    read-write
        STATUS        current
        DESCRIPTION   
               "Minimum severity of the message that are sent to 
                the terminals."
        DEFVAL { debug }
        ::= { cseSyslogConfigurationGroup 10 }

cseSyslogLinecardEnable OBJECT-TYPE
        SYNTAX        TruthValue
        MAX-ACCESS    read-write
        STATUS        current
        DESCRIPTION   
               "Indicate whether the Syslog messages should be 
               generated at the line cards."
        DEFVAL { false }
        ::= { cseSyslogConfigurationGroup 11 }

cseSyslogLinecardMsgSeverity OBJECT-TYPE
        SYNTAX        SyslogSeverity
        MAX-ACCESS    read-write
        STATUS        current
        DESCRIPTION   
               "Minimum severity of the message that are sent from 
                linecards."
        DEFVAL { debug }
        ::= { cseSyslogConfigurationGroup 12 }


-- Conformance

ciscoSyslogExtMIBConformance
       OBJECT IDENTIFIER ::= { ciscoSyslogExtMIB 2 }

ciscoSyslogExtMIBCompliances
       OBJECT IDENTIFIER ::= { ciscoSyslogExtMIBConformance 1 }

ciscoSyslogExtMIBGroups
       OBJECT IDENTIFIER ::= { ciscoSyslogExtMIBConformance 2 }

ciscoSyslogExtMIBCompliance MODULE-COMPLIANCE
        STATUS   current
        DESCRIPTION
                "The compliance statement for entities which
                 implement the CISCO-SYSLOG-EXT-MIB."
        MODULE MANDATORY-GROUPS { ciscoSyslogExtGroup }

        OBJECT cseSyslogServerAddressType             
        SYNTAX      INTEGER {
                   ipv4 (1),
                   dns (16)                                     
               }                                               
        DESCRIPTION 
                "Only dns and ipv4 addresses are need to be 
                supported."
               
        OBJECT cseSyslogServerStatus             
        SYNTAX     INTEGER {             
                     active (1),
                     createAndGo (4),
                     destroy (6)}
        DESCRIPTION 
                "Only three values 'createAndGo', 'destroy' and 
                'active' need to be supported."

        OBJECT cseSyslogLinecardEnable             
        MIN-ACCESS read-only
        DESCRIPTION 
                "Write access is not required."

        OBJECT cseSyslogLinecardMsgSeverity             
        MIN-ACCESS read-only
        DESCRIPTION 
                "Write access is not required."

--        OBJECT cseSyslogMessageFacility
--        SYNTAX     SyslogFacility
--        DESCRIPTION 
--                "Only the standard facilities need to be supported."
        ::= { ciscoSyslogExtMIBCompliances 1 }

-- Units of Conformance

ciscoSyslogExtGroup  OBJECT-GROUP
        OBJECTS  { cseSyslogConsoleEnable, 
                   cseSyslogLogFileName,
                   cseSyslogFileLoggingDisable, 
                   cseSyslogConsoleMsgSeverity,
                   cseSyslogLogFileMsgSeverity, 
                   cseSyslogServerTableMaxEntries, 
                   cseSyslogServerAddress, 
                   cseSyslogServerAddressType, 
                   cseSyslogServerMsgSeverity, 
                   cseSyslogServerStatus, 
                   cseSyslogServerFacility,
                   cseSyslogMessageSeverity,
                   cseSyslogTerminalEnable, 
                   cseSyslogTerminalMsgSeverity,
                   cseSyslogLinecardEnable, 
                   cseSyslogLinecardMsgSeverity
                    }
        STATUS   current
        DESCRIPTION
                "A collection of objects for Syslog management."
        ::= { ciscoSyslogExtMIBGroups 1 }

END
