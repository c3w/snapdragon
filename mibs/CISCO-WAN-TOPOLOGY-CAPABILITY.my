-- *****************************************************************
-- ciscoWanTopologyCapabilities MIB
--
-- AGENT-CAPABILITIES mib for CISCO-WAN-TOPOLOGY-MIB in Cisco MGX8800
-- series and other Products.
--
-- Copyright(c) 2001 by Cisco Systems,Inc.
--
-- Author: Shawn Hsu 
-- *****************************************************************

CISCO-WAN-TOPOLOGY-CAPABILITY DEFINITIONS ::= BEGIN

IMPORTS
        MODULE-IDENTITY
                FROM SNMPv2-SMI
        AGENT-CAPABILITIES
                FROM SNMPv2-CONF
        ciscoAgentCapability
                FROM CISCO-SMI;   

ciscoWanTopologyCapability MODULE-IDENTITY
        LAST-UPDATED    "200110100000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
           "The Agent Capabilities for CISCO-WAN-TOPOLOGY-MIB.
            This MIB is used in the MGX8850 product family, which
            contains the MGX8850 and MGX8950 switches."

        REVISION "200110100000Z"
        DESCRIPTION
           "Initial version of this MIB module."
        ::= { ciscoAgentCapability 999 }

ciscoWanTopologyCapabilityV3R00 AGENT-CAPABILITIES
    PRODUCT-RELEASE      "MGX8850 and BPX-SES Release 3.00"
    STATUS               current
    DESCRIPTION          "Persistent Topology MIB Capabilities."

    SUPPORTS CISCO-WAN-TOPOLOGY-MIB
        INCLUDES {   
                   cwtSystemMIBGroups,
                   cwtNodalMIBGroups
                 }

    VARIATION   cwtGatewayNodeFlag 
    ACCESS      read-only
    DESCRIPTION "write and create are not supported."

    VARIATION   cwtNodeId 
    ACCESS      read-only
    DESCRIPTION "write and create are not supported."

    VARIATION   cwtNodeName 
    ACCESS      read-only
    DESCRIPTION "write and create are not supported."

    VARIATION   cwtLanIP 
    ACCESS      read-only
    DESCRIPTION "write and create are not supported."

    VARIATION   cwtAtmIP 
    ACCESS      read-only
    DESCRIPTION "write and create are not supported."

    VARIATION   cwtSysObjId
    ACCESS      read-only
    DESCRIPTION "write and create are not supported."

    VARIATION   cwtDBLastChange 
    ACCESS      not-implemented
    DESCRIPTION "Not supported."

    VARIATION   cwtNodeInfoTimeOutFlag 
    ACCESS      not-implemented
    DESCRIPTION "Not supported."

    VARIATION   cwtRowStatus 
    SYNTAX      INTEGER {
                   active(1),
                   destroy(6)
                }
    DESCRIPTION "Does not support values notInService(2), notReady(3),
                 createAndGo(4), createAndWait(5)."

    ::= { ciscoWanTopologyCapability 1 }
END
