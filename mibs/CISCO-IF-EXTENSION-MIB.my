-- *****************************************************************
-- Cisco Extension to the IF MIB
--
-- May 2002, Manik Raina
--
-- Copyright (c) 2002 by cisco Systems, Inc.
-- All rights reserved.
-- *****************************************************************
--


CISCO-IF-EXTENSION-MIB DEFINITIONS ::= BEGIN


IMPORTS
        MODULE-IDENTITY, OBJECT-TYPE, Counter32, Gauge32,Integer32
            FROM SNMPv2-SMI
        TruthValue, TimeStamp
            FROM SNMPv2-TC
        MODULE-COMPLIANCE, OBJECT-GROUP
            FROM SNMPv2-CONF
        ifIndex
            FROM IF-MIB
        SnmpAdminString
            FROM SNMP-FRAMEWORK-MIB
        ciscoMgmt
            FROM CISCO-SMI;

        ciscoIfExtensionMIB    MODULE-IDENTITY
                LAST-UPDATED        "200210120000Z"
                ORGANIZATION        "Cisco Systems, Inc."
                CONTACT-INFO
                        "
                                Cisco Systems
                                170W Tasman Drive
                                San Jose, CA 95134
                                USA

                                +1 800 553-NETS
                                cs-core-mibs@cisco.com"
                DESCRIPTION
                        "A MIB module for extending the IF-MIB 
                         (RFC2863) to add objects which provide 
                         additional information about interfaces
                         not available in other MIBS. This MIB 
                         replaces the OLD-CISCO-INTERFACES-MIB."
                REVISION "200210120000Z"
                DESCRIPTION
                      " Added the objects cieIfDhcpMode, cieIfMtu,
                        cieIfContextName to cieIfInterfaceTable.
                        Deprecated the 
                        ciscoIfExtensionMIBCompliance compliance.
                        Added ciscoIfExtensionMIBCompliance1.
                        Added ciscoIfExtensionTableIntfGroup1. "
                ::= { ciscoMgmt 276 }  

        ciscoIfExtensionMIBNotifications OBJECT IDENTIFIER
                ::= { ciscoIfExtensionMIB 0 }

        ciscoIfExtensionMIBObjects OBJECT IDENTIFIER 
                ::= { ciscoIfExtensionMIB 1 }

        ciscoIfExtensionMIBConformance OBJECT IDENTIFIER 
                ::= { ciscoIfExtensionMIB 2 }

        ciscoIfExtensionStats    OBJECT IDENTIFIER
                ::= { ciscoIfExtensionMIBObjects 1 }


                --
                --  
                -- CISCO IF Extension Packet Stats Table
                --
                --
                
        cieIfPacketStatsTable OBJECT-TYPE
                SYNTAX     SEQUENCE OF CieIfPacketStatsEntry
                MAX-ACCESS not-accessible
                STATUS     current
                DESCRIPTION
                        "This  table contains interface packet 
                         statistics which are not available in 
                         IF-MIB(RFC2863). 

                         As an example, some interfaces to which
                         objects in this table are applicable are
                         as follows :

                                 o Ethernet
                                 o FastEthernet
                                 o ATM
                                 o BRI
                                 o Sonet
                                 o GigabitEthernet

                         Some objects defined in this table may be 
                         applicable to physical interfaces only.
                         As a result, this table may be sparse for
                         some logical interfaces."
                ::= { ciscoIfExtensionStats 1 }

 
        cieIfPacketStatsEntry OBJECT-TYPE
                SYNTAX     CieIfPacketStatsEntry
                MAX-ACCESS not-accessible
                STATUS     current
                DESCRIPTION
                        "An entry into the cieIfPacketStatsTable."
                INDEX     { ifIndex }
                ::= { cieIfPacketStatsTable 1 }


        CieIfPacketStatsEntry ::=
                SEQUENCE {
                        cieIfLastInTime          Gauge32,
                        cieIfLastOutTime         Gauge32,
                        cieIfLastOutHangTime     Gauge32,
                        cieIfInRuntsErrs         Counter32,
                        cieIfInGiantsErrs        Counter32,
                        cieIfInFramingErrs       Counter32,
                        cieIfInOverrunErrs       Counter32,
                        cieIfInIgnored           Counter32,
                        cieIfInAbortErrs         Counter32,
                        cieIfInputQueueDrops     Counter32,
                        cieIfOutputQueueDrops    Counter32,
                        cieIfPacketDiscontinuityTime TimeStamp
                }


        --
        -- The following section describes the objects in the table
        -- in greater detail.
        --

        cieIfLastInTime OBJECT-TYPE
                SYNTAX     Gauge32
                UNITS      "milliseconds"
                MAX-ACCESS read-only
                STATUS     current
                DESCRIPTION
                        "This object represents the elapsed time in 
                         milliseconds since last protocol input 
                         packet was received.

                         Discontinuities in the value of this variable
                         can occur at re-initialization of the
                         management system, and at other times as 
                         indicated by the values of 
                         cieIfPacketDiscontinuityTime."
                ::= { cieIfPacketStatsEntry 1 }


        cieIfLastOutTime OBJECT-TYPE
                SYNTAX     Gauge32
                UNITS      "milliseconds"
                MAX-ACCESS read-only
                STATUS     current
                DESCRIPTION
                        "This object represents the elapsed time in 
                         milliseconds since last protocol  output 
                         packet was transmitted.

                         Discontinuities in the value of this variable
                         can occur at re-initialization of the
                         management system, and at other times as 
                         indicated by the values of 
                         cieIfPacketDiscontinuityTime."
                ::= { cieIfPacketStatsEntry 2 }

        cieIfLastOutHangTime OBJECT-TYPE
                SYNTAX     Gauge32
                UNITS      "milliseconds"
                MAX-ACCESS read-only
                STATUS     current
                DESCRIPTION
                        "This object represents the elapsed time in 
                         milliseconds since last protocol    output
                         packet could not be successfully transmitted.

                         Discontinuities in the value of this variable
                         can occur at re-initialization of the
                         management system, and at other times as 
                         indicated by the values of 
                         cieIfPacketDiscontinuityTime."
                ::= { cieIfPacketStatsEntry 3 }

        cieIfInRuntsErrs OBJECT-TYPE
                SYNTAX     Counter32
                MAX-ACCESS read-only
                STATUS     current
                DESCRIPTION
                        "The number of packets input on a particular 
                         physical interface which were dropped as
                         they were smaller than the minimum allowable 
                         physical media limit.

                         Discontinuities in the value of this variable
                         can occur at re-initialization of the
                         management system, and at other times as 
                         indicated by the values of 
                         cieIfPacketDiscontinuityTime."
                ::= { cieIfPacketStatsEntry 4 }

        cieIfInGiantsErrs OBJECT-TYPE
                SYNTAX     Counter32
                MAX-ACCESS read-only
                STATUS     current
                DESCRIPTION
                        "The number of input packets on a particular 
                         physical interface which were dropped as 
                         they were larger than the ifMtu (largest 
                         permitted  size of a packet which can be 
                         sent/received on an interface).

                         Discontinuities in the value of this variable
                         can occur at re-initialization of the
                         management system, and at other times as 
                         indicated by the values of 
                         cieIfPacketDiscontinuityTime."
                ::= { cieIfPacketStatsEntry 5 }

        cieIfInFramingErrs OBJECT-TYPE
                SYNTAX     Counter32
                MAX-ACCESS read-only
                STATUS     current
                DESCRIPTION
                        "The number of input packets on a physical 
                         interface which were misaligned or had
                         framing errors. This happens when the 
                         format of the incoming packet on a physical
                         interface is incorrect.

                         Discontinuities in the value of this variable
                         can occur at re-initialization of the
                         management system, and at other times as 
                         indicated by the values of 
                         cieIfPacketDiscontinuityTime."
                ::= { cieIfPacketStatsEntry 6 }

        cieIfInOverrunErrs OBJECT-TYPE
                SYNTAX     Counter32
                MAX-ACCESS read-only
                STATUS     current
                DESCRIPTION
                        "The number of input packets which arrived 
                         on a particular physical interface which 
                         were too quick for the hardware to receive
                         and hence the receiver ran out of buffers.

                         Discontinuities in the value of this variable
                         can occur at re-initialization of the
                         management system, and at other times as 
                         indicated by the values of 
                         cieIfPacketDiscontinuityTime."
                ::= { cieIfPacketStatsEntry 7 }

        cieIfInIgnored OBJECT-TYPE
                SYNTAX     Counter32
                MAX-ACCESS read-only
                STATUS     current
                DESCRIPTION
                        "The number of input packets which were simply
                         ignored by this physical interface due to 
                         insufficient resources to handle the incoming
                         packets.
                          
                         For example, this could indicate that the input
                         receive buffers are not available or that the
                         receiver lost a packet.

                         Discontinuities in the value of this variable
                         can occur at re-initialization of the
                         management system, and at other times as 
                         indicated by the values of 
                         cieIfPacketDiscontinuityTime."
                ::= { cieIfPacketStatsEntry 8 }

        cieIfInAbortErrs OBJECT-TYPE
                SYNTAX     Counter32
                MAX-ACCESS read-only
                STATUS     current
                DESCRIPTION
                        "Number of input packets which were dropped 
                         because the receiver aborted.

                         Examples of this could be when an abort
                         sequence aborted the input frame or when
                         there is a collision in an ethernet segment.

                         Discontinuities in the value of this variable
                         can occur at re-initialization of the
                         management system, and at other times as 
                         indicated by the values of 
                         cieIfPacketDiscontinuityTime."
                ::= { cieIfPacketStatsEntry 9 }

        cieIfInputQueueDrops OBJECT-TYPE
                SYNTAX     Counter32
                MAX-ACCESS read-only
                STATUS     current
                DESCRIPTION
                        "The number of input packets which were
                         dropped.
                         
                         Some reasons why this object could be 
                         incremented are:

                         o  Input queue is full.
                         o  Errors at the receiver hardware 
                            while receiving the packet.

                         Discontinuities in the value of this variable
                         can occur at re-initialization of the
                         management system, and at other times as 
                         indicated by the values of 
                         cieIfPacketDiscontinuityTime."
                ::= { cieIfPacketStatsEntry 10 }

        cieIfOutputQueueDrops OBJECT-TYPE
                SYNTAX     Counter32
                MAX-ACCESS read-only
                STATUS     current
                DESCRIPTION
                        "This object indicates the  number of output
                         packets dropped by the interface even though
                         no error had been detected to prevent them
                         being transmitted. 

                         The packet could be dropped for many reasons,
                         which could range from the interface being
                         down to errors in the format of the packet.

                         Discontinuities in the value of this variable
                         can occur at re-initialization of the
                         management system, and at other times as 
                         indicated by the values of 
                         cieIfPacketDiscontinuityTime."
                ::= { cieIfPacketStatsEntry 11 }


        cieIfPacketDiscontinuityTime OBJECT-TYPE
                SYNTAX      TimeStamp
                MAX-ACCESS  read-only
                STATUS      current
                DESCRIPTION
                        "The value of sysUpTime on the most recent
                         occasion at which this interface's  counters
                         suffered  a discontinuity. 

                         If no such discontinuities have occurred 
                         since the last re-initialization of the 
                         local management subsystem, then this 
                         object contains a value of zero."
                ::= { cieIfPacketStatsEntry 12 }

 
        --
        --
        --
        --        Cisco IF Extension Interface Table
        --
        --
        --



        cieIfInterfaceTable OBJECT-TYPE
                SYNTAX     SEQUENCE OF CieIfInterfaceEntry
                MAX-ACCESS not-accessible
                STATUS     current
                DESCRIPTION
                        "This  table contains objects which provide
                         more information about interface  
                         properties not available in IF-MIB
                         (RFC 2863).

                         Some objects defined in this table may be
                         applicable to physical interfaces only.
                         As a result, this table may be sparse for
                         logical interfaces."
                ::= { ciscoIfExtensionStats 2 }

 
        cieIfInterfaceEntry OBJECT-TYPE
                SYNTAX     CieIfInterfaceEntry
                MAX-ACCESS not-accessible
                STATUS     current
                DESCRIPTION
                        "An entry into the cieIfInterfaceTable."
                INDEX     { ifIndex }
                ::= { cieIfInterfaceTable 1 }


        CieIfInterfaceEntry ::=
                SEQUENCE {
                    cieIfResetCount                 Counter32,
                    cieIfKeepAliveEnabled           TruthValue,
                    cieIfStateChangeReason          SnmpAdminString,
                    cieIfCarrierTransitionCount     Counter32,
                    cieIfInterfaceDiscontinuityTime TimeStamp,
                    cieIfDhcpMode                   TruthValue,
                    cieIfMtu                        Integer32,
                    cieIfContextName                OCTET STRING
                }


        cieIfResetCount OBJECT-TYPE
                SYNTAX     Counter32
                MAX-ACCESS read-only
                STATUS     current
                DESCRIPTION
                        "The number of times the interface was 
                         internally reset and brought up.

                         Some of the actions which can cause this
                         counter to increment are :

                         o  Bringing an interface up using the 
                            interface CLI command.

                         o  Clearing the interface with the exec
                            CLI command.

                         o  Bringing the interface up via SNMP.

                         Discontinuities in the value of this variable
                         can occur at re-initialization of the
                         management system, and at other times as 
                         indicated by the values of 
                         cieIfInterfaceDiscontinuityTime."
                ::= { cieIfInterfaceEntry 1 }

        cieIfKeepAliveEnabled OBJECT-TYPE
                SYNTAX     TruthValue
                MAX-ACCESS read-write
                STATUS     current
                DESCRIPTION
                        "A keepalive is a small, layer-2 message 
                         that is transmitted by a network device 
                         to let directly-connected network devices
                         know of its presence.

                         This object returns true(1) if keepalives
                         are enabled on this interface. If keepalives
                         are not enabled, false(2) is returned.

                         Setting this object to TRUE or FALSE enables
                         or disables (respectively) keepalive on this 
                         interface."
                ::= { cieIfInterfaceEntry 2 }

        cieIfStateChangeReason OBJECT-TYPE
                SYNTAX     SnmpAdminString
                MAX-ACCESS read-only
                STATUS     current
                DESCRIPTION
                        "This object displays a human-readable 
                         textual string which describes the 
                         cause of the last state change of the 
                         interface.

                         Examples of the values this object
                         can take are:

                         o  'Lost Carrier'
                         o  'administratively down'
                         o  'up'
                         o  'down'"
                ::= { cieIfInterfaceEntry 3 }

        cieIfCarrierTransitionCount OBJECT-TYPE
                SYNTAX     Counter32
                MAX-ACCESS read-only
                STATUS     current
                DESCRIPTION
                        "Number of times interface saw the carrier
                         signal transition.

                         For example, if a T1 line is unplugged, 
                         then framer will detect the loss of signal 
                         (LOS) on the line  and will count it as a
                         transition.

                         Discontinuities in the value of this variable
                         can occur at re-initialization of the
                         management system, and at other times as 
                         indicated by the values of 
                         cieIfInterfaceDiscontinuityTime."
                ::= { cieIfInterfaceEntry 4 }

        cieIfInterfaceDiscontinuityTime OBJECT-TYPE
                SYNTAX      TimeStamp
                MAX-ACCESS  read-only
                STATUS      current
                DESCRIPTION
                        "The value of sysUpTime on the most recent
                         occasion at which this interface's  counters 
                         suffered  a discontinuity. 

                         If no such discontinuities have occurred 
                         since the last re-initialization of the 
                         local management subsystem, then this 
                         object contains a value of zero."
                ::= { cieIfInterfaceEntry 5 }

        cieIfDhcpMode OBJECT-TYPE
                SYNTAX      TruthValue
                MAX-ACCESS  read-write
                STATUS      current
                DESCRIPTION
                        "The DHCP mode configured by the 
                         administrator.
                         If 'true(1)' the DHCP is enabled. In which
                         case an IP address is requested in DHCP.
                         This is in addition to any that are 
                         configured by the administrator in
                         'ciiIPAddressTable' or 'ciiIPIfAddressTable'
                         in CISCO-IP-IF-MIB.
                         If 'false(2)' the DHCP is disabled. In which
                         case all IP addresses are configured by the
                         administrator in 'ciiIPAddressTable' or 
                         'ciiIPIfAddressTable'.
                         For interfaces, for which DHCP cannot be or
                         is not supported, then this object has the
                         value false(2)."
                DEFVAL {false}
                ::= { cieIfInterfaceEntry 6 }

        cieIfMtu OBJECT-TYPE
                SYNTAX      Integer32 (40..2147483647)
                MAX-ACCESS  read-write
                STATUS      current
                DESCRIPTION
                       "The MTU configured by the administrator. 
                        This object is exactly same as 'ifMtu' in 
                        ifTable from IF-MIB for the same ifIndex
                        value , except that it is configurable by the
                        administrator. For more description of this
                        object refer to 'ifMtu' in IF-MIB."
                DEFVAL {1500}
                ::= { cieIfInterfaceEntry 7 }

        cieIfContextName OBJECT-TYPE
                SYNTAX      OCTET STRING(SIZE(0..32)) 
                MAX-ACCESS  read-only
                STATUS      current
                DESCRIPTION
                       "The ContextName denotes the interface 
                        'context' and is used to logically separate
                        the MIB management.
                        RFC 2571 and RFC 2737 describe this approach.
                        When the agent supports a different SNMP 
                        context, as detailed in RFC 2571 and 
                        RFC 2737, for different interfaces, then the
                        value of this object specifies the context
                        name used for this interface."
                DEFVAL {""}
                ::= { cieIfInterfaceEntry 8 }


    --
    -- Conformance
    --


        ciscoIfExtensionMIBCompliances OBJECT IDENTIFIER ::= 
                { ciscoIfExtensionMIBConformance 1 }         
      
        ciscoIfExtensionMIBGroups OBJECT IDENTIFIER ::= 
                { ciscoIfExtensionMIBConformance 2 }
   

    -- Compliance

        ciscoIfExtensionMIBCompliance MODULE-COMPLIANCE
                STATUS deprecated -- superceded by 
                                  -- ciscoIfExtensionMIBCompliance1
                DESCRIPTION
                        "The compliance statement for entities which
                         implement the CISCO-IF-EXTENSION-MIB."
                MODULE    --  this module


                MANDATORY-GROUPS {
                        ciscoIfExtensionTablePacketGroup,
                        ciscoIfExtensionTableIntfGroup
                }
                ::= { ciscoIfExtensionMIBCompliances 1 }

        ciscoIfExtensionMIBCompliance1 MODULE-COMPLIANCE
                STATUS current
                DESCRIPTION
                        "The compliance statement for entities which
                         implement the CISCO-IF-EXTENSION-MIB."
                MODULE    --  this module

                GROUP ciscoIfExtensionTablePacketGroup
                DESCRIPTION
                    "Implementation of this group is optional."

                GROUP ciscoIfExtensionTableIntfGroup
                DESCRIPTION
                    "Implementation of this group is optional."

                GROUP ciscoIfExtensionTableIntfGroup1
                DESCRIPTION
                    "Implementation of this group is optional."
      
                OBJECT  cieIfDhcpMode 
                SYNTAX     INTEGER{ false(2) }
                MIN-ACCESS read-only
                DESCRIPTION 
                   "It is compliant to implement this object as 
                    read-only. Support for true(1) is only required
                    on interfaces which support DHCP."

                OBJECT  cieIfMtu
                MIN-ACCESS read-only
                DESCRIPTION 
                   "It is compliant to implement this object as 
                    read-only."

                ::= { ciscoIfExtensionMIBCompliances 2 }


        ciscoIfExtensionTablePacketGroup OBJECT-GROUP
                OBJECTS {
                        cieIfLastInTime,
                        cieIfLastOutTime,
                        cieIfLastOutHangTime,
                        cieIfInRuntsErrs,
                        cieIfInGiantsErrs,
                        cieIfInFramingErrs,
                        cieIfInOverrunErrs,
                        cieIfInIgnored,
                        cieIfInAbortErrs,
                        cieIfInputQueueDrops,
                        cieIfOutputQueueDrops,
                        cieIfPacketDiscontinuityTime
                }
                STATUS current
                DESCRIPTION
                        "A collection of objects containing packet
                         statistics for a given interface."
                ::= { ciscoIfExtensionMIBGroups 1 }

        ciscoIfExtensionTableIntfGroup OBJECT-GROUP
                OBJECTS {
                        cieIfResetCount,
                        cieIfKeepAliveEnabled,
                        cieIfStateChangeReason,
                        cieIfCarrierTransitionCount,
                        cieIfInterfaceDiscontinuityTime
                }
                STATUS current
                DESCRIPTION
                        "A collection of objects containing
                         information about properties of 
                         interfaces."
                ::= { ciscoIfExtensionMIBGroups 2 }

        ciscoIfExtensionTableIntfGroup1 OBJECT-GROUP
                OBJECTS {
                        cieIfDhcpMode,
                        cieIfMtu,
                        cieIfContextName
                }
                STATUS current
                DESCRIPTION
                        "A collection of objects containing
                         information about properties of 
                         interfaces."
                ::= { ciscoIfExtensionMIBGroups 3 }


END
