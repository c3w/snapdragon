--
-- Sorrento Networks Private MIB for the GigaMux ESC8-S Card.
--
-- This MIB file is to be used with GigaMux GM-ESC8-S version 1.0.00
-- or greater. 
--
-- Revision 1.1  06/27/2002  mjagtap
-- 1. Corrected data types of 'channelUpTime' and 'channelDownTime'
--    objects from 'TimeTicks' to 'INTEGER'.
-- 2. Changed values of 'unitCommand' to make it compatible to gmCommon.mib.
-- 3. Deprecated 'unit', 'managemet', 'client' and 'tftp' groups.
--    Next firmware revision will NOT support these deprecated groups
--    from this MIB.
--    Firmware version 1.1.00 and up support such groups 
--    from gmCommon.mib.
-- 4. Removed TFTP related traps. Now supports these traps from gmCommon.mib.
--
-- Modification History
--
-- Revision 1.0  10/10/2000  ndhameja
-- Intial MIB release for GM-ESC8-S card type.
--
-- Copyright 2000 Sorrento Networks. All Rights Reserved.
-- Reproduction of this document is authorized on condition
-- that this copyright notice is included.
-- This Sorrento Networks SNMP Management Information Base
-- Specification (Specification) embodies Sorrento Networks'
-- proprietary intellectual property.  Sorrento Networks retains
-- all title and ownership in the Specification, including any
-- revisions.
--
-- It is Sorrento Networks intent to encourage the widespread
-- use of this Specification in connection with the management of
-- Sorrento Networks products. Sorrento Networks grants vendors,
-- end-users, and other interested parties a non-exclusive license to
-- use this Specification in connection with the management of Sorrento 
-- Networks products.
--
-- This Specification is supplied "AS IS," and Sorrento Networks
-- makes no warranty, either express or implied, as to the use,
-- operation, condition, or performance of the Specification.

	GMux-ESC8-S-Card-MIB DEFINITIONS ::= BEGIN

	IMPORTS
		  enterprises, TimeTicks, IpAddress, Gauge
			  FROM RFC1155-SMI
		  DisplayString
			  FROM RFC1213-MIB
		  OBJECT-TYPE
			  FROM RFC-1212
		  TRAP-TYPE
			  FROM RFC-1215;

	osicomTechnologies	OBJECT IDENTIFIER ::= { enterprises 2522 }
	gigaNest		OBJECT IDENTIFIER ::= { osicomTechnologies 1 }
	gigaMuxESC8SM		OBJECT IDENTIFIER ::= { gigaNest 21 }
		composite	OBJECT IDENTIFIER ::= { gigaMuxESC8SM 1 }
		channel 	OBJECT IDENTIFIER ::= { gigaMuxESC8SM 2 }
		unit		OBJECT IDENTIFIER ::= { gigaMuxESC8SM 3 }
		management	OBJECT IDENTIFIER ::= { gigaMuxESC8SM 4 }
		client		OBJECT IDENTIFIER ::= { gigaMuxESC8SM 5 }
		tftp		OBJECT IDENTIFIER ::= { gigaMuxESC8SM 6 }
			
		
--
--	Composite Group
--
--	The 8 channels are Time Division multiplexed into one
--	composite channel.
--

	compositeCircuitId OBJECT-TYPE
		SYNTAX DisplayString	(SIZE (0..20))
		ACCESS read-write
		STATUS mandatory
		DESCRIPTION
			"This optional field can be used by a network
			 management system to provide an end-to-end
			 view of a single channel which is
			 cross-connected through multiple
			 multiplexers. Enter the same number into all
			 modules which carry the same channel of
			 traffic. Up to 20 alphanumeric characters can
			 be entered."
		::= { composite 1 }

	compositeSequenceNumber OBJECT-TYPE
		SYNTAX INTEGER
		ACCESS read-write
		STATUS mandatory
		DESCRIPTION
			"This optional field is used along with the
			 CircuitId field to portray and end-to-end
			 view of each channel which is cross-connected
			 through multiplexers. Enter a two digit
			 number, starting with 01 on the module
			 interfacing to the customers equipment on the
			 one end. Increment this number as the
			 connection traverses other modules
			 to the far end of the circuit."
		::= { composite 2 }

	compositeOperStatus OBJECT-TYPE
		SYNTAX INTEGER {
			normal(1),
			minor(2),
			major(3),
			critical(4),
			testing(5)
		}
		ACCESS read-only
		STATUS mandatory
		DESCRIPTION
			"Summarizes the current operational state of
			 the composite. The state of this object depends
			 on received signal presence and presence of
			 any tests."
		::= { composite 3 }

	compositeStatusDelay OBJECT-TYPE
		SYNTAX INTEGER (0..255)
		ACCESS read-write
		STATUS mandatory
		DESCRIPTION
			"Specifies the delay in seconds between detection of a
			 alarm condition amount of time before the composite
			 is considered to be in an alarm condition.
			 Default = 3 seconds"
		::= { composite 4 }

	compositeLastChange OBJECT-TYPE
		SYNTAX TimeTicks
		ACCESS read-only
		STATUS mandatory
		DESCRIPTION
			"The value of sysUpTime at the time the
			 composite entered its current operational
			 state."
		::= { composite 5 }

	compositeUpTime OBJECT-TYPE
		SYNTAX INTEGER
		ACCESS read-only
		STATUS mandatory
		DESCRIPTION
			"Time, in seconds, that the compositeOperStatus
			 has been normal and available."
		::= { composite 6 }

	compositeDownTime OBJECT-TYPE
		SYNTAX INTEGER
		ACCESS read-only
		STATUS mandatory
		DESCRIPTION
			"Time, in seconds, that the compositeOperStatus
			 has been in alarm or testing states."
		::= { composite 7 }

	compositeReceivingData OBJECT-TYPE
		SYNTAX INTEGER {
			normal(1),
			minor(2),
			major(3),
			critical(4)
		}
		ACCESS read-only
		STATUS mandatory
		DESCRIPTION
			"Indicates presence of input data on the
			 composite interface.
			 normal(1)   - input signal is normal
			 minor(2)    - input signal lost or low
			 major(3)    - input signal lost or low
			 critical(4) - input signal lost or low"
		::= { composite 8 }

	compositeDataLossCount OBJECT-TYPE
		SYNTAX INTEGER
		ACCESS read-only
		STATUS mandatory
		DESCRIPTION
			"Indicates number of times that data
			 transitioned from normal status to an alarm status."
		::= { composite 9 }

	compositeOperStatusPriority OBJECT-TYPE
		SYNTAX INTEGER {
			minor(1),
			major(2),
			critical(3)
		}
		ACCESS read-write
		STATUS mandatory
		DESCRIPTION
			"Specifies the priority of the alarm condition.
			 The priority can be used to determine if
			 alarm contacts are closed, or traps are sent
			 if the state of this condition changes.
			 Default is critical(3)."
		::= { composite 10 }

	compositeDataLossPriority OBJECT-TYPE
		SYNTAX INTEGER {
			minor(1),
			major(2),
			critical(3)
		}
		ACCESS read-write
		STATUS mandatory
		DESCRIPTION
			"Specifies the priority of the alarm condition.
			 The priority can be used to determine if
			 alarm contacts are closed, or traps are sent
			 if the state of this condition changes.
			 Default is minor(1)."
		::= { composite 11 }

--
--	Channel Table
--
--	There are 8 channels that can be either electrical (SMB coax)
--	or optical (MMF LED) based. The speed of the channels can
--	vary.
--

	channelTable OBJECT-TYPE
		SYNTAX SEQUENCE OF ChannelEntry
		ACCESS not-accessible
		STATUS mandatory
		DESCRIPTION
			"This is the Channel table."
		::= { channel 1 }

	channelEntry OBJECT-TYPE
		SYNTAX ChannelEntry
		ACCESS not-accessible
		STATUS mandatory
		DESCRIPTION
			""
		INDEX	{ channelIndex }
		::= { channelTable 1 }

	ChannelEntry ::=
		SEQUENCE {
			channelIndex
				INTEGER,
			channelCircuitId
				DisplayString (SIZE (0..20)),
			channelSequenceNumber
				INTEGER,
			channelSpeed
				INTEGER,
			channelAdminStatus
				INTEGER,
			channelOperStatus
				INTEGER,
			channelStatusDelay
				INTEGER,
			channelLastChange
				TimeTicks,
			channelUpTime
				INTEGER,
			channelDownTime
				INTEGER,
			channelReceivingData
				INTEGER,
			channelDataLossCount
				INTEGER,
			channelOperStatusPriority
				INTEGER, 
			channelDataLossPriority
				INTEGER
		}

	channelIndex OBJECT-TYPE
		SYNTAX INTEGER (1..8)
		ACCESS read-only
		STATUS mandatory
		DESCRIPTION
			"Index for the Channel table."
		::= { channelEntry 1 }

	channelCircuitId OBJECT-TYPE
		SYNTAX DisplayString	(SIZE (0..20))
		ACCESS read-write
		STATUS mandatory
		DESCRIPTION
			"This optional field can be used by a network
			 management system to provide an end-to-end
			 view of a single channel which is
			 cross-connected through multiple
			 multiplexers. Enter the same number into all
			 modules which carry the same channel of
			 traffic. Up to 20 alphanumeric characters can
			 be entered."
		::= { channelEntry 2 }

	channelSequenceNumber OBJECT-TYPE
		SYNTAX INTEGER
		ACCESS read-write
		STATUS mandatory
		DESCRIPTION
			"This optional field is used along with the
			 CircuitId field to portray and end-to-end
			 view of each channel which is cross-connected
			 through multiplexers. Enter a two digit
			 number, starting with 01 on the module
			 interfacing to the customers equipment on the
			 one end. Increment this number as the
			 connection traverses other modules
			 to the far end of the circuit."
		::= { channelEntry 3 }

	channelSpeed OBJECT-TYPE
		SYNTAX INTEGER {
			freq-disable(1),		
			freq-155Mbps(2)
		}
		ACCESS read-write
		STATUS mandatory
		DESCRIPTION
			"Speed of this channel in Mbps. It can be either
			 155Mbps or disabled."
		::= { channelEntry 4 }

	channelAdminStatus OBJECT-TYPE
		SYNTAX INTEGER {
			enabled(1),
			disabled(2)
		}
		ACCESS read-write
		STATUS mandatory
		DESCRIPTION
			"The desired state of the channel.
			 enabled(1)  = channel is activated for use
			 disabled(2) = channel is deactivated, meaning
				       only that the agent will not
				       report the status of this
				       channel or generate traps
				       regarding this channel."
		::= { channelEntry 5 }

	channelOperStatus OBJECT-TYPE
		SYNTAX INTEGER {
			normal(1),
			minor(2),
			major(3),
			critical(4),
			test(5),
			disabled(6)
		}
		ACCESS read-only
		STATUS mandatory
		DESCRIPTION
			"Summarizes the current operational state of
			 the channel.
			 normal(1)   - fully operational
			 minor(2)    - no receive data
			 major(3)    - no receive data
			 critical(4) - no receive data
			 testing(5)  - interruptive diagnostics running
			 disabled(6) - administratively disabled."
		::= { channelEntry 6 }

	channelStatusDelay OBJECT-TYPE
		SYNTAX INTEGER (0..255)
		ACCESS read-write
		STATUS mandatory
		DESCRIPTION
			"Specifies the delay in seconds between detection of a
			 alarm condition amount of time before the channel
			 is considered to be in an alarm condition.
			 Default = 3 seconds"
		::= { channelEntry 7 }

	channelLastChange OBJECT-TYPE
		SYNTAX TimeTicks
		ACCESS read-only
		STATUS mandatory
		DESCRIPTION
			"The value of sysUpTime at the time the
			 channel entered its current operational
			 state."
		::= { channelEntry 8 }

	channelUpTime OBJECT-TYPE
		SYNTAX INTEGER
		ACCESS read-only
		STATUS mandatory
		DESCRIPTION
			"Time, in seconds, that the channelOperStatus
			 has been normal and available."
		::= { channelEntry 9 }

	channelDownTime OBJECT-TYPE
		SYNTAX INTEGER
		ACCESS read-only
		STATUS mandatory
		DESCRIPTION
			"Time, in seconds, that the channelOperStatus
			 has been in the alarm or testing(5) states."
		::= { channelEntry 10 }

	channelReceivingData OBJECT-TYPE
		SYNTAX INTEGER {
			normal(1),
			minor(2),
			major(3),
			critical(4)
		}
		ACCESS read-only
		STATUS mandatory
		DESCRIPTION
			"Indicates presence of input data on this
			 channel.
			 normal(1)   - presence of data detected
			 minor(2)    - no transitions observed
			 major(3)    - no transitions observed
			 critical(4) - no transitions observed."
		::= { channelEntry 11 }

	channelDataLossCount OBJECT-TYPE
		SYNTAX INTEGER
		ACCESS read-only
		STATUS mandatory
		DESCRIPTION
			"Number of times receive data has transferred from
			 a normal condition to an alarm condition on this 
			 channel."
		::= { channelEntry 12 }

	channelOperStatusPriority OBJECT-TYPE
		SYNTAX INTEGER {
			minor(1),
			major(2),
			critical(3)
		}
		ACCESS read-write
		STATUS mandatory
		DESCRIPTION
			"Specifies the priority of the alarm condition.
			 The priority can be used to determine if
			 alarm contacts are closed, or traps are sent
			 if the state of this condition changes.
			 Default is critical(3)."
		::= { channelEntry 13 }

	channelDataLossPriority OBJECT-TYPE
		SYNTAX INTEGER {
			minor(1),
			major(2),
			critical(3)
		}
		ACCESS read-write
		STATUS mandatory
		DESCRIPTION
			"Specifies the priority of the alarm condition.
			 The priority can be used to determine if
			 alarm contacts are closed, or traps are sent
			 if the state of this condition changes.
			 Default is minor(1)."
		::= { channelEntry 14 }

--
--
--	Unit group
--
--

	unitName OBJECT-TYPE
		SYNTAX DisplayString (SIZE (0..8))
		ACCESS read-only
		STATUS deprecated
		DESCRIPTION
			"Short name for the card."
		::= { unit 1 }

	unitDescription OBJECT-TYPE
		SYNTAX DisplayString (SIZE (0..40))
		ACCESS read-only
		STATUS deprecated
		DESCRIPTION
			"Additional description information about
			 the card, expanding upon the short name."
		::= { unit 2 }

	unitVersion OBJECT-TYPE
		SYNTAX DisplayString (SIZE (0..16))
		ACCESS read-only
		STATUS deprecated
		DESCRIPTION
			"The software version number."
		::= { unit 3 }

	unitCommand OBJECT-TYPE
		SYNTAX INTEGER
			{
			nothing(1),
			warmResetNow(2),
			resetAllCounters(3),
			saveConfigurationNow(4)
			}
		ACCESS read-write
		STATUS deprecated
		DESCRIPTION
			"Set this object to one of the following
			 values to perform one of a variety of
			 actions:
			 nothing(1)		 - Do nothing.
			 warmResetNow(2)	 - Causes a system
						   restart.
			 saveConfigurationNow(3) - Stores active
						   configuration into
						   non-volatile flash
						   memory.
			 resetAllCounters(4)	 - Reset all
						   statistics counters.
			 The default is nothing(1)."
		::= { unit 4 }

	unitConfigurationState OBJECT-TYPE
		SYNTAX INTEGER
		{
			unchanged(1),
			changed(2)
		}
		ACCESS read-only
		STATUS deprecated
		DESCRIPTION
			"Indicates the state of the active
			 configuration as compared to that saved in
			 flash memory.
			 unchanged(1) - Flash is up-to-date
			 changed(2)   - operating configuration differs
					from that saved in the flash
					memory."
		::= { unit 5 }

--
--	Management group
--
--	Internet management (SNMP/TCP/IP) configuration options.
--

	internetAddress OBJECT-TYPE
		SYNTAX IpAddress
		ACCESS read-only
		STATUS deprecated
		DESCRIPTION
			"internetAddress is the IP address that is
			 assigned to the card."
		::= { management 1 }

	subnetMask OBJECT-TYPE
		SYNTAX IpAddress
		ACCESS read-only
		STATUS deprecated
		DESCRIPTION
			"subnetMask is the IP subnet mask that is
			 assigned to the card."
		::= { management 2 }

	trapPriorityThreshold OBJECT-TYPE
		SYNTAX INTEGER {
			minor(1),
			major(2),
			critical(3),
			none(4)
		}
		ACCESS read-write
		STATUS deprecated
		DESCRIPTION
			"Specifies the minimum priority of an alarm
			 condition for which a trap will be generated.
			 minor(1)    - all traps will be sent
			 major(2)    - only critical and major traps
			 critical(3) - only critical traps are sent
			 none(4)     - no traps will be sent."
		::= { management 3 }

	trapDelay OBJECT-TYPE
		SYNTAX INTEGER (0..255)
		ACCESS read-write
		STATUS deprecated
		DESCRIPTION
			"Specifies the delay between detection of a
			 alarm condition and the sending of a trap.
			 During this delay period, if the trap
			 condition clears, then the trap will not be
			 sent. This delay is used to avoid
			 transmission of traps for momentary
			 problems."
		::= { management 4 }

	clientAutoLearn OBJECT-TYPE
		SYNTAX INTEGER	{
			enabled(1),
			disabled(2)
		     }
		ACCESS read-write
		STATUS deprecated
		DESCRIPTION
			"clientAutoLearn allows the card to
			 automatically learn client SNMP addresses. If
			 enabled, the card can automatically learn 16
			 Client IP addresses and store them in the
			 unitClientTable as dynamic. Addresses are
			 learned from incoming SNMP messages. If set
			 to disabled, only the addresses that are
			 manually entered in the unitClientTable are
			 available.
			 The default is enabled(1)."
		::= { management 5 }

--
--	Client Table
--
--	Contains the IP addresses of SNMP network management stations
--	that will receive SNMP traffic.  The agent will only
--	communicated with managers whose IP addresses are in the
--	table.	Entries can be either learned automatically, from
--	requests received by the card, or via configuration, by
--	terminal or SNMP. See also the clientAutoLearn object in the
--	management group.
--

	clientTable OBJECT-TYPE
		SYNTAX SEQUENCE OF ClientEntry
		ACCESS not-accessible
		STATUS deprecated
		DESCRIPTION
			"Client IP addresses of SNMP network
			 management stations that should receive SNMP
			 traffic generated by the card."
		::= { client 1 }

	clientEntry OBJECT-TYPE
		SYNTAX ClientEntry
		ACCESS not-accessible
		STATUS deprecated
		DESCRIPTION
			""
		INDEX	{ clientIndex }
		::= { clientTable 1 }

	ClientEntry ::=
		SEQUENCE {
			clientIndex
				INTEGER,
			clientAddress
				IpAddress,
			clientType
				INTEGER
		}

	clientIndex OBJECT-TYPE
		SYNTAX INTEGER
		ACCESS read-only
		STATUS deprecated
		DESCRIPTION
			"Number for this entry in the client table."
		::= { clientEntry 1 }

	clientAddress OBJECT-TYPE
		SYNTAX IpAddress
		ACCESS read-write
		STATUS deprecated
		DESCRIPTION
			"IP address for an SNMP network management
			 station. Set the address to 0.0.0.0 to remove
			 the entry."
		::= { clientEntry 2 }

	clientType OBJECT-TYPE
		SYNTAX INTEGER
		     {
			dynamic (1),
			static (2),
			unused (3)
		     }
		ACCESS read-only
		STATUS deprecated
		DESCRIPTION
			"Status of the entry:
			 dynamic(1) - Auto-learned from an SNMP request
			 static(2)  - Configured statically
			 unused(3)  - As yet unusd entry."
		::= { clientEntry 3 }

--
--
-- tftp Group
--
--

	tftpSoftwareServerIPAddress OBJECT-TYPE
	SYNTAX IpAddress
	ACCESS read-write
	STATUS deprecated
	DESCRIPTION
		"IP address of TFTP Server for Operational Code."
	::= { tftp 1 }
														
	tftpSoftwareFileName OBJECT-TYPE
		SYNTAX DisplayString (SIZE (0..32))
		ACCESS read-write
		STATUS deprecated
		DESCRIPTION
			"File name of operational code."
		::= { tftp 2}

	tftpAction OBJECT-TYPE
		SYNTAX INTEGER  
		{
			no-action(1),
			start-software-download(2)
		}
		ACCESS read-write
		STATUS deprecated
		DESCRIPTION
		    "Get or Set download state.
				no-action(1)                - no TFTP activity
				start-software-download(2)  - srtart software download"
		::= { tftp 3 }

	tftpStatus OBJECT-TYPE
		SYNTAX INTEGER  
		{
			file-not-found(1),
			access-violation(2),
			disk-full(3),
			illegal-TFTP-operation(4),
			unknown-part-TID(5),
			file-already-exists(6),
			no-such-user(7),
			missing-software-server-address(8),
			missing-software-file-name(9),
			file-type-error(10),
			bad-db-version(11),
			no-memory(12),
			crc-Error(13),
			time-out(14),
			transfer-ok(15),
			tftp-in-progress(16),
			none(99)
		}
		ACCESS read-only
		STATUS deprecated
		DESCRIPTION
			"Status of TFTP operation."
		::= { tftp 4 }


--
--
--	MIB specific traps
--
--

	compositeDownTrap TRAP-TYPE
		ENTERPRISE gigaMuxESC8SM
		DESCRIPTION
			"The compositeOperStatus has transitioned
			 to an alarm state."
		::= 1

	compositeUpTrap TRAP-TYPE
		ENTERPRISE gigaMuxESC8SM
		DESCRIPTION
			"The compositeOperStatus has transitioned into
			 the the normal(1) state."
		::= 2

	compositeDataLossTrap TRAP-TYPE
		ENTERPRISE gigaMuxESC8SM
		DESCRIPTION
			"The compositeDataLossStatus has transitioned into
			 an alarm state."
		::= 3

	compositeDataRestoredTrap TRAP-TYPE
		ENTERPRISE gigaMuxESC8SM
		DESCRIPTION
			"The compositeDataLossStatus has transitioned into
			 a normal state."
		::= 4

	channelDownTrap TRAP-TYPE
		ENTERPRISE gigaMuxESC8SM
		VARIABLES { channelIndex }
		DESCRIPTION
			"The channelOperStatus has transitioned into
			 an alarm state. This could be caused by
			 disappearance of input data."
		::= 5

	channelUpTrap TRAP-TYPE
		ENTERPRISE gigaMuxESC8SM
		VARIABLES { channelIndex }
		DESCRIPTION
			"The channelOperStatus has transitioned into
			 the normal(1) state."
		::= 6

	channelDataLossTrap TRAP-TYPE
		ENTERPRISE gigaMuxESC8SM
		VARIABLES { channelIndex }
		DESCRIPTION
			"The channelDataLossStatus has transitioned into
			 an alarm state."
		::= 7

	channelDataRestoredTrap TRAP-TYPE
		ENTERPRISE gigaMuxESC8SM
		VARIABLES { channelIndex }
		DESCRIPTION
			"The channelDataLossStatus has transitioned into
			 the normal(1) state."
		::= 8

	END
