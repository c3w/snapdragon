-- *********************************************************************
-- CISCO-FC-FE-MIB.my: Cisco Fibre Channel Fibre Element Mib
--
-- September 2002, Srini Kode
--
-- Copyright (c) 2002 by cisco Systems, Inc.
-- All rights reserved.
-- 
-- *********************************************************************

CISCO-FC-FE-MIB DEFINITIONS ::= BEGIN

IMPORTS
        MODULE-IDENTITY, OBJECT-TYPE,
        Counter32, Counter64, Integer32,
        Unsigned32, NOTIFICATION-TYPE          FROM SNMPv2-SMI
        MODULE-COMPLIANCE, OBJECT-GROUP,
        NOTIFICATION-GROUP                     FROM SNMPv2-CONF
        TEXTUAL-CONVENTION, TruthValue         FROM SNMPv2-TC
        SnmpAdminString                        FROM SNMP-FRAMEWORK-MIB
        ifIndex, 
        InterfaceIndexOrZero                   FROM IF-MIB
        ciscoMgmt                              FROM CISCO-SMI
        MicroSeconds                           FROM CISCO-TC
        FcNameId, FcAddressId,
        FcClassOfServices,
        FcPortTypes, FcPortTxTypes, FcIfSpeed,
        FcPortModuleTypes                      FROM CISCO-ST-TC
        vsanIndex                              FROM CISCO-VSAN-MIB
        FcList                                 FROM CISCO-ZS-MIB;
        
         
ciscoFcFeMIB MODULE-IDENTITY
        LAST-UPDATED "200211110000Z"
        ORGANIZATION "Cisco Systems Inc. "
        CONTACT-INFO
                "     Cisco Systems
                      Customer Service
                Postal: 170 W Tasman Drive
                      San Jose, CA  95134
                      USA
                Tel: +1 800 553 -NETS
                E-mail: cs-san@cisco.com"
        DESCRIPTION
            "This is the Cisco fibre element management MIB module.
             It covers:
             - Cisco extension to the interface MIB ( IF-MIB )
             - Contains all the groups from FIBRE-CHANNEL-FE-MIB
               relevant to Cisco fabric.
             - Other features specific to Cisco fabric.
             This MIB supports all the port types defined by the
             textual convention FcPortTypes. In addition it also
             supports Nx_port, where Nx_port can be either N_port or
             NL_port. The FC standards define Interconnect_Ports
             to be E_ports or B_Ports.
             This MIB supports Port Channel ports. Port 
             Channel port is a single logical port, which contains 
             multiple physical ports as its members. Presently only 
             E_ports can be a member of Port Channel port." 
        REVISION    "200211110000Z"
        DESCRIPTION
            "Modified fcTrunkIfUpNotify description."     
        REVISION    "200211010000Z"
        DESCRIPTION 
        "Modifed fcIfTable, fcIfCapTable. "  
        REVISION   "200210020000Z"
        DESCRIPTION
            "Initial version of this MIB module."
        ::= { ciscoMgmt 289 }

ciscoFcFeObjects     OBJECT IDENTIFIER   ::= { ciscoFcFeMIB 1 }
cffFcFeMIBConformance  OBJECT IDENTIFIER ::= { ciscoFcFeMIB 2 }
cffFcFeConfig        OBJECT IDENTIFIER   ::= { ciscoFcFeObjects 1 }
cffFcFeStatistics    OBJECT IDENTIFIER   ::= { ciscoFcFeObjects 2 }
cffFcFeNotification  OBJECT IDENTIFIER   ::= { ciscoFcFeObjects 3 }
cffFcFeNotifications OBJECT IDENTIFIER   ::= { cffFcFeNotification 0 }


-- Textual Conventions

FcphVersion ::= TEXTUAL-CONVENTION
     STATUS         current
     DESCRIPTION    "Represents the version of FC-PH supported by an
                     NxPort or FC-Port. "
     SYNTAX         Integer32 (0..255)

FcBbCredit ::= TEXTUAL-CONVENTION
     STATUS         current
     DESCRIPTION    "Represents the buffer-to-buffer credit of an
                    NxPort or FC-Port. "
     SYNTAX         Integer32 (0..32767)

FcRxDataFieldSize ::= TEXTUAL-CONVENTION
     STATUS         current
     DESCRIPTION    "Represents the receive data field size of an
                     NxPort or FC-Port. "
     SYNTAX         Integer32 (128..2112)

FcBbCreditModel ::= TEXTUAL-CONVENTION
     STATUS         current
     DESCRIPTION    "Represents the Buffer-to-Buffer Credit model of 
                     an FC-Port.
                     regular(1)   - Credit model is regular
                     alternate(2) - Credit model is alternate. "
     SYNTAX         INTEGER { 
                        regular(1),
                        alternate (2)
                    }

FcIfOperStatusReason  ::= TEXTUAL-CONVENTION
     STATUS         current
     DESCRIPTION    "The cause of current operational state of the  
                     port.
                     'other(1)' - reasons other than defined here.
                     'none(2)' - no failure
                     'hwFailure(3)' - hardware failure.  
                     'loopbackDiagFailure(4)' - loopback diagnostics 
                         failure.
                     'errorDisabled(5)' - the port is not operational 
                         due to some error conditions that require
                         administrative attention.
                     'swFailure(6)' - software failure.
                     'linkFailure(7)' - physical link failure.
                     'offline(8)' -  physical link is in offline state
                         as defined in the FC-FS standards.
                     'nonParticipating(9)' - during loop initialization,
                         the port is not allowed to participate in loop
                         operations.
                     'initializing(10)' - port is being initialized. 
                     'vsanInactive(11)'- port VSAN is inactive. The port
                         becomes operational again when the port VSAN is
                         active. 
                     'adminDown(12)' - 'ifAdminStatus' is down(2).
                     'channelAdminDown(13)' - this port is a member of
                         a port channel and that port channel's
                         ifAdminStatus is 'down(2)'. 
                     'channelOperSuspended(14)' - this port is a member
                         of a port channel and its operational 
                         parameters are incompatible with the port 
                         channel parameters.  
                     'channelConfigurationInProgress(15)' - this port 
                         is undergoing a port channel configuration.
                     'rcfInProgress(16)' -  an isolated xE_port is 
                         transmiting an reconfigure fabric, requesting
                         a disruptive reconfiguration in an attempt to 
                         build a single, non-isolated fabric.
                     Only the Interconnect_Ports can become isolated. 
                     'elpFailureIsolation(17)' - during a port 
                         initialization the prospective 
                         Interconnect_Ports find incompatible link
                         parameters.
                     'escFailureIsolation(18) - during a port 
                         initialization the prospective 
                         Interconnect_Ports are unable to proceed with
                         initialization as a result of Exchange Switch
                         Capabilities (ESC).
                     'domainOverlapIsolation(19)' - there is a overlap 
                         in domains while attempting to connect two
                         existing fabrics.
                     'domainAddrAssignFailureIsolation(20)' - the 
                         elected principal switch is not capable of
                         performing domain address manager functions so
                         no Nx_port traffic can be forwarded across
                         switches, hence all Interconnect_Ports in the
                         switch are isolated.
                     'domainOtherSideEportIsolation(21)' - the peer 
                         e-port is isolated.
                     'domainInvalidRCFReceived(22)' - Invalid rcf 
                         received.
                     'domainManagerDisabled(23) - domain manager is
                         disabled.
                     'zoneMergeFailureIsolation(24)' - the two 
                         Interconnect_Ports cannot merge zoning 
                         configuration after having exchanged merging 
                         request for zoning.
                     'vsanMismatchIsolation(25)' - this vsan is not 
                         configured on both sides of a trunk port.
                     'parentDown(26)' - the physical port to which this
                         interface is bound is down.
                     'srcPortNotBound(27)'- no source port is specified
                         for this interface.
                     'interfaceRemoved(28)' - interface is being 
                         removed.
                     'fcotNotPresent(29)' - fcot(GBIC) not present.
                     'fcotVendorNotSupported(30)' - fcot(GBIC) vendor 
                         is not supported. 
                     'incompatibleAdminMode(31)' - port admin mode is
                         incompatible with port capabilities. 
                     'incompatibleAdminSpeed(32)' - port speed is
                         incompatible with port capabilities. 
                     'suspendedByMode(33)' -  port that belongs to a
                         port channel is suspended due to incompatible
                         operational mode.                         
                     'suspendedBySpeed(34)' - port that belongs to a
                         port channel is suspended due to incompatible
                         operational speed.
                     'suspendedByWWN(35)' - port that belongs to a
                         port channel is suspended due to incompatible
                         remote switch WWN.
                     'domainMaxReTxFailure(36)' - domain manager 
                         failure after maximum retries.
                     'eppFailure(37)' - trunk negotiation protocol
                         failure after maximum retries.
                     'portVsanMismatchIsolation(38)' - an attempt is
                         made to connect two switches using 
                         non-trunking ports having different port 
                         VSANs. 
                     'loopbackIsolation(39)' - port is connected to
                         another port in the same switch.
                     'upgradeInProgress(40)' - linecard upgrade in 
                         progress.
                     'incompatibleAdminRxBBCredit(41)' - receive
                         BB credit is incompatible.
                     'incompatibleAdminRxBufferSize(42)' - receive
                         buffer size is incompatible.
                     'portChannelMembersDown(43)' - no operational
                         members.
                     'zoneRemoteNoRespIsolation(44)' - isolation
                         due to remote zone server not responding."
     SYNTAX          INTEGER {
                       other(1),
                       none(2),
                       hwFailure(3),
                       loopbackDiagFailure(4),
                       errorDisabled(5),
                       swFailure(6),
                       linkFailure(7),
                       offline(8),
                       nonParticipating(9),
                       initializing(10),
                       vsanInactive(11),
                       adminDown(12),
                       channelAdminDown(13),
                       channelOperSuspended(14),
                       channelConfigurationInProgress(15),
                       rcfInProgress(16),
                       elpFailureIsolation(17),
                       escFailureIsolation(18),
                       domainOverlapIsolation(19),
                       domainAddrAssignFailureIsolation(20),
                       domainOtherSideEportIsolation(21),
                       domainInvalidRCFReceived(22),
                       domainManagerDisabled(23),
                       zoneMergeFailureIsolation(24),
                       vsanMismatchIsolation(25),
                       parentDown(26),
                       srcPortNotBound(27),
                       interfaceRemoved(28),
                       fcotNotPresent(29),
                       fcotVendorNotSupported(30),
                       incompatibleAdminMode(31),
                       incompatibleAdminSpeed(32),
                       suspendedByMode(33),
                       suspendedBySpeed(34),
                       suspendedByWWN(35),
                       domainMaxReTxFailure(36),
                       eppFailure(37),
                       portVsanMismatchIsolation(38),
                       loopbackIsolation(39),
                       upgradeInProgress(40),
                       incompatibleAdminRxBBCredit(41),
                       incompatibleAdminRxBufferSize(42),
                       portChannelMembersDown(43),
                       zoneRemoteNoRespIsolation(44)
                     }             

--
-- fibre element group information
--

cffFcFeElementName  OBJECT-TYPE
        SYNTAX      FcNameId
        MAX-ACCESS  read-write
        STATUS      current
        DESCRIPTION
              "The World-Wide Name of this fabric element. It's a 
               64-bit identifier and is unique worldwide. "
        ::= { cffFcFeConfig 1 }


--
-- fcIfTable
--

fcIfTable  OBJECT-TYPE
        SYNTAX     SEQUENCE OF FcIfEntry
        MAX-ACCESS not-accessible
        STATUS     current
        DESCRIPTION
               "This table contains one entry per fibre channel switch
                port interface. Each entry holds the port interface 
                parameters. The entries are created by the fabric 
                switch when a module is inserted and it identifies a
                port on the module. 
                Similarly when a module is removed from the fabric
                switch all the port entries in this table 
                corresponding to that module are removed.
                This table also hold entries for Port Channel ports.  
                NOTE: Nx_ports are not represented in this table. "
        ::= { cffFcFeConfig  2 }

fcIfEntry OBJECT-TYPE
        SYNTAX     FcIfEntry
        MAX-ACCESS not-accessible
        STATUS     current
        DESCRIPTION
               "Each entry contains FC-port configuration parameters
                and state information. "
        INDEX { ifIndex }
        ::= { fcIfTable 1 }

FcIfEntry ::= 
        SEQUENCE {
            fcIfWwn                           FcNameId,
            fcIfAdminMode                     FcPortTypes,
            fcIfOperMode                      FcPortTypes,
            fcIfAdminSpeed                    FcIfSpeed,
            fcIfBeaconMode                    TruthValue,
            fcIfPortChannelIfIndex            InterfaceIndexOrZero,
            fcIfOperStatusCause               FcIfOperStatusReason,
            fcIfOperStatusCauseDescr          SnmpAdminString,
            fcIfAdminTrunkMode                INTEGER,
            fcIfOperTrunkMode                 INTEGER,
            fcIfAllowedVsanList2k             FcList,
            fcIfAllowedVsanList4k             FcList,
            fcIfActiveVsanList2k              FcList,
            fcIfActiveVsanList4k              FcList,          
            fcIfBbCreditModel                 FcBbCreditModel,
            fcIfHoldTime                      MicroSeconds,
            fcIfTransmitterType               FcPortTxTypes,
            fcIfConnectorType                 FcPortModuleTypes,   
            fcIfSerialNo                      SnmpAdminString,
            fcIfRevision                      SnmpAdminString,
            fcIfVendor                        SnmpAdminString,
            fcIfSFPSerialIDData               SnmpAdminString,
            fcIfPartNumber                    SnmpAdminString,
            fcIfAdminRxBbCredit               FcBbCredit,
            fcIfAdminRxBbCreditModeISL        FcBbCredit,
            fcIfAdminRxBbCreditModeFx         FcBbCredit,
            fcIfOperRxBbCredit                FcBbCredit,
            fcIfRxDataFieldSize               FcRxDataFieldSize
         }


fcIfWwn  OBJECT-TYPE
        SYNTAX      FcNameId
        MAX-ACCESS  read-only
        STATUS      current
        DESCRIPTION
              "The World-Wide Name of this FC-Port. It's a 64-bit 
               identifier and is unique worldwide. "
        ::= { fcIfEntry 1 }

fcIfAdminMode  OBJECT-TYPE
        SYNTAX      FcPortTypes                   
        MAX-ACCESS  read-write 
        STATUS      current
        DESCRIPTION
              "The port mode configured by the user. If the user 
               configured the port as auto(1), then the port 
               initialization scheme determines the mode of the port.
               In this case the user can look at 'fcIfOperMode' to 
               determine the current operating mode of port.
               If this interface is a Port Channel port then only
               auto(1) or ePort(4) is allowed. "
    	  DEFVAL  {auto}
        ::= { fcIfEntry 2 }

fcIfOperMode  OBJECT-TYPE
        SYNTAX      FcPortTypes           
        MAX-ACCESS  read-only 
        STATUS      current
        DESCRIPTION
              "The current operating mode of the port.
               This object will also be an additional varbind sent
               in the linkUp notification ( defined in IF-MIB ) in
               addition to the varbinds defined for this notification. "
        ::= { fcIfEntry 3 }


fcIfAdminSpeed  OBJECT-TYPE
        SYNTAX      FcIfSpeed
        MAX-ACCESS  read-write 
        STATUS      current
        DESCRIPTION
              "The port speed configured by the user.
               Since this is a characteristic of a physical port, this
               object is not applicable for Port Channel ports, i.e.,
               the value is instantiated but its value is irrelevant. "
        DEFVAL {auto}
        ::= { fcIfEntry 4 }

fcIfBeaconMode  OBJECT-TYPE
        SYNTAX      TruthValue
        MAX-ACCESS  read-write 
        STATUS      current
        DESCRIPTION
              "The Beacon mode configured by the user.
               If 'true', the Beacon mode is enabled.
               If 'false', the beacon mode is disabled.
               In Beacon mode, an interface LED is put into flashing 
               mode for easy identification of a particular
               interface. "
        DEFVAL  {true}
        ::= { fcIfEntry 5 }

fcIfPortChannelIfIndex  OBJECT-TYPE
        SYNTAX      InterfaceIndexOrZero
        MAX-ACCESS  read-only 
        STATUS      current
        DESCRIPTION
              "The ifIndex of the port channel port this port belongs
               to.
               A value of zero indicates that this port is not part
               of any port channel.
               For port channel port this object will have the ifIndex
               of the port channel port itself. " 
        ::= { fcIfEntry 6 }
      
fcIfOperStatusCause  OBJECT-TYPE
        SYNTAX      FcIfOperStatusReason              
        MAX-ACCESS  read-only 
        STATUS      current
        DESCRIPTION
              "The cause of current operational state of the 
               port.
               The current operational state of the port is shown by 
               the 'ifOperStatus' defined in IF-MIB. This object
               will show 'none(2)' for all the 'ifOperStatus' values
               except for 'down(2)'. It will show one of the values
               from the 'FcIfOperStatusReason' textual convention
               if 'ifOperStatus' is 'down(2)'. It will show other(1)
               if the operational status cause is not from one
               defined in  'FcIfOperStatusReason'.
               This object will also be an additional varbind sent
               in the linkDown notification ( defined in IF-MIB ) in 
               addition to the varbinds defined for this notification. "
        ::= { fcIfEntry 7 }

fcIfOperStatusCauseDescr  OBJECT-TYPE
        SYNTAX      SnmpAdminString
        MAX-ACCESS  read-only 
        STATUS      current
        DESCRIPTION
              "The description for the cause of current operational 
               state of the port, shown by the object 
               'fcIfOperStatusCause'. "
        ::= { fcIfEntry 8 }
  
fcIfAdminTrunkMode  OBJECT-TYPE
        SYNTAX      INTEGER {
                       nonTrunk(1),
                       trunk(2),
                       auto(3)
                    }
        MAX-ACCESS  read-write
        STATUS      current
        DESCRIPTION
               "The trunking mode configured by the user.
                When set to 'nonTrunk(1)', the port negotiates and
                converts the link into non-trunking mode. This port
                and the neighboring port's fcIfOperTrunkMode becomes
                non-trunk. When set to 'trunk(2)', the port 
                negotiates and converts the link into trunking mode
                only if the neighboring port, fcIfAdminTrunkMode is
                either 'trunk(2)' or 'auto(3)'. When set to 
                'auto(3)', the port is willing to convert the link
                to a trunk link only if the the neighbouring port,
                fcIfAdminTrunkMode is set to 'trunk(2)' mode. "
        DEFVAL {nonTrunk}            
        ::= { fcIfEntry 9 }

fcIfOperTrunkMode  OBJECT-TYPE
        SYNTAX      INTEGER {
                       nonTrunk(1),
                       trunk(2)
                    }
        MAX-ACCESS  read-only
        STATUS      current
        DESCRIPTION
               "The current trunking mode of the port. "    
        ::= { fcIfEntry 10 }

fcIfAllowedVsanList2k   OBJECT-TYPE
        SYNTAX      FcList
        MAX-ACCESS  read-write
        STATUS      current
        DESCRIPTION
               "The VSANs which are allowed to be received/
                transmitted on the port when the port is
                operating in trunking mode.
                Only ports operating in trunk mode can belong to 
                multiple VSANs. Each octet within the value of this
                object specifies a set of eight VSANs, with the first
                octet specifying VSANs 0 through 7, the second octet
                specifying VSANs 8 through 15, etc. Within each octet,
                the most significant bit represents the lowest
                numbered VSAN, and the least significant bit
                represents the highest numbered VSAN.  Thus, each 
                VSAN, is represented by a single bit within the value
                of this object. The corresponding VSAN is allowed on 
                this port if and only if that bit has a value of '1'.
                If this object has a value which is less than 256
                bytes long, then the VSANs which are not represented
                are considered to be allowed,i.e., effectively, the
                string is extended to be of length 256 bytes by
                appending bytes containing x'FF'. Note that this 
                means that the zero-length string represents the 
                'all VSANs are allowed' value.   
                This object is applicable to only ports operating
                in trunk mode.
                The value configured to this object will be retained 
                but will not be applicable when the port is put into
                non-trunking mode. It will be again applicable when
                the port is operating in trunking mode.
                Similarly, it can be modified at the time when this
                object is not applicable, i.e. when the port is 
                operating in non-trunking mode, but the modified value
                is retained for use on subsequent occasions when this
                object is applicable when the port is operating in 
                trunking mode.
                The default value is the zero-length string. " 
        DEFVAL {""}
        ::= { fcIfEntry 11 }

fcIfAllowedVsanList4k   OBJECT-TYPE
        SYNTAX      FcList
        MAX-ACCESS  read-write
        STATUS      current
        DESCRIPTION
                "The VSANs which are allowed to be received/
                transmitted on the port when the port is
                operating in trunking mode.
                Only ports operating in trunk mode can belong to 
                multiple VSANs. Each octet within the value of this
                object specifies a set of eight VSANs, with the first
                octet specifying VSANs 2047 through 2054, the second
                octet specifying VSANs 2055 through 2062, etc. Within
                each octet,the most significant bit represents the
                lowest numbered VSAN, and the least significant bit
                represents the highest numbered VSAN.  Thus, each 
                VSAN, is represented by a single bit within the value
                of this object. The corresponding VSAN is allowed on 
                this port if and only if that bit has a value of '1'.
                If this object has a value which is less than 256
                bytes long, then the VSANs which are not represented
                are considered to be allowed, i.e., effectively, the
                string is extended to be of length 256 bytes by
                appending bytes containing x'FF'. Note that this 
                means that the zero-length string represents the 
                'all VSANs are allowed' value.   
                This object is applicable to only ports operating
                in trunk mode.
                The value configured to this object will be retained 
                but will not be applicable when the port is put into
                non-trunking mode. It will be again applicable when
                the port is operating in trunking mode.
                Similarly, it can be modified at the time when this
                object is not applicable, i.e. when the port is 
                operating in non-trunking mode, but the modified value
                is retained for use on subsequent occasions when this
                object is applicable when the port is operating in 
                trunking mode.
                The default value is the zero-length string. " 
        DEFVAL {""}
        ::= { fcIfEntry 12 }

fcIfActiveVsanList2k  OBJECT-TYPE
        SYNTAX      FcList
        MAX-ACCESS  read-only 
        STATUS      current
        DESCRIPTION
                "The VSANs this port is associated with. Only ports
                 operating in trunk mode can belong to multiple VSANs.
                 Each octet within the value of this object specifies 
                 a set of eight VSANs, with the first octet specifying
                 VSANs 0 through 7, the second octet specifying 
                 VSANs 8 through 15, etc. Within each octet, the most
                 significant bit represents the lowest numbered
                 VSAN, and the least significant bit represents the
                 highest numbered VSAN. Thus, each VSAN to which this
                 port has membership to, is represented by a single 
                 bit within the value of this object. The corresponding 
                 VSAN that this port is a member of is active if and
                 only if that bit has a value of '1'. 
                 Note that the zero-length string represents that none 
                 of the VSANs that this port is a member of are active.
                 This object is applicable to only ports operating
                 in trunk mode. "
        ::= { fcIfEntry 13 }

fcIfActiveVsanList4k  OBJECT-TYPE
        SYNTAX      FcList
        MAX-ACCESS  read-only 
        STATUS      current
        DESCRIPTION
                "The VSANs this port is associated with. Only ports
                 operating in trunk mode can belong to multiple VSANs.
                 Each octet within the value of this object specifies 
                 a set of eight VSANs, with the first octet specifying
                 VSANs 2047 through 2054, the second octet specifying 
                 VSANs 2055 through 2062, etc. Within each octet, the
                 most significant bit represents the lowest numbered
                 VSAN, and the least significant bit represents the
                 highest numbered VSAN.  Thus, each VSAN to which this
                 port has membership to, is represented by a single 
                 bit within the value of this object. The corresponding 
                 VSAN that this port is a member of is active if and
                 only if that bit has a value of '1'. 
                 Note that the zero-length string represents that none 
                 of the VSANs that this port is a member of are active.
                 This object is applicable to only ports operating
                 in trunk mode. "
        ::= { fcIfEntry 14 }

fcIfBbCreditModel OBJECT-TYPE
        SYNTAX      FcBbCreditModel
        MAX-ACCESS  read-only
        STATUS      current
        DESCRIPTION
              "The BB_Credit model used by the FC-port. 
               The alternate BB_Credit management model can be used 
               in the arbitrated loop topology to manage the flow of
               frames between the two ports participating in the
               current loop circuit.
               Since this is a characteristic of a physical port, this
               object is not applicable for Port Channel ports, i.e.,
               the value is instantiated but its value is irrelevant. "
        ::= { fcIfEntry 15 }

fcIfHoldTime  OBJECT-TYPE
        SYNTAX      MicroSeconds
        UNITS       "microseconds"
        MAX-ACCESS  read-only
        STATUS      current
        DESCRIPTION
              "The maximum time that the FC-Port shall hold a frame
               in the transmitter buffer before discarding it, if it
               is unable to deliver the frame. 
               The value 0 in this object means the frame will be
               discarded immediately if the port is unable to deliver
               the frame.
               Since this is a characteristic of a physical port, this
               object is not applicable for Port Channel ports, i.e.,
               the value is instantiated but its value is irrelevant. "
        ::= { fcIfEntry 16 }

fcIfTransmitterType OBJECT-TYPE
        SYNTAX      FcPortTxTypes
        MAX-ACCESS  read-only
        STATUS      current
        DESCRIPTION
              "The technology of the port transceiver.
               Since this is a characteristic of a physical port, this
               object is not applicable for Port Channel ports, i.e.,
               the value is instantiated but its value is irrelevant. "
        ::= { fcIfEntry 17 }

fcIfConnectorType  OBJECT-TYPE
        SYNTAX      FcPortModuleTypes
        MAX-ACCESS  read-only
        STATUS      current
        DESCRIPTION
               "The module type of the port connector. This object 
                refers to the hardware implementation of the port.
                It will be 'embedded(3)' if the hardware equivalent to
                Gigabit interface card ( GBIC ) is part of the line
                card and is unremovable. It will be glm(3) if its a
                gigabit link module ( GLM ). A GLM has a different form
                factor than GBIC. GLM is not supported by our switch.
                It will be 'gbicSerialId(4)' if the GBIC serial id can
                be read, else it will be 'gbicNoSerialId(5)'.
                It will be 'sfpSerialId(6)', if the small form factor
                ( SFP ) pluggable GBICs serial id can be read, else
                it will be 'sfpNoSerialId(7)'.
                Since this is a characteristic of a physical port, this
                object is not applicable for Port Channel ports, i.e.,
                the value is instantiated but its value is irrelevant. "
        ::= { fcIfEntry 18 }

fcIfSerialNo  OBJECT-TYPE
        SYNTAX      SnmpAdminString
        MAX-ACCESS  read-only
        STATUS      current
        DESCRIPTION
              "The serial number of the connector unit ( e.g.,
               for a GBIC ). If this is not applicable, return a
               zero-length string.
               Since this is a characteristic of a physical port, this
               object is not applicable for Port Channel ports, i.e.,
               the value is instantiated but its value is irrelevant. "
        ::= { fcIfEntry 19 }

fcIfRevision  OBJECT-TYPE
        SYNTAX      SnmpAdminString
        MAX-ACCESS  read-only
        STATUS      current
        DESCRIPTION
             "The port revision of the connector unit (e.g., for a
              GBIC). If this is not applicable it returns a
              zero-length string.
              Since this is a characteristic of a physical port, this
              object is not applicable for Port Channel ports, i.e.,
              the value is instantiated but its value is irrelevant. "
        ::= { fcIfEntry 20 }

fcIfVendor  OBJECT-TYPE
        SYNTAX      SnmpAdminString
        MAX-ACCESS  read-only
        STATUS      current
        DESCRIPTION
             "The connector unit ( e.g., for a GBIC ) vendor.
              If this is not applicable it returns a
              zero-length string.
              Since this is a characteristic of a physical port, this
              object is not applicable for Port Channel ports, i.e.,
              the value is instantiated but its value is irrelevant. "
        ::= { fcIfEntry 21 }

fcIfSFPSerialIDData  OBJECT-TYPE
        SYNTAX      SnmpAdminString
        MAX-ACCESS  read-only
        STATUS      current
        DESCRIPTION
             "The connector unit ( e.g., for a GBIC ) Serial ID 
              data.
              If this is not applicable it returns a
              zero-length string.
              Since this is a characteristic of a physical port, this
              object is not applicable for Port Channel ports, i.e.,
              the value is instantiated but its value is irrelevant. "
        ::= { fcIfEntry 22 }

fcIfPartNumber  OBJECT-TYPE
        SYNTAX      SnmpAdminString
        MAX-ACCESS  read-only
        STATUS      current
        DESCRIPTION
             "The connector unit ( e.g., for a GBIC ) part number.
              If this is not applicable it returns a
              zero-length string.
              Since this is a characteristic of a physical port, this
              object is not applicable for Port Channel ports, i.e.,
              the value is instantiated but its value is irrelevant. "
        ::= { fcIfEntry 23 }

fcIfAdminRxBbCredit OBJECT-TYPE
        SYNTAX      FcBbCredit
        UNITS       "buffers"
        MAX-ACCESS  read-write
        STATUS      current
        DESCRIPTION
             "The receive buffer-to-buffer credits configured for
              this port. If the value configured is zero, then
              the value of the object fcIfCapRxBbCreditDefault is 
              used if the port is operating in Fx mode. Similarly,
              if the port is operating in xE_port mode then the value
              of the object fcIfCapISLRxBbCreditDefault is used. 
              If a non-zero value is configured for this object then,
              if the values configured for fcIfAdminRxBbCreditModeISL
              and fcIfAdminRxBbCreditModeFx is zero, then the 
              value of this object is used for the port operating
              in either Fx or xE_port mode. But if
              fcIfAdminRxBbCreditModeISL is configured with a valid
              value, then the value of fcIfAdminRxBbCreditModeISL 
              object is used instead of this value, if the port is
              operating in xE_port mode. Similarly, if
              the values configured for fcIfAdminRxBbCreditModeFx
              is valid, then the value of fcIfAdminRxBbCreditModeFx
              object is used instead of this value, if the port is
              operating in Fx mode. "
        ::= { fcIfEntry 24 }

fcIfAdminRxBbCreditModeISL OBJECT-TYPE
        SYNTAX      FcBbCredit
        UNITS       "buffers"
        MAX-ACCESS  read-write
        STATUS      current
        DESCRIPTION
             "The receive buffer-to-buffer credits configured for
              this port to be used if it is operating in 
              xE_port mode. "
        ::= { fcIfEntry 25 }

fcIfAdminRxBbCreditModeFx OBJECT-TYPE
        SYNTAX      FcBbCredit
        UNITS       "buffers"
        MAX-ACCESS  read-write
        STATUS      current
        DESCRIPTION
             "The receive buffer-to-buffer credits configured for
              this port to be used if it is operating in 
              Fx mode. "
        ::= { fcIfEntry 26 }

fcIfOperRxBbCredit OBJECT-TYPE
        SYNTAX      FcBbCredit
        UNITS       "buffers"
        MAX-ACCESS  read-only
        STATUS      current
        DESCRIPTION
             "The receive buffer-to-buffer credits configured for
              the operational port mode. "
        ::= { fcIfEntry 27 }

fcIfRxDataFieldSize OBJECT-TYPE
        SYNTAX      FcRxDataFieldSize
        UNITS       "bytes"
        MAX-ACCESS  read-write
        STATUS      current
        DESCRIPTION
             "The largest Data_Field size for an FT_1 frame that
             can be received by this port. "
        ::= { fcIfEntry 28 }

--
-- fcTrunkIfTable.
--

fcTrunkIfTable  OBJECT-TYPE
        SYNTAX     SEQUENCE OF FcTrunkIfEntry
        MAX-ACCESS not-accessible
        STATUS     current
        DESCRIPTION
               "This table contains one entry for each trunking fibre 
                channel port per VSAN. When the FC-port goes
                into trunking mode, the fibre channel switch creates
                one entry per FC-port for each active VSAN, from the
                allowed VSAN list for this port. 
                The allowed VSAN list is configured using the objects,
                fcIfAllowedVsanList2k and fcIfAllowedVsanList4k. 
                If an VSAN becomes inactive then the switch removes the
                corresponding entries from this table, if they exist. "
        ::= { cffFcFeConfig  3 }

fcTrunkIfEntry OBJECT-TYPE
        SYNTAX     FcTrunkIfEntry
        MAX-ACCESS not-accessible
        STATUS     current
        DESCRIPTION
               "Each entry contains trunking FC-port parameters. "
        INDEX { ifIndex, vsanIndex }
        ::= { fcTrunkIfTable 1 }

FcTrunkIfEntry ::= 
        SEQUENCE {
            fcTrunkIfOperStatus            INTEGER,
            fcTrunkIfOperStatusCause       FcIfOperStatusReason,
            fcTrunkIfOperStatusCauseDescr  SnmpAdminString
        }

fcTrunkIfOperStatus  OBJECT-TYPE
        SYNTAX      INTEGER {
                       up(1),
                       down(2)             
                    }                      
        MAX-ACCESS  read-only 
        STATUS      current
        DESCRIPTION
              "The operational state of a VSAN on this port. If the port
               is in trunking mode, it is possible that the port state
               may be 'down(2)' only in some VSANs. If this port is down
               in this VSAN only then port state shown by 'ifOperStatus'
               may not be 'down(2)', but this object will show 
               'down(2)'.
               The 'fcTrunkIfOperStatusCause' object shows the reason
               for port being 'down(2)'. "
        ::= { fcTrunkIfEntry 1 }

fcTrunkIfOperStatusCause  OBJECT-TYPE
        SYNTAX      FcIfOperStatusReason
        MAX-ACCESS  read-only 
        STATUS      current
        DESCRIPTION
              "The cause of current operational state of the 
               port.
               The current operational state of the port is shown by 
               the 'fcTrunkIfOperStatus'. This object will show
               'none(2)' for all the 'fcTrunkIfOperStatus' values
               except for 'down(2)'. It will show one of the values
               from the 'FcIfOperStatusReason' textual convention
               if 'fcTrunkIfOperStatus' is 'down(2)'. "            
        ::= { fcTrunkIfEntry 2 }

fcTrunkIfOperStatusCauseDescr  OBJECT-TYPE
        SYNTAX      SnmpAdminString
        MAX-ACCESS  read-only 
        STATUS      current
        DESCRIPTION
              "The description for the cause of current operational 
               state of the port, shown by the object 
               'fcTrunkIfOperStatusCause'. "
        ::= { fcTrunkIfEntry 3 }


-- The FC-Port Fabric Login Group

fcIfLoginEntryCount  OBJECT-TYPE
        SYNTAX      Unsigned32 
        MAX-ACCESS  read-only
        STATUS      current
        DESCRIPTION
               "The number of login entries in 'fcIfLoginTable'. "    
        ::= { cffFcFeConfig 4 }

--
-- fcIfFLoginTable
--

fcIfFLoginTable OBJECT-TYPE
        SYNTAX      SEQUENCE OF FcIfFLoginEntry
        MAX-ACCESS  not-accessible
        STATUS      current
        DESCRIPTION
              "This table contains, one entry for each Nx_Port 
               attached to a particular FC-port in this VSAN in the
               Fabric element.
               Each entry contains services parameters established 
               from the most recent Fabric Login, explicit or 
               implicit. In case of private devices attached to port,
               the fabric switch does the login on behalf of the
               private device. The fabric switch creates or deletes an
               entry in this table.
               Note: An FC-port may have one or more Nx_Port 
               logged-in to it. "
        ::= { cffFcFeConfig 5 }

fcIfFLoginEntry OBJECT-TYPE
        SYNTAX      FcIfFLoginEntry
        MAX-ACCESS  not-accessible
        STATUS      current
        DESCRIPTION
              "An entry containing service parameters established
               by a successful Fabric Login to the port indicated
               by ifIndex. "
        INDEX { ifIndex, vsanIndex, fcIfNxLoginIndex }
        ::= { fcIfFLoginTable 1 }

FcIfFLoginEntry ::=
        SEQUENCE {
            fcIfNxLoginIndex            Unsigned32,
            fcIfNxPortNodeName          FcNameId,
            fcIfNxPortName              FcNameId,
            fcIfNxPortAddress           FcAddressId,
            fcIfNxFcphVersionAgreed     FcphVersion,
            fcIfNxRxBbCredit            FcBbCredit,
            fcIfNxTxBbCredit            FcBbCredit,
            fcIfNxClass2RxDataFieldSize FcRxDataFieldSize,
            fcIfNxClass3RxDataFieldSize FcRxDataFieldSize,
            fcIfNxCosSuppAgreed         FcClassOfServices,
            fcIfNxClass2SeqDelivAgreed  TruthValue,
            fcIfNxClass3SeqDelivAgreed  TruthValue
        }

fcIfNxLoginIndex  OBJECT-TYPE
        SYNTAX      Unsigned32
        MAX-ACCESS  not-accessible
        STATUS      current
        DESCRIPTION
              "An arbitrary value identifying the associated Nx_Port
               in the attachment for which the entry contains
               information. "
        ::= { fcIfFLoginEntry 1 }

fcIfNxPortNodeName  OBJECT-TYPE
        SYNTAX      FcNameId
        MAX-ACCESS  read-only
        STATUS      current
        DESCRIPTION
              "The world wide name of the Remote Node the 
               logged-in Nx_Port belongs to. "
        ::= { fcIfFLoginEntry 2 }

fcIfNxPortName  OBJECT-TYPE
        SYNTAX      FcNameId
        MAX-ACCESS  read-only
        STATUS      current
        DESCRIPTION
              "The world wide name of the logged-in Nx_Port. "
        ::= { fcIfFLoginEntry 3 }

fcIfNxPortAddress  OBJECT-TYPE
        SYNTAX      FcAddressId
        MAX-ACCESS  read-only
        STATUS      current
        DESCRIPTION
              "The address identifier that has been assigned to the
               logged-in Nx_Port. " 
        ::= { fcIfFLoginEntry 4 }

fcIfNxFcphVersionAgreed  OBJECT-TYPE
        SYNTAX      FcphVersion
        MAX-ACCESS  read-only
        STATUS      current
        DESCRIPTION
              "The version of FC-PH that the Fx_Port has agreed to 
               support from the Fabric Login. "
        ::= { fcIfFLoginEntry 5 }

fcIfNxRxBbCredit  OBJECT-TYPE
        SYNTAX      FcBbCredit
        MAX-ACCESS  read-only
        STATUS      current
        DESCRIPTION
              "The maximum number of receive buffers available for
               holding Class 2, Class 3 received from the logged-in
               Nx_Port.
               It is for buffer-to-buffer flow control in the 
               incoming direction from the logged-in Nx_Port to 
               FC-port. "
        ::= { fcIfFLoginEntry 6 }

fcIfNxTxBbCredit  OBJECT-TYPE
        SYNTAX      FcBbCredit
        MAX-ACCESS  read-only
        STATUS      current
        DESCRIPTION
              "The total number of buffers available for holding 
               Class 2, Class 3 frames to be transmitted to 
               the logged-in Nx_Port.  
               It is for buffer-to-buffer flow control in the 
               direction from FC-Port to Nx_Port.
               The buffer-to-buffer flow control mechanism is 
               indicated in the respective fcIfBbCreditModel. "
        ::= { fcIfFLoginEntry 7 }

fcIfNxClass2RxDataFieldSize  OBJECT-TYPE
        SYNTAX      FcRxDataFieldSize
        MAX-ACCESS  read-only
        STATUS      current
        DESCRIPTION
              "The Class 2 Receive Data Field Size of the logged-in 
               Nx_Port. 
               This object specifies the largest Data Field Size for 
               an FT_1 frame that can be received by the Nx_Port. "
        ::= { fcIfFLoginEntry 8 }

fcIfNxClass3RxDataFieldSize  OBJECT-TYPE
        SYNTAX      FcRxDataFieldSize
        MAX-ACCESS  read-only
        STATUS      current
        DESCRIPTION
              "The Class3 Receive Data Field Size of the logged-in
               Nx_Port. 
               This object specifies the largest Data Field Size for 
               an FT_1 frame that can be received by the Nx_Port. "
        ::= { fcIfFLoginEntry 9 }

fcIfNxCosSuppAgreed  OBJECT-TYPE
        SYNTAX      FcClassOfServices
        MAX-ACCESS  read-only
        STATUS      current
        DESCRIPTION
              "The object indicating the classes of services that 
               the logged-in Nx_Port has requested the FC-Port to 
               support and the FC-Port has granted the request. "
        ::= { fcIfFLoginEntry 10 }

fcIfNxClass2SeqDelivAgreed  OBJECT-TYPE
        SYNTAX      TruthValue
        MAX-ACCESS  read-only
        STATUS      current
        DESCRIPTION
              "The object indicating whether the FC-Port has agreed 
               to support Class 2 sequential delivery during the 
               Fabric Login. This is meaningful only if Class 2 
               service has been agreed. This object is applicable only
               to Fx_Ports. "
        ::= { fcIfFLoginEntry 11 }

fcIfNxClass3SeqDelivAgreed  OBJECT-TYPE
        SYNTAX      TruthValue
        MAX-ACCESS  read-only
        STATUS      current
        DESCRIPTION
              "The flag indicating whether the FxPort has agreed to 
               support Class 3 sequential delivery during the Fabric
               Login. This is meaningful only if Class 3 service has
               been agreed. This object is applicable only to
               Fx_Ports. "
        ::= { fcIfFLoginEntry 12 }


--
-- fcIfElpTable 
-- 

fcIfElpTable OBJECT-TYPE
        SYNTAX      SEQUENCE OF FcIfElpEntry
        MAX-ACCESS  not-accessible
        STATUS      current
        DESCRIPTION
              "This table contains, one entry for each local
               Interconnect_Port that has performed Exchange Link
               Parameters Switch Fabric Internal Link Service
               exchange with its peer Interconnect_Port.
               Each entry contains Exchange Link Parameters
               established from the most recent ELP exchange between
               the 2 Interconnect_Port.
               The agent creates and deletes each entry in this 
               table. The agent creates an entry in this table on a
               successful completion of a ELP exchange. Similarly the
               agent deletes the entry when the port goes down.
               NOTE:Port Channel ports are not represented in 
               this table. "
        ::= { cffFcFeConfig 6 }

fcIfElpEntry OBJECT-TYPE
        SYNTAX      FcIfElpEntry
        MAX-ACCESS  not-accessible
        STATUS      current
        DESCRIPTION
              "An entry containing Exchange Link parameters
               established between the Interconnect_Port indicated 
               by ifIndex and the peer Interconnect_Port indicated by 
               fcIfElpNbrPortName. "
        INDEX { ifIndex }
        ::= { fcIfElpTable 1 }

FcIfElpEntry ::=
        SEQUENCE {
            fcIfElpNbrNodeName               FcNameId,
            fcIfElpNbrPortName               FcNameId,
            fcIfElpRxBbCredit                FcBbCredit,
            fcIfElpTxBbCredit                FcBbCredit,
            fcIfElpCosSuppAgreed             FcClassOfServices,
            fcIfElpClass2SeqDelivAgreed      TruthValue,
            fcIfElpClass2RxDataFieldSize     FcRxDataFieldSize,
            fcIfElpClass3SeqDelivAgreed      TruthValue,
            fcIfElpClass3RxDataFieldSize     FcRxDataFieldSize,
            fcIfElpClassFXII                 TruthValue,
            fcIfElpClassFRxDataFieldSize     FcRxDataFieldSize,
            fcIfElpClassFConcurrentSeq       Unsigned32,
            fcIfElpClassFEndToEndCredit      Unsigned32,
            fcIfElpClassFOpenSeq             Unsigned32
        }

fcIfElpNbrNodeName  OBJECT-TYPE
        SYNTAX      FcNameId
        MAX-ACCESS  read-only
        STATUS      current
        DESCRIPTION
              "The node world wide name of the peer Node. "
        ::= { fcIfElpEntry 1 }

fcIfElpNbrPortName  OBJECT-TYPE
        SYNTAX      FcNameId
        MAX-ACCESS  read-only
        STATUS      current
        DESCRIPTION
              "The port world wide name of the peer Interconnect_Port. "
        ::= { fcIfElpEntry 2 }

fcIfElpRxBbCredit  OBJECT-TYPE
        SYNTAX      FcBbCredit
        MAX-ACCESS  read-only
        STATUS      current
        DESCRIPTION
              "The maximum number of receive buffers available for
               holding Class 2, Class 3, Class F frames received from
               the peer Interconnect_Port.
               It is for buffer-to-buffer flow control in the 
               incoming direction from the peer Interconnect_Port to 
               local Interconnect_Port.
               The buffer-to-buffer flow control mechanism is 
               indicated in the respective fcIfBbCreditModel. "
        ::= { fcIfElpEntry 3 }

fcIfElpTxBbCredit  OBJECT-TYPE
        SYNTAX      FcBbCredit
        MAX-ACCESS  read-only
        STATUS      current
        DESCRIPTION
              "The total number of buffers available for holding 
               Class 2, Class 3, Class F frames to be transmitted to 
               the peer Interconnect_Port.  
               It is for buffer-to-buffer flow control in the 
               direction from the local Interconnect_Port to 
               peer Interconnect_Port.
               The buffer-to-buffer flow control mechanism is 
               indicated in the corresponding fcIfBbCreditModel. "
        ::= { fcIfElpEntry 4 }

fcIfElpCosSuppAgreed  OBJECT-TYPE
        SYNTAX      FcClassOfServices
        MAX-ACCESS  read-only
        STATUS      current
        DESCRIPTION
              "The object indicating the classes of services that 
               the peer Interconnect_Port has requested the local 
               Interconnect_Port to support and the local 
               Interconnect_Port has granted the request. "
        ::= { fcIfElpEntry 5 }

fcIfElpClass2SeqDelivAgreed  OBJECT-TYPE
        SYNTAX      TruthValue
        MAX-ACCESS  read-only
        STATUS      current
        DESCRIPTION
              "The object indicating whether the local 
               Interconnect_Port has agreed to support Class 2 
               sequential delivery during the Exchange Link 
               Parameters Switch Fabric Internal Link Service 
               request. This is meaningful only if Class 2 service 
               has been agreed. "
        ::= { fcIfElpEntry 6 }

fcIfElpClass2RxDataFieldSize  OBJECT-TYPE
        SYNTAX      FcRxDataFieldSize
        MAX-ACCESS  read-only
        STATUS      current
        DESCRIPTION
              "The Class 2 Receive Data Field Size of the peer
               Interconnect_Port. 
               This object specifies the largest Data Field Size for 
               an FT_1 frame that can be received by the 
               Interconnect_Port. This is meaningful only if Class 2
               service has been agreed. "
        ::= { fcIfElpEntry 7 }

fcIfElpClass3SeqDelivAgreed  OBJECT-TYPE
        SYNTAX      TruthValue
        MAX-ACCESS  read-only
        STATUS      current
        DESCRIPTION
              "The object indicating whether the local 
               Interconnect_Port has agreed to support Class 3 
               sequential delivery during the Exchange Link 
               Parameters Switch Fabric Internal Link Service 
               request. This is meaningful only if Class 3 service 
               has been agreed. "
        ::= { fcIfElpEntry 8 }

fcIfElpClass3RxDataFieldSize  OBJECT-TYPE
        SYNTAX      FcRxDataFieldSize
        MAX-ACCESS  read-only
        STATUS      current
        DESCRIPTION
              "The Class 3 Receive Data Field Size of the peer
               Interconnect_Port. 
               This object specifies the largest Data Field Size for 
               an FT_1 frame that can be received by the 
               Interconnect_Port. This is meaningful only if Class 3
               service has been agreed. "
        ::= { fcIfElpEntry 9 }

fcIfElpClassFXII  OBJECT-TYPE
        SYNTAX      TruthValue
        MAX-ACCESS  read-only
        STATUS      current
        DESCRIPTION
              "The object when true(1) indicates that the peer
               Interconnect_Port supplying this parameter requires
               that an interlock be used during X_ID assignment in
               Class F.
               This is meaningful only if Class F service has been 
               agreed. "
        ::= { fcIfElpEntry 10 }

fcIfElpClassFRxDataFieldSize  OBJECT-TYPE
        SYNTAX      FcRxDataFieldSize
        MAX-ACCESS  read-only
        STATUS      current
        DESCRIPTION
              "The Class F Receive Data Field Size of the peer
               Interconnect_Port. Class F service is always
               agreed between two Interconnect_Ports, and thus
               this object is always meaningful.
               This object specifies the largest Data Field Size for 
               an FT_1 frame that can be received by the 
               Interconnect_Port. "
        ::= { fcIfElpEntry 11 }

fcIfElpClassFConcurrentSeq  OBJECT-TYPE
        SYNTAX      Unsigned32 (0..255)
        MAX-ACCESS  read-only
        STATUS      current
        DESCRIPTION
              "The object indicating the number of sequence status
               blocks provided by the Interconnect_Port supplying
               the parameters for tracking the progress of a sequence
               as a sequence recipient. The maximum number of 
               concurrent sequences that can be specified is 255. A
               value of zero in this field is reserved. "
        ::= { fcIfElpEntry 12 }

fcIfElpClassFEndToEndCredit  OBJECT-TYPE
        SYNTAX      Unsigned32
        MAX-ACCESS  read-only
        STATUS      current
        DESCRIPTION
              "The object indicating the maximum number of Class F
               data frames which can be transmitted by an
               Interconnect_Port without receipt of accompanying
               ACK or Link_Response frames. The minimum value of
               end-to-end credit is one. The end-to-end credit
               field specified is associated with the number of
               buffers available for holding the Data_Field of a
               Class F frame and processing the contents of that
               Data_Field by the Interconnect_Port supplying the
               parameters. "
        ::= { fcIfElpEntry 13 }

fcIfElpClassFOpenSeq  OBJECT-TYPE
        SYNTAX      Unsigned32
        MAX-ACCESS  read-only
        STATUS      current
        DESCRIPTION
              "The value of the open sequences per exchange shall
               specify the maximum number of sequences that can be 
               open at one time at the recipient between a pair of
               Interconnect_Ports for one exchange.This value is 
               used for exchange and sequence tracking. "
        ::= { fcIfElpEntry 14 }




--
-- fcIfCapTable
--

fcIfCapTable OBJECT-TYPE
        SYNTAX      SEQUENCE OF FcIfCapEntry
        MAX-ACCESS  not-accessible
        STATUS      current
        DESCRIPTION
               "This table contains, one entry for each FC-Port.
                It contains information describing about what each
                FC-port is inherently capable of operating or 
                supporting.
                The fabric switch creates or deletes an entry in this
                table.
                NOTE:This table has objects which represent the
                characteristics of a physical port. Thus, Port 
                Channel ports are not represented in this table. "
        ::= { cffFcFeConfig  7 }

fcIfCapEntry OBJECT-TYPE
        SYNTAX      FcIfCapEntry
        MAX-ACCESS  not-accessible
        STATUS      current
        DESCRIPTION
               "Each entry contains the Capability of a FC-Port. "
        AUGMENTS { fcIfEntry }
        ::= { fcIfCapTable 1 }

FcIfCapEntry ::=
        SEQUENCE {
            fcIfCapFcphVersionHigh        FcphVersion,
            fcIfCapFcphVersionLow         FcphVersion,
            fcIfCapRxBbCreditMax          FcBbCredit,
            fcIfCapRxBbCreditMin          FcBbCredit,
            fcIfCapRxDataFieldSizeMax     FcRxDataFieldSize,
            fcIfCapRxDataFieldSizeMin     FcRxDataFieldSize,
            fcIfCapCos                    FcClassOfServices,
            fcIfCapClass2SeqDeliv         TruthValue,
            fcIfCapClass3SeqDeliv         TruthValue,
            fcIfCapHoldTimeMax            MicroSeconds,
            fcIfCapHoldTimeMin            MicroSeconds,
            fcIfCapISLRxBbCreditMax       FcBbCredit,
            fcIfCapISLRxBbCreditMin       FcBbCredit,
            fcIfCapRxBbCreditWriteable    TruthValue,
            fcIfCapRxBbCreditDefault      FcBbCredit,
            fcIfCapISLRxBbCreditDefault   FcBbCredit
         }

fcIfCapFcphVersionHigh OBJECT-TYPE
         SYNTAX      FcphVersion
         MAX-ACCESS  read-only
         STATUS      current
         DESCRIPTION
               "The highest version of FC-PH that the FC-Port is
                capable of supporting. "
         ::= { fcIfCapEntry 1 }

fcIfCapFcphVersionLow OBJECT-TYPE
         SYNTAX      FcphVersion
         MAX-ACCESS  read-only
         STATUS      current
         DESCRIPTION
               "The lowest version of FC-PH that the FC-Port is
                capable of supporting. "
         ::= { fcIfCapEntry 2 }

fcIfCapRxBbCreditMax OBJECT-TYPE
         SYNTAX      FcBbCredit  
         UNITS       "buffers"
         MAX-ACCESS  read-only
         STATUS      current
         DESCRIPTION
               "The maximum number of receive buffers the port
                hardware is capable of receiving 
                from the attached Nx_Port. This object is 
                applicable to ports operating in Fx mode. "
         ::= { fcIfCapEntry 3 }

fcIfCapRxBbCreditMin OBJECT-TYPE
         SYNTAX      FcBbCredit 
         UNITS       "buffers"
         MAX-ACCESS  read-only
         STATUS      current
         DESCRIPTION
               "The minimum number of receive buffers the port
                hardware is capable of receiving from 
                the attached Nx_Port. This object is applicable
                to ports operating in  Fx mode. "
         ::= { fcIfCapEntry 4 }

fcIfCapRxDataFieldSizeMax OBJECT-TYPE
         SYNTAX      FcRxDataFieldSize
         MAX-ACCESS  read-only
         STATUS      current
         DESCRIPTION
               "The maximum size in bytes of the Data Field in a frame
                that the FC-Port is capable of receiving from its 
                attached FC-port. "
         ::= { fcIfCapEntry 5 }

fcIfCapRxDataFieldSizeMin OBJECT-TYPE
         SYNTAX      FcRxDataFieldSize
         MAX-ACCESS  read-only
         STATUS      current
         DESCRIPTION
               "The minimum size in bytes of the Data Field in a frame 
                that the FC-Port is capable of receiving from its
                attached FC-port. "
         ::= { fcIfCapEntry 6 }

fcIfCapCos OBJECT-TYPE
         SYNTAX      FcClassOfServices
         MAX-ACCESS  read-only
         STATUS      current
         DESCRIPTION
               "The Bit mask indicating the set of Classes of Service
                that the FC-Port is capable of supporting. "
         ::= { fcIfCapEntry 7 }

fcIfCapClass2SeqDeliv OBJECT-TYPE
         SYNTAX      TruthValue
         MAX-ACCESS  read-only
         STATUS      current
         DESCRIPTION
               "The flag indicating whether or not the FC-Port is 
                capable of supporting Class 2 Sequential Delivery. "
         ::= { fcIfCapEntry 8 }

fcIfCapClass3SeqDeliv OBJECT-TYPE
         SYNTAX      TruthValue
         MAX-ACCESS  read-only
         STATUS      current
         DESCRIPTION
               "The flag indicating whether or not the FC-Port is 
                capable of supporting Class 3 Sequential Delivery. "
         ::= { fcIfCapEntry 9 }

fcIfCapHoldTimeMax OBJECT-TYPE
         SYNTAX      MicroSeconds
         MAX-ACCESS  read-only
         STATUS      current
         DESCRIPTION
               "The maximum holding time ( in microseconds ) that the 
                FC-Port is capable of supporting. "
         ::= { fcIfCapEntry 10 }

fcIfCapHoldTimeMin OBJECT-TYPE
         SYNTAX      MicroSeconds
         MAX-ACCESS  read-only
         STATUS      current
         DESCRIPTION
               "The minimum holding time ( in microseconds ) that the 
                FC-Port is capable of supporting."
         ::= { fcIfCapEntry 11 }

fcIfCapISLRxBbCreditMax OBJECT-TYPE
         SYNTAX      FcBbCredit
         UNITS       "buffers"
         MAX-ACCESS  read-only
         STATUS      current
         DESCRIPTION
               "The maximum number of receive buffers the port
                hardware  is capable of receiving from 
                the attached Inter Connect  port. This object 
                is applicable to ports operating in xE_port mode. "
         ::= { fcIfCapEntry 12 }

fcIfCapISLRxBbCreditMin OBJECT-TYPE
         SYNTAX      FcBbCredit 
         UNITS       "buffers"
         MAX-ACCESS  read-only
         STATUS      current
         DESCRIPTION
               "The minimum number of receive buffers the port
                hardware is capable of receiving from the
                attached xE_port or B_port. This object is 
                applicable to ports operating in xE_port mode. "
         ::= { fcIfCapEntry 13 }
         
fcIfCapRxBbCreditWriteable  OBJECT-TYPE
         SYNTAX      TruthValue
         MAX-ACCESS  read-only
         STATUS      current
         DESCRIPTION
               "The value indicating whether the port is capable
               of allowing the user to configure receive buffer to
               buffer credit. 
               The values configured for the objects:
               fcIfAdminRxBbCredit,fcIfAdminRxBbCreditModeISL,
               fcIfAdminRxBbCreditModeFx will take effect 
               only if the value of this object is true(1),
               otherwise the default values specified by the 
               objects: fcIfCapRxBbCreditDefault,
               fcIfCapISLRxBbCreditDefault will stay in efect
               depending on the operating mode of the port. "
         ::= { fcIfCapEntry 14 }

fcIfCapRxBbCreditDefault OBJECT-TYPE
         SYNTAX      FcBbCredit
         UNITS       "buffers"
         MAX-ACCESS  read-only
         STATUS      current
         DESCRIPTION
               "The default recieve buffer-to-buffer credits if
                the port is operating in Fx mode. "
         ::= { fcIfCapEntry 15 }
         
fcIfCapISLRxBbCreditDefault OBJECT-TYPE
         SYNTAX      FcBbCredit
         UNITS       "buffers"
         MAX-ACCESS  read-only
         STATUS      current
         DESCRIPTION
               "The default recieve buffer-to-buffer credits if
                the port is operating in xE_port mode. "
         ::= { fcIfCapEntry 16 }

adminTrunkProtocol  OBJECT-TYPE
        SYNTAX      INTEGER {
                       enable(1),
                       disable(2)             
                    }                      
        MAX-ACCESS  read-write
        STATUS      current
        DESCRIPTION
              "The object to either enable or disable the trunking 
               protocol for the device. The trunking protocol is used
               for negotiating trunk mode and calculating operational
               VSANs on an EISL link. It also performs port VSAN
               consistency checks. On non-trunking ISL links, if the
               port VSANs are different, the E ports will be isolated.
               To avoid this isolation, this mib variable should be 
               set to 'disable(2)'.
               enable(1) - enables trunking protocol.
               disable (2) - disables the trunking protocol. "  
        ::= { cffFcFeConfig 8 }

fcIfElpRejectReasonCode  OBJECT-TYPE
        SYNTAX        Integer32 (0..2147483647)
        MAX-ACCESS    accessible-for-notify
        STATUS        current
        DESCRIPTION   
               "The reason code for the ELP reject."
        REFERENCE
              "FC-SW-2 REV 4.9 Section 6.1.2"
        ::= {  cffFcFeConfig 9 }

fcIfElpRejectReasonCodeExpl  OBJECT-TYPE
        SYNTAX        Integer32 (0..2147483647)
        MAX-ACCESS    accessible-for-notify
        STATUS        current
        DESCRIPTION   
               "The reason code explanation for the ELP reject."
        REFERENCE
              "FC-SW-2 REV 4.9 Section 6.1.2"
        ::= {  cffFcFeConfig 10 }                         

--
-- fcIfErrorTable
-- 

fcIfErrorTable OBJECT-TYPE
        SYNTAX      SEQUENCE OF FcIfErrorEntry
        MAX-ACCESS  not-accessible
        STATUS      current
        DESCRIPTION
               "This table contains, one entry for each fabric 
                channel port( including any Port Channel ports ). It 
                contains counters that record the errors detected.
                This table is an extension to interfaces group defined
                in IF-MIB. It contains additional errors specific
                to this device. "
        ::= { cffFcFeStatistics 1 }

fcIfErrorEntry OBJECT-TYPE
        SYNTAX      FcIfErrorEntry
        MAX-ACCESS  not-accessible
        STATUS      current
        DESCRIPTION
               "Each entry contains error counters of a fabric 
                channel port. "
        AUGMENTS { fcIfEntry }
        ::= { fcIfErrorTable 1 }

FcIfErrorEntry ::=  
        SEQUENCE {
            fcIfLinkFailures               Counter32,
            fcIfSyncLosses                 Counter32,
            fcIfSigLosses                  Counter32,
            fcIfPrimSeqProtoErrors         Counter32,
            fcIfInvalidTxWords             Counter32,
            fcIfInvalidCrcs                Counter32,
            fcIfDelimiterErrors            Counter32,
            fcIfAddressIdErrors            Counter32,
            fcIfLinkResetIns               Counter32,
            fcIfLinkResetOuts              Counter32,
            fcIfOlsIns                     Counter32,
            fcIfOlsOuts                    Counter32,
            fcIfRuntFramesIn               Counter32,
            fcIfJabberFramesIn             Counter32,           
            fcIfTxWaitCount                Counter32,
            fcIfFramesTooLong              Counter32,
            fcIfFramesTooShort             Counter32,
            fcIfLRRIn                      Counter32,
            fcIfLRROut                     Counter32,
            fcIfNOSIn                      Counter32,
            fcIfNOSOut                     Counter32,
            fcIfFragFrames                 Counter32,
            fcIfEOFaFrames                 Counter32,
            fcIfUnknownClassFrames         Counter32,
            fcIf8b10bDisparityErrors       Counter32,
            fcIfFramesDiscard              Counter32,
            fcIfELPFailures                Counter32,
            fcIfBBCreditTransistionFromZero  Counter32,
            fcIfEISLFramesDiscard          Counter32,
            fcIfFramingErrorFrames         Counter32
        } 

fcIfLinkFailures OBJECT-TYPE
        SYNTAX      Counter32
        MAX-ACCESS  read-only
        STATUS      current
        DESCRIPTION
              "The number of link failures detected by the FC-Port. " 
        REFERENCE
              "FC-PH REV 4.3 Section 29.3.1"
        ::= { fcIfErrorEntry 1 }

fcIfSyncLosses OBJECT-TYPE
        SYNTAX      Counter32
        MAX-ACCESS  read-only
        STATUS      current
        DESCRIPTION
              "The number of loss of synchronization failures 
               detected  by the FC-Port. "
        REFERENCE
              "FC-PH REV 4.3 Section 12.1.3.1"
        ::= { fcIfErrorEntry 2 }

fcIfSigLosses OBJECT-TYPE
        SYNTAX      Counter32
        MAX-ACCESS  read-only
        STATUS      current
        DESCRIPTION
              "The number of signal losses detected by the FC-Port. "
        REFERENCE
              "FC-PH REV 4.3 Section 12.1.3.4"
        ::= { fcIfErrorEntry 3 }

fcIfPrimSeqProtoErrors OBJECT-TYPE
        SYNTAX      Counter32
        MAX-ACCESS  read-only
        STATUS      current
        DESCRIPTION
              "The number of primitive sequence protocol errors 
               detected by the FC-Port. "
        REFERENCE
              "FC-PH REV 4.3 Section 29.3.3"
        ::= { fcIfErrorEntry 4 }

fcIfInvalidTxWords OBJECT-TYPE
        SYNTAX      Counter32
        MAX-ACCESS  read-only
        STATUS      current
        DESCRIPTION
              "The number of invalid transmission words detected by 
               the FC-Port. "
        REFERENCE
              "FC-PH REV 4.3 Section 12.1.3.1"
        ::= { fcIfErrorEntry 5 }

fcIfInvalidCrcs OBJECT-TYPE
        SYNTAX      Counter32
        MAX-ACCESS  read-only
        STATUS      current
        DESCRIPTION
              "The number of invalid CRCs detected by the FC-Port.
               Loop ports should not count CRC errors passing 
               through when monitoring. "
        REFERENCE
              "FC-PH REV 4.3 Section 29.8"
        ::= { fcIfErrorEntry 6 }

fcIfDelimiterErrors OBJECT-TYPE
        SYNTAX      Counter32
        MAX-ACCESS  read-only
        STATUS      current
        DESCRIPTION
              "The number of Delimiter Errors detected by the 
               FC-Port. "
        REFERENCE
              "FC-PH REV 4.3 Section 29.9"
        ::= { fcIfErrorEntry 7 }

fcIfAddressIdErrors OBJECT-TYPE
        SYNTAX      Counter32
        MAX-ACCESS  read-only
        STATUS      current
        DESCRIPTION
              "The number of address identifier errors detected by 
               the FC-Port. "
        REFERENCE
              "FC-PH REV 4.3 Section 29.9"
        ::= { fcIfErrorEntry 8 }

fcIfLinkResetIns OBJECT-TYPE
        SYNTAX      Counter32
        MAX-ACCESS  read-only
        STATUS      current
        DESCRIPTION
              "The number of link reset protocol errors received by 
               the FC-Port from the attached FC-port. "
        REFERENCE
              "FC-PH REV 4.3 Section 29.4"
        ::= { fcIfErrorEntry 9 }

fcIfLinkResetOuts OBJECT-TYPE
        SYNTAX      Counter32
        MAX-ACCESS  read-only
        STATUS      current
        DESCRIPTION
              "The number of link reset protocol errors issued by 
               the FC-Port to the attached FC-Port. "
        REFERENCE
              "FC-PH REV 4.3 Section 29.4"
        ::= { fcIfErrorEntry 10 }

fcIfOlsIns OBJECT-TYPE
        SYNTAX      Counter32
        MAX-ACCESS  read-only
        STATUS      current
        DESCRIPTION
              "The number of Offline Sequence errors received by the 
               FC-Port. "
        REFERENCE
              "FC-PH REV 4.3 Section 16.4.3"
        ::= { fcIfErrorEntry 11 }

fcIfOlsOuts OBJECT-TYPE
        SYNTAX      Counter32
        MAX-ACCESS  read-only
        STATUS      current
        DESCRIPTION
              "The number of Offline Sequence errors issued by the
               FC-Port. "
        REFERENCE
              "FC-PH REV 4.3 Section 16.4.3"
        ::= { fcIfErrorEntry 12 }

fcIfRuntFramesIn   OBJECT-TYPE
        SYNTAX      Counter32
        MAX-ACCESS  read-only
        STATUS      current
        DESCRIPTION
               "The number of frames received by the FC-port that are
                shorter than the minimum allowable frame length 
                regardless if the  CRC is good or not. "              
        ::= { fcIfErrorEntry 13 }

fcIfJabberFramesIn  OBJECT-TYPE
        SYNTAX      Counter32
        MAX-ACCESS  read-only
        STATUS      current
        DESCRIPTION
               "The number of frames received by the FC-port that are
                longer than a maximum frame length and also have a 
                CRC error. "         
        ::= { fcIfErrorEntry 14 }

fcIfTxWaitCount  OBJECT-TYPE
        SYNTAX      Counter32
        MAX-ACCESS  read-only
        STATUS      current
        DESCRIPTION
               "The number of times the FC-port waited due to lack of
                transmit credits. "
        ::= { fcIfErrorEntry 15 }

fcIfFramesTooLong  OBJECT-TYPE
        SYNTAX      Counter32
        MAX-ACCESS  read-only
        STATUS      current
        DESCRIPTION
               "The number of frames received by the FC-port where 
                the frame length was greater than what was agreed to 
                in FLOGI/PLOGI. This could be caused by losing the 
                end of frame delimiter. "
        ::= { fcIfErrorEntry 16 }

fcIfFramesTooShort  OBJECT-TYPE
        SYNTAX      Counter32
        MAX-ACCESS  read-only
        STATUS      current
        DESCRIPTION
               "The number of frames received by the FC-port where 
                the frame length was less than the minimum indicated
                by the frame header (normally 24 bytes), but it could 
                be more if the DFCTL field indicates an optional
                header should be present. "
        ::= { fcIfErrorEntry 17 }

fcIfLRRIn  OBJECT-TYPE
        SYNTAX      Counter32
        MAX-ACCESS  read-only
        STATUS      current
        DESCRIPTION
               "The number of Link reset responses received by the 
                FC-port. "
        REFERENCE
              "FC-PH REV 4.3 Section 16.4.5"         
        ::= { fcIfErrorEntry 18 }

fcIfLRROut  OBJECT-TYPE
        SYNTAX      Counter32
        MAX-ACCESS  read-only
        STATUS      current
        DESCRIPTION
               "The number of Link reset responses transmitted 
                by the FC-port. "
        REFERENCE
              "FC-PH REV 4.3 Section 16.4.5"          
        ::= { fcIfErrorEntry 19 }

fcIfNOSIn  OBJECT-TYPE
        SYNTAX      Counter32
        MAX-ACCESS  read-only
        STATUS      current
        DESCRIPTION
               "The number of non-operational sequences received by
                the FC-port. "
        REFERENCE
              "FC-PH REV 4.3 Section 16.4.2"             
        ::= { fcIfErrorEntry 20 }

fcIfNOSOut  OBJECT-TYPE
        SYNTAX      Counter32
        MAX-ACCESS  read-only
        STATUS      current
        DESCRIPTION
               "The number of non-operational sequences transmitted
                by the FC-port. "
        REFERENCE
              "FC-PH REV 4.3 Section 16.4.2"           
        ::= { fcIfErrorEntry 21 }

fcIfFragFrames   OBJECT-TYPE
        SYNTAX      Counter32
        MAX-ACCESS  read-only
        STATUS      current
        DESCRIPTION
               "The number of fragmented frames received by the 
                FC-port. "         
        ::= { fcIfErrorEntry 22 }

fcIfEOFaFrames  OBJECT-TYPE
        SYNTAX      Counter32
        MAX-ACCESS  read-only
        STATUS      current
        DESCRIPTION
               "The number of frames received by FC-port with 
                EOF aborts. " 
        REFERENCE
              "FC-PH REV 4.3 Section 17.6.3"        
        ::= { fcIfErrorEntry 23 }

fcIfUnknownClassFrames  OBJECT-TYPE
        SYNTAX      Counter32
        MAX-ACCESS  read-only
        STATUS      current
        DESCRIPTION
               "The number of unknown class frames received by
                FC-port. "         
        ::= { fcIfErrorEntry 24 }

fcIf8b10bDisparityErrors  OBJECT-TYPE
        SYNTAX      Counter32
        MAX-ACCESS  read-only
        STATUS      current
        DESCRIPTION
               "The number of 8b10b disparity errors. "         
        ::= { fcIfErrorEntry 25 }

fcIfFramesDiscard  OBJECT-TYPE
        SYNTAX      Counter32
        MAX-ACCESS  read-only
        STATUS      current
        DESCRIPTION
               "The number of frames discarded by the FC-port. "
        ::= { fcIfErrorEntry 26 }

fcIfELPFailures OBJECT-TYPE
        SYNTAX      Counter32
        MAX-ACCESS  read-only
        STATUS      current
        DESCRIPTION
              "The number of Exchange Link Parameters Switch Fabric
               Internal Link service request failures detected by the
               FC-Port. This object is applicable to only 
               Interconnect_Port, which are E_Port or B_Port. " 
        REFERENCE
              "FC-PH REV 4.3 Section 29.3.1"
        ::= { fcIfErrorEntry 27 }

fcIfBBCreditTransistionFromZero OBJECT-TYPE
        SYNTAX      Counter32
        MAX-ACCESS  read-only
        STATUS      current
        DESCRIPTION
              "The number of transistions of BB credit
               out of zero state. "
        ::= { fcIfErrorEntry 28 }

fcIfEISLFramesDiscard  OBJECT-TYPE
        SYNTAX      Counter32
        MAX-ACCESS  read-only
        STATUS      current
        DESCRIPTION
              "The number of Enhanced Inter Switch Link (EISL) frames
               discarded by the FC-port. EISL frames carry an EISL
               header containing VSAN among other information. " 
        ::= { fcIfErrorEntry 29 }

fcIfFramingErrorFrames  OBJECT-TYPE
        SYNTAX      Counter32
        MAX-ACCESS  read-only
        STATUS      current
        DESCRIPTION
              "The number of framing errors. This denotes that the 
               FC-port detected an inconsistency of frame structure. "
        ::= { fcIfErrorEntry 30 }


--
-- fcIfC2AccountingTable .
--

fcIfC2AccountingTable OBJECT-TYPE
        SYNTAX      SEQUENCE OF FcIfC2AccountingEntry
        MAX-ACCESS  not-accessible
        STATUS      current
        DESCRIPTION
              "This table contains, one entry for each F, FL or TL
               ports in the fabric element, including Port Channel
               ports. It contains Class 2 accounting information."
        ::= { cffFcFeStatistics 2 }

fcIfC2AccountingEntry OBJECT-TYPE
        SYNTAX      FcIfC2AccountingEntry
        MAX-ACCESS  not-accessible
        STATUS      current
        DESCRIPTION
              "Each entry contains Class 2 accounting information for
               each F, FL or TL port. "
        INDEX { ifIndex }
        ::= { fcIfC2AccountingTable 1 }

FcIfC2AccountingEntry ::=
        SEQUENCE {
            fcIfC2InFrames           Counter64,
            fcIfC2OutFrames          Counter64,
            fcIfC2InOctets           Counter64,
            fcIfC2OutOctets          Counter64,
            fcIfC2Discards           Counter32,
            fcIfC2FbsyFrames         Counter32,
            fcIfC2FrjtFrames         Counter32,
            fcIfC2PBSYFrames         Counter32,
            fcIfC2PRJTFrames         Counter32 
        }

fcIfC2InFrames OBJECT-TYPE
        SYNTAX      Counter64
        MAX-ACCESS  read-only
        STATUS      current
        DESCRIPTION
             "The number of Class 2 frames received by this port from
              its attached Nx_Port. "
        ::= { fcIfC2AccountingEntry 1 }

fcIfC2OutFrames OBJECT-TYPE
        SYNTAX      Counter64
        MAX-ACCESS  read-only
        STATUS      current
        DESCRIPTION
              "The number of Class 2 frames delivered through this
               port to its attached Nx_Port. "
        ::= { fcIfC2AccountingEntry 2 }

fcIfC2InOctets OBJECT-TYPE
        SYNTAX      Counter64
        MAX-ACCESS  read-only
        STATUS      current
        DESCRIPTION
              "The number of Class 2 frame octets, including the frame
               delimiters, received by this port from its attached
               Nx_Port. "
        ::= { fcIfC2AccountingEntry 3 }

fcIfC2OutOctets OBJECT-TYPE
        SYNTAX      Counter64
        MAX-ACCESS  read-only
        STATUS      current
        DESCRIPTION
              "The number of Class 2 frame octets, including the frame
               delimiters, delivered through this port to its attached
               Nx_Port. "
        ::= { fcIfC2AccountingEntry 4 }

fcIfC2Discards OBJECT-TYPE
        SYNTAX      Counter32
        MAX-ACCESS  read-only
        STATUS      current
        DESCRIPTION
              "The number of Class 2 frames discarded by this port. "
        ::= { fcIfC2AccountingEntry 5 }

fcIfC2FbsyFrames OBJECT-TYPE
        SYNTAX      Counter32
        MAX-ACCESS  read-only
        STATUS      current
        DESCRIPTION
              "The number of F_BSY frames generated by this port 
               against Class 2 frames. "
        REFERENCE
              "FC-PH REV 4.3 Section 20.3.3.1"
        ::= { fcIfC2AccountingEntry 6 }

fcIfC2FrjtFrames OBJECT-TYPE
        SYNTAX      Counter32
        MAX-ACCESS  read-only
        STATUS      current
        DESCRIPTION
              "The number of F_RJT frames generated by this port
               against Class 2 frames. "
        REFERENCE
              "FC-PH REV 4.3 Section 20.3.3.3"
        ::= { fcIfC2AccountingEntry 7 }

fcIfC2PBSYFrames  OBJECT-TYPE
        SYNTAX      Counter32
        MAX-ACCESS  read-only
        STATUS      current
        DESCRIPTION
               "The number of times that port busy was returned to 
                this port as result of a class 2 frame that could not
                be delivered to the other end of the link. This 
                occurs if the destination Nx_Port is temporarily busy.
                PBSY can only occur on SOFc1 frames ( the frames that
                establish a connection ). "
        REFERENCE
              "FC-PH REV 4.3 Section 29.9.2" 
        ::= { fcIfC2AccountingEntry 8 }

fcIfC2PRJTFrames  OBJECT-TYPE
        SYNTAX      Counter32
        MAX-ACCESS  read-only
        STATUS      current
        DESCRIPTION
                "The number of times that port reject was returned to
                 this port as a result of a class 2 frame that was 
                 rejected at the destination Nx_Port. "
        REFERENCE
              "FC-PH REV 4.3 Section 29.9.2"               
        ::= { fcIfC2AccountingEntry 9 }


-- 
-- fcIfC3AccountingTable 
-- 

fcIfC3AccountingTable OBJECT-TYPE
        SYNTAX      SEQUENCE OF FcIfC3AccountingEntry
        MAX-ACCESS  not-accessible
        STATUS      current
        DESCRIPTION
              "This table contains, one entry for each F, FL or TL
               ports in the fabric element, including Port Channel
               ports. It contains Class 3 accounting information. "
        ::= { cffFcFeStatistics 3 }

fcIfC3AccountingEntry OBJECT-TYPE
        SYNTAX      FcIfC3AccountingEntry
        MAX-ACCESS  not-accessible
        STATUS      current
        DESCRIPTION
              "Each entry contains Class 3 accounting information for
               each F, FL or TL port. "
        INDEX { ifIndex}
        ::= { fcIfC3AccountingTable 1 }


FcIfC3AccountingEntry ::=
        SEQUENCE {
            fcIfC3InFrames              Counter64,
            fcIfC3OutFrames             Counter64,
            fcIfC3InOctets              Counter64,
            fcIfC3OutOctets             Counter64,
            fcIfC3Discards              Counter32      
        }

fcIfC3InFrames OBJECT-TYPE
        SYNTAX      Counter64
        MAX-ACCESS  read-only
        STATUS      current
        DESCRIPTION
              "The number of Class 3 frames received by this port 
               from its attached Nx_Port. "
        ::= { fcIfC3AccountingEntry 1 }

fcIfC3OutFrames OBJECT-TYPE
        SYNTAX      Counter64
        MAX-ACCESS  read-only
        STATUS      current
        DESCRIPTION
              "The number of Class 3 frames transmitted by this 
               port to its attached Nx_Port. "
        ::= { fcIfC3AccountingEntry 2 }

fcIfC3InOctets OBJECT-TYPE
        SYNTAX      Counter64
        MAX-ACCESS  read-only
        STATUS      current
        DESCRIPTION
              "The number of Class 3 frame octets, including the 
               frame delimiters, received by this port from its 
               attached Nx_Port. "
        ::= { fcIfC3AccountingEntry 3 }

fcIfC3OutOctets OBJECT-TYPE
        SYNTAX      Counter64
        MAX-ACCESS  read-only
        STATUS      current
        DESCRIPTION
              "The number of Class 3 frame octets, including the 
               frame delimiters, transmitted by this port to its a
               attached Nx_Port. "
        ::= { fcIfC3AccountingEntry 4 }

fcIfC3Discards OBJECT-TYPE
        SYNTAX      Counter32
        MAX-ACCESS  read-only
        STATUS      current
        DESCRIPTION
              "The number of Class 3 frames discarded by this port. "
        ::= { fcIfC3AccountingEntry 5 }


-- 
-- fcIfCfAccountingTable 
--

fcIfCfAccountingTable OBJECT-TYPE
        SYNTAX      SEQUENCE OF FcIfCfAccountingEntry
        MAX-ACCESS  not-accessible
        STATUS      current
        DESCRIPTION
               "A table that contains, one entry for each
                Interconnect_Ports (xE_port, B_port) in the fabric
                element, including Port Channel ports.
                It contains Class F accounting information. "
        ::= { cffFcFeStatistics 4 }

fcIfCfAccountingEntry OBJECT-TYPE
        SYNTAX      FcIfCfAccountingEntry
        MAX-ACCESS  not-accessible
        STATUS      current
        DESCRIPTION
               "An entry containing Class F accounting information for
               each xE_port. "
        INDEX { ifIndex }
        ::= { fcIfCfAccountingTable 1 }

FcIfCfAccountingEntry ::=  
        SEQUENCE {
            fcIfCfInFrames           Counter64,
            fcIfCfOutFrames          Counter64,
            fcIfCfInOctets           Counter64,
            fcIfCfOutOctets          Counter64,
            fcIfCfDiscards           Counter32
        }

fcIfCfInFrames  OBJECT-TYPE
        SYNTAX      Counter64
        MAX-ACCESS  read-only
        STATUS      current
        DESCRIPTION
               "The number of Class F frames received by this port. "
        ::= { fcIfCfAccountingEntry 1 }

fcIfCfOutFrames  OBJECT-TYPE
        SYNTAX      Counter64
        MAX-ACCESS  read-only
        STATUS      current
        DESCRIPTION
               "The number of Class F frames transmitted by this 
                port. "            
        ::= { fcIfCfAccountingEntry 2 }

fcIfCfInOctets OBJECT-TYPE
        SYNTAX      Counter64
        MAX-ACCESS  read-only
        STATUS      current
        DESCRIPTION
              "The number of Class F frame octets, including the 
               frame delimiters, received by this port from its 
               attached Nx_Port. "
        ::= { fcIfCfAccountingEntry 3 }

fcIfCfOutOctets OBJECT-TYPE
        SYNTAX      Counter64
        MAX-ACCESS  read-only
        STATUS      current
        DESCRIPTION
              "The number of Class F frame octets, including the 
               frame delimiters, transmitted by this port to its a
               attached Nx_Port. "
        ::= { fcIfCfAccountingEntry 4 }

fcIfCfDiscards OBJECT-TYPE
        SYNTAX      Counter32
        MAX-ACCESS  read-only
        STATUS      current
        DESCRIPTION
              "The number of Class F frames discarded by this port. "
        ::= { fcIfCfAccountingEntry 5 }

-- Notifications


fcTrunkIfDownNotify NOTIFICATION-TYPE
        OBJECTS    { fcTrunkIfOperStatus, fcTrunkIfOperStatusCause,
                     fcTrunkIfOperStatusCauseDescr }
        STATUS     current
        DESCRIPTION
               "This notification is generated by the agent
                whenever the fcTrunkifOperStatus object for this
                trunk interface is about to enter the down state from
                some other state. This other state is indicated by 
                the included value of fcTrunkifOperStatus."
        ::= { cffFcFeNotifications 1 }

fcTrunkIfUpNotify NOTIFICATION-TYPE
        OBJECTS    { fcTrunkIfOperStatus, fcTrunkIfOperStatusCause,
                     fcTrunkIfOperStatusCauseDescr }
        STATUS     current
        DESCRIPTION
               "This notification is generated by the agent
                whenever the fcTrunkifOperStatus object for one of
                its trunk interfaces has left the down state and 
                transitioned into some other state. This other
                state is indicated by the included value of
                fcTrunkifOperStatus."
        ::= { cffFcFeNotifications 2 }

fcIfElpReject NOTIFICATION-TYPE
        OBJECTS    { fcIfElpNbrNodeName, fcIfElpNbrPortName,
                     fcIfElpRejectReasonCode, 
                     fcIfElpRejectReasonCodeExpl }
        STATUS     current
        DESCRIPTION
               "This notification is generated by the agent
                whenever this interface received a ELP request and
                rejected it. "
        ::= { cffFcFeNotifications 3 }


-- conformance information

cffFcFeMIBCompliances  OBJECT IDENTIFIER ::= { cffFcFeMIBConformance 1 }
cffFcFeMIBGroups       OBJECT IDENTIFIER ::= { cffFcFeMIBConformance 2 }

cffFcFeMIBCompliance  MODULE-COMPLIANCE
            STATUS   current
            DESCRIPTION
                   "The compliance statement for entities which 
                    implement the fc management mib."
            MODULE MANDATORY-GROUPS { fcFeGroup,
                                      fcIfGroup,
                                      fcTrunkIfGroup,
                                      fcIfLoginGroup,
                                      fcIfElpGroup,
                                      fcIfCapGroup,
                                      fcIfErrorGroup,
                                      fcIfC2AccountingGroup,
                                      fcIfC3AccountingGroup,
                                      fcIfCfAccountingGroup,
                                      fcIfNotificationGroup }

            OBJECT  cffFcFeElementName
            MIN-ACCESS read-only
            DESCRIPTION
                   "Write access is not required."  
                   
            OBJECT fcIfRxDataFieldSize
            SYNTAX Integer32 (256..2112)
            DESCRIPTION 
                 "It is compliant to support a minimum value of
                  of 256 for this object which is larger than 
                  the defined minimum value."       

            ::= { cffFcFeMIBCompliances  1 }


-- Units of Conformance

fcFeGroup OBJECT-GROUP
     OBJECTS  { cffFcFeElementName, adminTrunkProtocol,
                fcIfElpRejectReasonCode, 
                fcIfElpRejectReasonCodeExpl }
     STATUS  current
     DESCRIPTION
            "A collection objects giving port information."
     ::= { cffFcFeMIBGroups  1 }

fcIfGroup OBJECT-GROUP
     OBJECTS  { fcIfWwn, fcIfAdminMode, fcIfOperMode,
                fcIfAdminSpeed, fcIfBeaconMode,
                fcIfPortChannelIfIndex, fcIfOperStatusCause,
                fcIfOperStatusCauseDescr,
                fcIfAdminTrunkMode, fcIfOperTrunkMode,
                fcIfAllowedVsanList2k, fcIfAllowedVsanList4k,
                fcIfActiveVsanList2k,
                fcIfActiveVsanList4k, fcIfBbCreditModel,
                fcIfHoldTime, fcIfTransmitterType,
                fcIfConnectorType, fcIfSerialNo,
                fcIfRevision, fcIfVendor, fcIfSFPSerialIDData,
                fcIfPartNumber,fcIfAdminRxBbCredit,
                fcIfAdminRxBbCreditModeISL,
                fcIfAdminRxBbCreditModeFx,fcIfOperRxBbCredit,
                fcIfRxDataFieldSize }      
     STATUS  current
     DESCRIPTION
            "A collection objects giving port information."
     ::= { cffFcFeMIBGroups  2 }

fcTrunkIfGroup OBJECT-GROUP
     OBJECTS  { fcTrunkIfOperStatus, fcTrunkIfOperStatusCause,
                fcTrunkIfOperStatusCauseDescr }
     STATUS  current
     DESCRIPTION
            "A collection objects giving trunk port information."
     ::= { cffFcFeMIBGroups  3 }

fcIfLoginGroup  OBJECT-GROUP
     OBJECTS   { fcIfLoginEntryCount, fcIfNxPortNodeName,
                 fcIfNxPortName, fcIfNxPortAddress,
                 fcIfNxFcphVersionAgreed, fcIfNxRxBbCredit,
                 fcIfNxTxBbCredit, fcIfNxClass2RxDataFieldSize,
                 fcIfNxClass3RxDataFieldSize, fcIfNxCosSuppAgreed,
                 fcIfNxClass2SeqDelivAgreed,
                 fcIfNxClass3SeqDelivAgreed } 
     STATUS  current
     DESCRIPTION
            "A collection of objects giving Fabric Login info for
             Fx_Port."
     ::= { cffFcFeMIBGroups  4 }

fcIfElpGroup  OBJECT-GROUP
     OBJECTS   { fcIfElpNbrNodeName, fcIfElpNbrPortName,
                 fcIfElpRxBbCredit, fcIfElpTxBbCredit,
                 fcIfElpCosSuppAgreed, fcIfElpClass2SeqDelivAgreed,
                 fcIfElpClass2RxDataFieldSize,
                 fcIfElpClass3SeqDelivAgreed,
                 fcIfElpClass3RxDataFieldSize, fcIfElpClassFXII,
                 fcIfElpClassFRxDataFieldSize,
                 fcIfElpClassFConcurrentSeq,
                 fcIfElpClassFEndToEndCredit, fcIfElpClassFOpenSeq }
     STATUS  current
     DESCRIPTION
            "A collection of objects giving Exchange Link Parameters
             established between the 2 Interconnect_Ports."
     ::= { cffFcFeMIBGroups  5 }


fcIfCapGroup  OBJECT-GROUP
     OBJECTS  { fcIfCapFcphVersionHigh, fcIfCapFcphVersionLow,
                fcIfCapRxBbCreditMax, fcIfCapRxBbCreditMin,
                fcIfCapRxDataFieldSizeMax, fcIfCapRxDataFieldSizeMin,
                fcIfCapCos, fcIfCapClass2SeqDeliv,
                fcIfCapClass3SeqDeliv, fcIfCapHoldTimeMax,
                fcIfCapHoldTimeMin,fcIfCapISLRxBbCreditMax,
                fcIfCapISLRxBbCreditMin,fcIfCapRxBbCreditWriteable,
                fcIfCapRxBbCreditDefault,fcIfCapISLRxBbCreditDefault  }
     STATUS  current
     DESCRIPTION
            "A collection of objects providing information what the 
             port is capable of supporting. "
     ::= { cffFcFeMIBGroups  6 }


fcIfErrorGroup OBJECT-GROUP
     OBJECTS  { fcIfLinkFailures, fcIfSyncLosses,
                fcIfSigLosses, fcIfPrimSeqProtoErrors,
                fcIfInvalidTxWords, fcIfInvalidCrcs,
                fcIfDelimiterErrors, fcIfAddressIdErrors,
                fcIfLinkResetIns, fcIfLinkResetOuts, fcIfOlsIns,
                fcIfOlsOuts, fcIfRuntFramesIn, fcIfJabberFramesIn,
                fcIfTxWaitCount, fcIfFramesTooLong,
                fcIfFramesTooShort, fcIfLRRIn,
                fcIfLRROut, fcIfNOSIn, fcIfNOSOut, fcIfFragFrames,
                fcIfEOFaFrames, fcIfUnknownClassFrames,
                fcIf8b10bDisparityErrors, fcIfFramesDiscard,
                fcIfELPFailures, fcIfBBCreditTransistionFromZero,
                fcIfEISLFramesDiscard, fcIfFramingErrorFrames }
     STATUS  current
     DESCRIPTION
            "A collection of objects providing errors of the ports. "
     ::= { cffFcFeMIBGroups  7 }

fcIfC2AccountingGroup OBJECT-GROUP
     OBJECTS  { fcIfC2InFrames, fcIfC2OutFrames, fcIfC2InOctets,
                fcIfC2OutOctets, fcIfC2Discards, fcIfC2FbsyFrames,
                fcIfC2FrjtFrames, fcIfC2PBSYFrames, fcIfC2PRJTFrames }
     STATUS  current
     DESCRIPTION
            "A collection of objects providing class 2 accounting
             information of  the ports. "
     ::= { cffFcFeMIBGroups  8 }

fcIfC3AccountingGroup OBJECT-GROUP
     OBJECTS  { fcIfC3InFrames, fcIfC3OutFrames, fcIfC3InOctets,
                fcIfC3OutOctets, fcIfC3Discards }
     STATUS  current
     DESCRIPTION
            "A collection of objects providing class 3 accounting
             information of  the ports. "
     ::= { cffFcFeMIBGroups  9 }

fcIfCfAccountingGroup OBJECT-GROUP
     OBJECTS  { fcIfCfInFrames, fcIfCfOutFrames, fcIfCfInOctets,
                fcIfCfOutOctets, fcIfCfDiscards }
     STATUS  current
     DESCRIPTION
            "A collection of objects providing class f accounting
             information of the ports. "
     ::= { cffFcFeMIBGroups  10 }

fcIfNotificationGroup        NOTIFICATION-GROUP
     NOTIFICATIONS { fcTrunkIfDownNotify, fcTrunkIfUpNotify, 
                     fcIfElpReject }
     STATUS current
     DESCRIPTION
            "A collection of notifications for monitoring fibre
             channel interfaces. "
     ::= { cffFcFeMIBGroups  11 }

       
END
